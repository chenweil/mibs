-- =================================================================
-- Copyright (c) 2020 Unisyue Technologies Co., Ltd.  All rights reserved.
--
-- Description: ENTITY RELATION MIB
-- Version: V1.2
-- History:
--   V1.0(Initial version) 19th Aug 2004
--   V1.1 2004-09-10 Exchange MIB objects' sequence, including unisEntRelationType
--                   and unisEntityIndex.
--                   Change subidentifier of unisEntRelationConformance from 3 to 2.
--   V1.2 2004-10-12 updated by gaolong
--        Remove unisEntityIndex, unisEntRelationType from unisEntRelationGroup
--        because they are not-accessible objects.
-- =================================================================
--

    UNIS-ENTRELATION-MIB DEFINITIONS ::= BEGIN

        IMPORTS
            PhysicalIndex
                FROM ENTITY-MIB
            unisCommon
                FROM UNIS-OID-MIB
            OBJECT-GROUP, MODULE-COMPLIANCE
                FROM SNMPv2-CONF
            OBJECT-TYPE, MODULE-IDENTITY
                FROM SNMPv2-SMI
            TEXTUAL-CONVENTION
                FROM SNMPv2-TC;



        unisEntityRelation MODULE-IDENTITY
            LAST-UPDATED "200408190000Z"
            ORGANIZATION
                "Unisyue Technologies Co., Ltd."
            CONTACT-INFO
                ""
            DESCRIPTION
                "The private MIB file includes the general relation information
                information of entities.
                Entity MIB is used to express the physical location of the physical
                entities. Other relations, such as stack port pair and combo port
                pair, are not suitable to be implemented in Entity MIB. So this MIB is
                used to  express these relations. "
            ::= { unisCommon 15 }



--  Textual conventions
--
        UnisEntRelationType ::= TEXTUAL-CONVENTION
            STATUS current
            DESCRIPTION
                "entRelationType describe the relation type of the two entities
                (indicated by entityIndex and relatedEntityIndex) .
                stackport: this port is a stack port.
                entityIndex is the default uplinkport index,
                and relatedEntityIndex is the default downlinkport index.
                comboport: this port is a combo port.
                entityIndex is the default active port index,
                and relatedEntityIndex is the default inactive port index."
            SYNTAX INTEGER
                {
                stackport(1),
                comboport(2)
                }




--  Node definitions
--
        unisEntRelationObjects OBJECT IDENTIFIER ::= { unisEntityRelation 1 }

--    MIB contains four groups
        unisEntRelation OBJECT IDENTIFIER ::= { unisEntRelationObjects 1 }

        unisEntRelationTable OBJECT-TYPE
            SYNTAX SEQUENCE OF UnisEntRelationEntry
            MAX-ACCESS not-accessible
            STATUS current
            DESCRIPTION
                "Entity MIB is used to express the physical location of
                the physical entities. Other relations, such as stack
                port pair and combo port pair, are not suitable to be
                implemented in Entity MIB. This MIB is used to express
                these relations. "
            ::= { unisEntRelation 1 }

        unisEntRelationEntry OBJECT-TYPE
            SYNTAX UnisEntRelationEntry
            MAX-ACCESS not-accessible
            STATUS current
            DESCRIPTION
                "The information about a particular physical entity."
            INDEX { unisEntRelationType, unisEntityIndex, unisRelatedEntityIndex }
            ::= { unisEntRelationTable 1 }

        UnisEntRelationEntry ::=
            SEQUENCE {
                unisEntRelationType
                    UnisEntRelationType,
                unisEntityIndex
                    PhysicalIndex,
                unisRelatedEntityIndex
                    PhysicalIndex
             }

        unisEntRelationType OBJECT-TYPE
            SYNTAX UnisEntRelationType
            MAX-ACCESS not-accessible
            STATUS current
            DESCRIPTION
                "The index of unisEntRelationTable.
                entRelationType describe the relation type of the two
                entities(indicated by entityIndex and relatedEntityIndex) "
            ::= { unisEntRelationEntry 1 }

        unisEntityIndex OBJECT-TYPE
            SYNTAX PhysicalIndex
            MAX-ACCESS not-accessible
            STATUS current
            DESCRIPTION
                "The index of unisEntRelationTable.
                entityIndex is the index of the entity.
                This index is identical to entPhysicalIndex in ENTITY-MIB"
            ::= { unisEntRelationEntry 2 }

        unisRelatedEntityIndex OBJECT-TYPE
            SYNTAX PhysicalIndex
            MAX-ACCESS read-only
            STATUS current
            DESCRIPTION
                "The index of unisEntRelationTable.
                relatedEntityIndex is the entity index that entityIndex related to,
                This index is identical to entPhysicalIndex in ENTITY-MIB"
            ::= { unisEntRelationEntry 3 }

--    Conformance and Compliance
        unisEntRelationConformance OBJECT IDENTIFIER ::= { unisEntityRelation 2 }

        unisEntRelationCompliances OBJECT IDENTIFIER ::= { unisEntRelationConformance 1 }


-- this module
        unisEntRelationCompliance MODULE-COMPLIANCE
            STATUS current
            DESCRIPTION
                "The compliance statement for systems supporting this MIB."
            MODULE -- this module
                MANDATORY-GROUPS { unisEntRelationGroup }
            ::= { unisEntRelationCompliances 1 }

        unisEntRelationGroups OBJECT IDENTIFIER ::= { unisEntRelationConformance 2 }

        unisEntRelationGroup OBJECT-GROUP
            OBJECTS { unisRelatedEntityIndex }
            STATUS current
            DESCRIPTION
                "Standard Entity Relation group."
            ::= { unisEntRelationGroups 1 }


    END
