-- =================================================================
-- Copyright (c) 2020 Unisyue Technologies Co., Ltd.  All rights reserved.
--
-- Description:
-- Reference:
-- Version: V2.8
-- History:
--  V1.0 Initial version 2004-07-13
--  V1.1 2004-10-12 updated by gaolong
--       Remove hyphens from DisplayString definition.
--  V2.0 2004-12-28 updated by huguohua02576
--       Add unisUserState, unisUserInfoRowStatus, unisUserIndex under unisUserInfoTable
--   Change index from unisUserName to unisUserIndex under unisUserInfoTable
--       Modify unisUserName, unisUserPassword, unisAuthMode, unisUserLevel's MAX-ACCESS
--       from read-only to read-create
--       Add unisUserAttributeTable, unisUserMaxNum, unisUserCurrNum and unisUserIndexIndicator
--  V2.1 2006-02-07 updated by sunludong03130
--       Modify unisFtpService, unisLanAccessService, unisSshService, unisTelnetService,
--       unisTerminalService, unisFtpDirectory's description
--  V2.2 2006-12-26 updated by zhangzhancheng02444
--       Modify unisAccessLimit, unisFtpDirectory, unisSlotNum, unisSubSlotNum,
--       and unisPortNum
--  V2.3 2008-03-13 updated by w02260
--       Add unisExpirationDate, unisUserGroup under unisUserAttributeTable,
--       and add unisUserGroupObjects
--  V2.4 2008-12-29 updated by liubo04367
--       Add unisPortalService under unisUserAttributeTable
--  V2.5 2012-02-28 updated by y02965
--       Add unisUserRoleTable
--       Add unisPPPService, unisHttpService and unisHttpsService under unisUserAttributeTable
--  V2.6 2012-05-28 updated by y06401
--       Modify description of unisAuthMode.
--       2012-10-11 updated by l04367
--       Add unisUserIfIndex
--       Modify unisUserRole
--  V2.7 2013-04-25 updated by q04356
--       Modified the description of unisIdleCut
--  V2.8 2016-11-19 updated by y06401
--       Modified the description of unisUserGroup
--       Modified the SYNTAX of unisUserGroupName
-- =================================================================
UNIS-USER-MIB DEFINITIONS ::= BEGIN
IMPORTS
    unisCommon
        FROM UNIS-OID-MIB
    RowStatus, MacAddress, TEXTUAL-CONVENTION, DateAndTime, DisplayString
        FROM SNMPv2-TC
    IpAddress, Integer32, OBJECT-TYPE, MODULE-IDENTITY
        FROM SNMPv2-SMI;

unisUser MODULE-IDENTITY
    LAST-UPDATED "201611190000Z"            -- November 19, 2016 at 00:00 GMT
    ORGANIZATION
        "Unisyue Technologies Co., Ltd."
    CONTACT-INFO
        ""
    DESCRIPTION
        "
        This MIB contains objects to
        Manage configuration and Monitor running state
        for userlog feature.
        "
    REVISION "201611190000Z"        -- November 19, 2016 at 00:00 GMT
    DESCRIPTION
        "Modified description of unisUserGroup.
        Modified SYNTAX of unisUserGroupName"
    ::= { unisCommon 12 }


--
-- type definitions
--

-- ServiceType
ServiceType ::=  TEXTUAL-CONVENTION
    STATUS      current
    DESCRIPTION
        "enable (1)
        disable (2)
        "
    SYNTAX      INTEGER
        {
            enable(1),
            disable(2)
        }
--
-- end of type definitions
--

-- unisUserObjects===============================================================
unisUserObjects OBJECT IDENTIFIER ::= { unisUser 1 }


-- unisUserInfoTable=============================================================
unisUserInfoTable OBJECT-TYPE
    SYNTAX      SEQUENCE OF UnisUserInfoEntry
    MAX-ACCESS  not-accessible
    STATUS      current
    DESCRIPTION
        "
        Local User Info Table
        "
    ::= { unisUserObjects 1 }

unisUserInfoEntry OBJECT-TYPE
    SYNTAX      UnisUserInfoEntry
    MAX-ACCESS  not-accessible
    STATUS      current
    DESCRIPTION
        "
        The entry of unisUserInfoTable
        "
    INDEX
        {
            unisUserIndex
        }
    ::= { unisUserInfoTable 1 }

UnisUserInfoEntry ::= SEQUENCE
    {
        unisUserName             DisplayString,
        unisUserPassword         DisplayString,
        unisAuthMode             Integer32,
        unisUserLevel            Integer32,
        unisUserState            INTEGER,
        unisUserInfoRowStatus    RowStatus,
        unisUserIndex            Integer32
    }


unisUserName OBJECT-TYPE
    SYNTAX      DisplayString(SIZE(1..255))
    MAX-ACCESS  read-create
    STATUS      current
    DESCRIPTION
        "
        The name of local user, it must be unique.
        "
    ::= { unisUserInfoEntry 1 }

unisUserPassword OBJECT-TYPE
    SYNTAX      DisplayString(SIZE(0..255))
    MAX-ACCESS  read-create
    STATUS      current
    DESCRIPTION
        "
        The password of local user, default is null.
        When read, unisUserPassword always returns an Octet String of length zero.
        "
    ::= { unisUserInfoEntry 2 }

unisAuthMode OBJECT-TYPE
    SYNTAX      Integer32
    MAX-ACCESS  read-create
    STATUS      current
    DESCRIPTION
        "
        The encrypting type of password:
        0 : password simple, means password is entered in clean text and saved in cipher text.
        1 : password hash simple, means password is entered in clean text and saved in hash value.
        7 : password cipher, means password is entered and saved in cipher text.
        8 : password hash cipher, means password is entered and saved in hash value.
        default is 0.
        "
    ::= { unisUserInfoEntry 3 }

unisUserLevel OBJECT-TYPE
    SYNTAX      Integer32
    MAX-ACCESS  read-create
    STATUS      current
    DESCRIPTION
        "
        The privilege of local user
        the value range is from 0 to 3, and 0 is minimum, 3 is maximum.
        default is 0.
        "
    ::= { unisUserInfoEntry 4 }

unisUserState OBJECT-TYPE
    SYNTAX      INTEGER
        {
            active(0),
            block(1)
        }
    MAX-ACCESS  read-create
    STATUS      current
    DESCRIPTION
        "
        The state of local user
        0: active, means local user can execute any operations that he has
           privilege to do.
        1: block, means local user can not execute any operations.
        default is active.
        "
    ::= { unisUserInfoEntry 5 }

unisUserInfoRowStatus OBJECT-TYPE
    SYNTAX      RowStatus
    MAX-ACCESS  read-create
    STATUS      current
    DESCRIPTION
        "
        The status of this conceptual row.  Now only support CreateAndGo and
        Destroy and Active.
        "
    ::= { unisUserInfoEntry 6 }


unisUserIndex OBJECT-TYPE
    SYNTAX      Integer32(1..2147483646)
    MAX-ACCESS  not-accessible
    STATUS      current
    DESCRIPTION
        "
        The index of local user
        "
    ::= { unisUserInfoEntry 7 }

-- unisUserAttributeTable========================================================
unisUserAttributeTable OBJECT-TYPE
    SYNTAX      SEQUENCE OF UnisUserAttributeEntry
    MAX-ACCESS  not-accessible
    STATUS      current
    DESCRIPTION
        "
        Local User Attribute Table.
        if there are data in unisUserInfoTable, this table should have the
        relevant data.
        this table only support query and modify, but not support create and
        delete operations.
        "
    ::= { unisUserObjects 2 }

unisUserAttributeEntry OBJECT-TYPE
    SYNTAX      UnisUserAttributeEntry
    MAX-ACCESS  not-accessible
    STATUS      current
    DESCRIPTION
        "The entry of unisUserAttributeTable "
    INDEX
        {
            unisUserIndex
        }
    ::= { unisUserAttributeTable 1 }

UnisUserAttributeEntry ::= SEQUENCE
    {
        unisAccessLimit         Integer32,
        unisIdleCut             Integer32,
        unisIPAddress           IpAddress,
        unisNasIPAddress        IpAddress,
        unisSlotNum             Integer32,
        unisSubSlotNum          Integer32,
        unisPortNum             Integer32,
        unisMacAddress          MacAddress,
        unisVlan                Integer32,
        unisFtpService          ServiceType,
        unisFtpDirectory        OCTET STRING,
        unisLanAccessService    ServiceType,
        unisSshService          ServiceType,
        unisTelnetService       ServiceType,
        unisTerminalService     ServiceType,
        unisExpirationDate      DateAndTime,
        unisUserGroup           DisplayString,
        unisPortalService       ServiceType,
        unisPPPService          ServiceType,
        unisHttpService         ServiceType,
        unisHttpsService        ServiceType,
        unisUserIfIndex         Integer32
    }


unisAccessLimit OBJECT-TYPE
    SYNTAX      Integer32
    MAX-ACCESS  read-write
    STATUS      current
    DESCRIPTION
        "
        The maximum user number of current user who can access devices.
        default is 0, means no limit.
        "
    ::= { unisUserAttributeEntry 1 }

unisIdleCut OBJECT-TYPE
    SYNTAX      Integer32
    MAX-ACCESS  read-write
    STATUS      current
    DESCRIPTION
        "
        Valid idle time out(second),
        default is 0, means disable idle time out.
        "
    ::= { unisUserAttributeEntry 2 }

unisIPAddress OBJECT-TYPE
    SYNTAX      IpAddress
    MAX-ACCESS  read-write
    STATUS      current
    DESCRIPTION
        "
        Set local user's ip address.
        default is 0.0.0.0
        "
    ::= { unisUserAttributeEntry 3 }

unisNasIPAddress OBJECT-TYPE
    SYNTAX      IpAddress
    MAX-ACCESS  read-write
    STATUS      current
    DESCRIPTION
        "
        Set local user's ip address of network access server.
        default is 127.0.0.1, means local machine.
        "
    ::= { unisUserAttributeEntry 4 }

unisSlotNum OBJECT-TYPE
    SYNTAX      Integer32
    MAX-ACCESS  read-write
    STATUS      current
    DESCRIPTION
        "
        Set local user's slot.
        default is 0.
        "
    ::= { unisUserAttributeEntry 5 }

unisSubSlotNum OBJECT-TYPE
    SYNTAX      Integer32
    MAX-ACCESS  read-write
    STATUS      current
    DESCRIPTION
        "
        Set local user's sub-slot.
        default is 0.
        "
    ::= { unisUserAttributeEntry 6 }

unisPortNum OBJECT-TYPE
    SYNTAX      Integer32
    MAX-ACCESS  read-write
    STATUS      current
    DESCRIPTION
        "
        Set local user's port number.
        0 is an insignificant value for initial status.
        "
    ::= { unisUserAttributeEntry 7 }

unisMacAddress OBJECT-TYPE
    SYNTAX      MacAddress
    MAX-ACCESS  read-write
    STATUS      current
    DESCRIPTION
        "
        Set local user's mac address.
        default is 0-0-0, means the local user do not bind any mac address.
        "
    ::= { unisUserAttributeEntry 8 }

unisVlan OBJECT-TYPE
    SYNTAX      Integer32(0..4094)
    MAX-ACCESS  read-write
    STATUS      current
    DESCRIPTION
        "
        Set local user's vlan id.
        the value range is from 0 to 4094.
        default is 0, means the local user is not in any vlan.
        "
    ::= { unisUserAttributeEntry 9 }

unisFtpService OBJECT-TYPE
    SYNTAX      ServiceType
    MAX-ACCESS  read-write
    STATUS      current
    DESCRIPTION
        "
        FTP service:
        enable
        Setting this object to the value enable has the
        effect of enabling the FTP service for the corresponding entry in the
        unisUserAttributeTable.

        disable
        Setting this object to the value disable has the
        effect of disabling the FTP service for the corresponding entry in the
        unisUserAttributeTable.

        The default value is disable.
        "
    ::= { unisUserAttributeEntry 10 }

unisFtpDirectory OBJECT-TYPE
    SYNTAX      OCTET STRING
    MAX-ACCESS  read-write
    STATUS      current
    DESCRIPTION
        "
        Directory of FTP user.
        default is null, means if local user has the privilege of ftp service.
        "
    ::= { unisUserAttributeEntry 11 }

unisLanAccessService OBJECT-TYPE
    SYNTAX      ServiceType
    MAX-ACCESS  read-write
    STATUS      current
    DESCRIPTION
        "
        Lan Access service:
        enable
        Setting this object to the value enable has the
        effect of enabling the lan access service for the corresponding entry
        in the unisUserAttributeTable.

        disable
        Setting this object to the value disable has the
        effect of disabling the lan access service for the corresponding entry
        in the unisUserAttributeTable.

        The default value is disable.
        "
    ::= { unisUserAttributeEntry 12 }

unisSshService OBJECT-TYPE
    SYNTAX      ServiceType
    MAX-ACCESS  read-write
    STATUS      current
    DESCRIPTION
        "
        SSH service:
        enable
        Setting this object to the value enable has the
        effect of enabling the SSH service for the corresponding entry in the
        unisUserAttributeTable.

        disable
        Setting this object to the value disable has the
        effect of disabling the SSH service for the corresponding entry in the
        unisUserAttributeTable.

        The default value is disable.
        "
    ::= { unisUserAttributeEntry 13 }

unisTelnetService OBJECT-TYPE
    SYNTAX      ServiceType
    MAX-ACCESS  read-write
    STATUS      current
    DESCRIPTION
        "
        Telnet service:
        enable
        Setting this object to the value enable has the
        effect of enabling the TELNET service for the corresponding entry in the
        unisUserAttributeTable.

        disable
        Setting this object to the value disable has the
        effect of disabling the TELNET service for the corresponding entry in the
        unisUserAttributeTable.

        The default value is disable.
        "
    ::= { unisUserAttributeEntry 14 }

unisTerminalService OBJECT-TYPE
    SYNTAX      ServiceType
    MAX-ACCESS  read-write
    STATUS      current
    DESCRIPTION
        "
        Terminal service:
        enable
        Setting this object to the value enable has the
        effect of enabling the terminal service for the corresponding entry
        in the unisUserAttributeTable.

        disable
        Setting this object to the value disable has the
        effect of disabling the terminal service for the corresponding entry
        in the unisUserAttributeTable.

        The default value is disable.
        "
    ::= { unisUserAttributeEntry 15 }

unisExpirationDate OBJECT-TYPE
    SYNTAX      DateAndTime(SIZE(8))
    MAX-ACCESS  read-write
    STATUS      current
    DESCRIPTION
        "
        Expired date of user.
        The default value is 0-0-0,0:0:0.0, and means it doesn't expire for
        ever.
        "
    ::= { unisUserAttributeEntry 16 }

unisUserGroup      OBJECT-TYPE
    SYNTAX      DisplayString(SIZE(0..255))
    MAX-ACCESS  read-write
    STATUS      current
    DESCRIPTION
        "
        The user group that user belongs to.
        Any user must belong to a user group.
        The default group is the 'system' group.
        "
    ::= { unisUserAttributeEntry 17 }

unisPortalService OBJECT-TYPE
    SYNTAX      ServiceType
    MAX-ACCESS  read-write
    STATUS      current
    DESCRIPTION
        "
        Portal service:
        enable
        Setting this object to the value enable has the
        effect of enabling the portal service for the corresponding entry
        in the unisUserAttributeTable.

        disable
        Setting this object to the value disable has the
        effect of disabling the portal service for the corresponding entry
        in the unisUserAttributeTable.

        The default value is disable.
        "
    ::= { unisUserAttributeEntry 18 }

unisPPPService OBJECT-TYPE
    SYNTAX      ServiceType
    MAX-ACCESS  read-write
    STATUS      current
    DESCRIPTION
        "
        PPP service:
        enable
        Setting this object to the value enable has the
        effect of enabling the PPP service for the corresponding entry
        in the unisUserAttributeTable.

        disable
        Setting this object to the value disable has the
        effect of disabling the PPP service for the corresponding entry
        in the unisUserAttributeTable.

        The default value is disable.
        "
    ::= { unisUserAttributeEntry 19 }

unisHttpService OBJECT-TYPE
    SYNTAX      ServiceType
    MAX-ACCESS  read-write
    STATUS      current
    DESCRIPTION
        "
        Http service:
        enable
        Setting this object to the value enable has the
        effect of enabling the Web service for the corresponding entry
        in the unisUserAttributeTable.

        disable
        Setting this object to the value disable has the
        effect of disabling the Web service for the corresponding entry
        in the unisUserAttributeTable.

        The default value is disable.
        "
    ::= { unisUserAttributeEntry 20 }

unisHttpsService OBJECT-TYPE
    SYNTAX      ServiceType
    MAX-ACCESS  read-write
    STATUS      current
    DESCRIPTION
        "
        Https service:
        enable
        Setting this object to the value enable has the
        effect of enabling the Web service for the corresponding entry
        in the unisUserAttributeTable.

        disable
        Setting this object to the value disable has the
        effect of disabling the Web service for the corresponding entry
        in the unisUserAttributeTable.

        The default value is disable.
        "
    ::= { unisUserAttributeEntry 21 }

unisUserIfIndex OBJECT-TYPE
    SYNTAX      Integer32
    MAX-ACCESS  read-write
    STATUS      current
    DESCRIPTION
        "
        Set local user's interface index.  A value of 0 means that the interface
        index has not been assigned or the interface assigned not exist.
        The default value is 0.
        "
    ::= { unisUserAttributeEntry 22 }

-- unisUserMaxNum================================================================
unisUserMaxNum OBJECT-TYPE
    SYNTAX      Integer32
    MAX-ACCESS  read-only
    STATUS      current
    DESCRIPTION
        "
        This object contains the maximum number of local users.
        "
    ::= { unisUserObjects 3 }

-- unisUserCurrNum===============================================================
unisUserCurrNum OBJECT-TYPE
    SYNTAX      Integer32
    MAX-ACCESS  read-only
    STATUS      current
    DESCRIPTION
        "
        This object contains the current number of local users.
        "
    ::= { unisUserObjects 4 }

-- unisUserIndexIndicator========================================================
unisUserIndexIndicator OBJECT-TYPE
    SYNTAX      Integer32
    MAX-ACCESS  read-only
    STATUS      current
    DESCRIPTION
        "
        This object contains an appropriate value to
        be used for unisUserIndex when creating entries in the
        unisUserInfoTable.  The value 0 indicates that no unassigned
        entries are available.  To obtain the
        unisUserIndex value for a new
        entry, the manager issues a management
        protocol retrieval operation to obtain the
        current value of this object.  After each
        retrieval, the agent should modify the value
        to the next unassigned index.
        After a manager retrieves a value the agent will
        determine through its local policy when this index
        value will be made available for reuse.
        "
    ::= { unisUserObjects 5 }


-- unisUserRoleTable========================================================
unisUserRoleTable OBJECT-TYPE
    SYNTAX      SEQUENCE OF UnisUserRoleEntry
    MAX-ACCESS  not-accessible
    STATUS      current
    DESCRIPTION
        "
        Local User Role Table.
        If there is data in unisUserInfoTable, this table should has the
        relevant data.
        "
    ::= { unisUserObjects 6 }

unisUserRoleEntry OBJECT-TYPE
    SYNTAX      UnisUserRoleEntry
    MAX-ACCESS  not-accessible
    STATUS      current
    DESCRIPTION
        "The entry of unisUserRoleTable."
    INDEX
        {
            unisUserIndex,
            unisUserRole
        }
    ::= { unisUserRoleTable 1 }

UnisUserRoleEntry ::= SEQUENCE
    {
        unisUserRole           DisplayString,
        unisUserRoleStatus     RowStatus
    }

unisUserRole      OBJECT-TYPE
    SYNTAX      DisplayString(SIZE(1..63))
    MAX-ACCESS  not-accessible
    STATUS      current
    DESCRIPTION
        "
        The user's role determines the user's privilege.
        The user must be authorized one role at least.
        The default user role for a local user created by a network-admin user
        is network-operator, and the default user role for a local user created
        by an mdc-admin or level-15 user is mdc-operator.
        "
    ::= { unisUserRoleEntry 1 }

unisUserRoleStatus   OBJECT-TYPE
    SYNTAX   RowStatus
    MAX-ACCESS  read-create
    STATUS   current
    DESCRIPTION
        "
        This object is responsible for managing the creation, deletion and
        modification of rows, which support active status and CreateAndGo,
        Destroy operation.  To create a new row, unisUserIndex must be specified.
        The number of rows with same unisUserIndex cann't be more than 64.
        If the the number of rows with a unisUserIndex is 1, this row cann't be
        destroyed.
        "
    ::= { unisUserRoleEntry 2 }


-- unisUserGroupObjects==========================================================
unisUserGroupObjects OBJECT IDENTIFIER ::= { unisUser 2 }


-- unisUserGroupInfoTable========================================================
unisUserGroupInfoTable OBJECT-TYPE
    SYNTAX      SEQUENCE OF UnisUserGroupInfoEntry
    MAX-ACCESS  not-accessible
    STATUS      current
    DESCRIPTION
        "
        User group information table.
        "
    ::= { unisUserGroupObjects 1 }

unisUserGroupInfoEntry OBJECT-TYPE
    SYNTAX      UnisUserGroupInfoEntry
    MAX-ACCESS  not-accessible
    STATUS      current
    DESCRIPTION
        "
        The entry of unisUserGroupInfoTable.
        "
    INDEX
        {
            unisUserGroupName
        }
    ::= { unisUserGroupInfoTable 1 }

UnisUserGroupInfoEntry ::= SEQUENCE
    {
        unisUserGroupName             DisplayString,
        unisUserGroupInfoRowStatus    RowStatus
    }

unisUserGroupName OBJECT-TYPE
    SYNTAX      DisplayString(SIZE(1..255))
    MAX-ACCESS  not-accessible
    STATUS      current
    DESCRIPTION
        "
        The index of user group.
        "
    ::= { unisUserGroupInfoEntry 1 }

unisUserGroupInfoRowStatus OBJECT-TYPE
    SYNTAX      RowStatus
    MAX-ACCESS  read-create
    STATUS      current
    DESCRIPTION
        "
        The status of this conceptual row.  Only support createAndGo, destroy
        and active.
        "
    ::= { unisUserGroupInfoEntry 2 }

END
