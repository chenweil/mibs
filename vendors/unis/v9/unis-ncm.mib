-- =================================================================
-- Copyright (c) 2021 Unisyue Technologies Co., Ltd.  All rights reserved.
--
-- Description: ncm mib
-- Reference:
-- Version: V1.1
-- History:
--  V1.0 Created by lisheng
--      Initial version 2021-02-02
--  V1.1 2021-07-07 Modified by zhangfeng
--      add unisNcmTrapFeatureName to unisNcmNotificationVarBindings.
--      add unisNcmCUConfigFailed  to unisNcmCUConnTrapPrefix.
-- =================================================================
UNIS-NCM-MIB DEFINITIONS ::= BEGIN

IMPORTS
    MODULE-IDENTITY, OBJECT-TYPE, NOTIFICATION-TYPE,
    Integer32
        FROM SNMPv2-SMI
    DisplayString
        FROM SNMPv2-TC
    InetAddressType, InetAddress
        FROM INET-ADDRESS-MIB
    unisCommon
        FROM UNIS-OID-MIB;

unisNcm MODULE-IDENTITY
    LAST-UPDATED "202107070000Z"
    ORGANIZATION
        "Unisyue Technologies Co., Ltd."
    CONTACT-INFO
        ""
    DESCRIPTION
        "The MIB module is used for Netconf Client Management."
    REVISION    "202107070000Z"
    DESCRIPTION
        "add unisNcmTrapFeatureName to unisNcmNotificationVarBindings.
         add unisNcmCUConfigFailed  to unisNcmCUConnTrapPrefix."
    REVISION    "202102020000Z"
    DESCRIPTION    "The initial version."
    ::= { unisCommon 201 }

unisNcmTable OBJECT IDENTIFIER ::= { unisNcm 1 }

unisNcmConnectionTable OBJECT-TYPE
    SYNTAX        SEQUENCE OF UnisNcmConnectionEntry
    MAX-ACCESS    not-accessible
    STATUS        current
    DESCRIPTION
        "This table contains NCM session information."
    ::= { unisNcmTable 1 }

unisNcmConnectionEntry OBJECT-TYPE
    SYNTAX      UnisNcmConnectionEntry
    MAX-ACCESS  not-accessible
    STATUS      current
    DESCRIPTION
        "An entry of the unisNcmConnectionTable."
    INDEX    {
                 unisNcmUpId,
                 unisNcmSessionId
             }
    ::= { unisNcmConnectionTable 1 }

UnisNcmConnectionEntry ::= SEQUENCE
    {
        unisNcmUpId                   Integer32,
        unisNcmSessionId              Integer32,
        unisNcmConnName               DisplayString,
        unisNcmConnUserName           DisplayString,
        unisNcmConnSrcIpAddressType   InetAddressType,
        unisNcmConnSrcIpAddress       InetAddress,
        unisNcmConnDestIpAddressType  InetAddressType,
        unisNcmConnDestIpAddress      InetAddress,
        unisNcmConnVrf                DisplayString,
        unisNcmConnPort               Integer32,
        unisNcmSessionState           INTEGER
    }

unisNcmUpId   OBJECT-TYPE
    SYNTAX      Integer32(1..2147483647)
    MAX-ACCESS  not-accessible
    STATUS      current
    DESCRIPTION
        "The first index of unisNcmConnectionTable, UP
        id of Connection."
    ::= { unisNcmConnectionEntry 1 }

unisNcmSessionId   OBJECT-TYPE
    SYNTAX      Integer32(1..32)
    MAX-ACCESS  not-accessible
    STATUS       current
    DESCRIPTION
        "The second index of unisNcmConnectionTable, Connect
        session id of unisNcmConnectionTable."
    ::= { unisNcmConnectionEntry 2 }

unisNcmConnName   OBJECT-TYPE
    SYNTAX      DisplayString (SIZE(1..63))
    MAX-ACCESS  read-only
    STATUS       current
    DESCRIPTION
        "Connection name of unisNcmConnectionTable."
    ::= { unisNcmConnectionEntry 3 }

unisNcmConnUserName   OBJECT-TYPE
    SYNTAX      DisplayString (SIZE(1..80))
    MAX-ACCESS  read-only
    STATUS       current
    DESCRIPTION
        "Connection user name of unisNcmConnectionTable."
    ::= { unisNcmConnectionEntry 4 }

unisNcmConnSrcIpAddressType    OBJECT-TYPE
    SYNTAX      InetAddressType
    MAX-ACCESS  read-only
    STATUS       current
    DESCRIPTION
        "Connection ip address of unisNcmConnectionTable."
    ::= { unisNcmConnectionEntry 5 }

unisNcmConnSrcIpAddress    OBJECT-TYPE
    SYNTAX      InetAddress
    MAX-ACCESS  read-only
    STATUS       current
    DESCRIPTION
        "Connection ip address of unisNcmConnectionTable."
    ::= { unisNcmConnectionEntry 6 }

unisNcmConnDestIpAddressType    OBJECT-TYPE
    SYNTAX      InetAddressType
    MAX-ACCESS  read-only
    STATUS       current
    DESCRIPTION
        "Connection ip address of unisNcmConnectionTable."
    ::= { unisNcmConnectionEntry 7 }

unisNcmConnDestIpAddress    OBJECT-TYPE
    SYNTAX      InetAddress
    MAX-ACCESS  read-only
    STATUS       current
    DESCRIPTION
        "Connection ip address of unisNcmConnectionTable."
    ::= { unisNcmConnectionEntry 8 }

unisNcmConnVrf      OBJECT-TYPE
    SYNTAX      DisplayString (SIZE(1..31))
    MAX-ACCESS  read-only
    STATUS       current
    DESCRIPTION
        "Connection vrf of unisNcmConnectionTable."
    ::= { unisNcmConnectionEntry 9 }

unisNcmConnPort      OBJECT-TYPE
    SYNTAX      Integer32 (1..65535)
    MAX-ACCESS  read-only
    STATUS       current
    DESCRIPTION
        "Connect port of unisNcmConnectionTable."
    ::= { unisNcmConnectionEntry 10 }

unisNcmSessionState   OBJECT-TYPE
    SYNTAX              INTEGER
    {
        initialed              (1),
        connected              (2)
    }
    MAX-ACCESS   read-only
    STATUS       current
    DESCRIPTION
        "Connect session state of unisNcmConnectionTable."
    ::= { unisNcmConnectionEntry 11 }

-- ==================================================================
--
-- NCM trap object
--
-- ==================================================================
unisNcmObjects OBJECT IDENTIFIER ::= { unisNcm 2 }

unisNcmNotificationVarBindings OBJECT IDENTIFIER
    ::= { unisNcmObjects 1 }

unisNcmTrapUpId OBJECT-TYPE
    SYNTAX       Integer32(1..2147483647)
    MAX-ACCESS   accessible-for-notify
    STATUS   current
    DESCRIPTION
    "UP id of Connection."
    ::= { unisNcmNotificationVarBindings 1 }

unisNcmTrapConnIpAndPort OBJECT-TYPE
    SYNTAX       DisplayString (SIZE(1..31))
    MAX-ACCESS   accessible-for-notify
    STATUS   current
    DESCRIPTION
    "The IP and Port.  For example 127.0.0.1:830."
    ::= { unisNcmNotificationVarBindings 2 }

unisNcmTrapConnUserName OBJECT-TYPE
    SYNTAX       DisplayString (SIZE(1..80))
    MAX-ACCESS   accessible-for-notify
    STATUS   current
    DESCRIPTION
    "The connection user name."
    ::= { unisNcmNotificationVarBindings 3 }

unisNcmTrapConnFailedReason OBJECT-TYPE
    SYNTAX       DisplayString (SIZE(1..63))
    MAX-ACCESS   accessible-for-notify
    STATUS   current
    DESCRIPTION
    "The Connection Fail Reason."
    ::= { unisNcmNotificationVarBindings 4 }

unisNcmTrapFeatureName OBJECT-TYPE
    SYNTAX       DisplayString (SIZE(1..63))
    MAX-ACCESS   accessible-for-notify
    STATUS   current
    DESCRIPTION
    "The name of module that sent the configuration request."
    ::= { unisNcmNotificationVarBindings 5 }

unisNcmTrap OBJECT IDENTIFIER ::= { unisNcm 3 }
unisNcmCUConnTrapPrefix OBJECT IDENTIFIER ::= { unisNcmTrap 0 }

unisNcmCUConnDisconnected NOTIFICATION-TYPE
    OBJECTS { unisNcmTrapUpId, unisNcmTrapConnIpAndPort, unisNcmTrapConnUserName, unisNcmTrapConnFailedReason }
    STATUS  current
    DESCRIPTION
        "The NETCONF connection with a peer device was torn down."
::= { unisNcmCUConnTrapPrefix 1 }

unisNcmCUConnReconnected NOTIFICATION-TYPE
    OBJECTS { unisNcmTrapUpId, unisNcmTrapConnIpAndPort, unisNcmTrapConnUserName }
    STATUS  current
    DESCRIPTION
        "The NETCONF connection with a peer device is resumed."
::= { unisNcmCUConnTrapPrefix 2 }

unisNcmCUConnectFailed NOTIFICATION-TYPE
    OBJECTS { unisNcmTrapUpId, unisNcmTrapConnIpAndPort, unisNcmTrapConnUserName, unisNcmTrapConnFailedReason }
    STATUS  current
    DESCRIPTION
        "Failed to establish a NETCONF connection with a peer device."
::= { unisNcmCUConnTrapPrefix 3}

unisNcmCUConnectSuccess NOTIFICATION-TYPE
    OBJECTS { unisNcmTrapUpId, unisNcmTrapConnIpAndPort, unisNcmTrapConnUserName }
    STATUS  current
    DESCRIPTION
        "Successed in establishing a NETCONF connection with a peer device."
::= { unisNcmCUConnTrapPrefix 4 }

unisNcmCUConfigFailed NOTIFICATION-TYPE
    OBJECTS { unisNcmTrapUpId, unisNcmTrapConnIpAndPort, unisNcmTrapConnUserName, unisNcmTrapFeatureName }
    STATUS  current
    DESCRIPTION
        "Failed to deliver configurations to a peer device."
::= { unisNcmCUConnTrapPrefix 5 }

END
