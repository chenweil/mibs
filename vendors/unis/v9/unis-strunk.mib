-- =====================================================================
-- Copyright (c) 2021 Unisyue Technologies Co., Ltd.  All rights reserved.
--
-- Description: STRUNK MIB
-- Reference:
-- Version: V1.0
-- History:
--   V1.0 Initial version, created by wangmeng
-- =====================================================================
UNIS-STRUNK-MIB DEFINITIONS ::= BEGIN

IMPORTS
    unisCommon
        FROM UNIS-OID-MIB
    Integer32, OBJECT-TYPE,NOTIFICATION-TYPE,MODULE-IDENTITY
        FROM SNMPv2-SMI;

unisStrunk MODULE-IDENTITY
    LAST-UPDATED "202107191126Z"    -- July 19, 2021 at 11:26 GMT
    ORGANIZATION
        "Unisyue Technologies Co., Ltd."
    CONTACT-INFO
        ""
    DESCRIPTION
        "
        Smart Trunk (S-Trunk) is used on two PEs that provide dual-homed
        access for a CE for link and node redundancy. It virtualizes two
        PEs into one system through a multichassis link aggregation
        called smart trunk.
        "

    REVISION "202107191126Z"
    DESCRIPTION
        "The initial revision of this MIB module."
    ::= { unisCommon 208 }


-- trap --
unisStrunkTrap      OBJECT IDENTIFIER ::= { unisStrunk 1 }


-- All trap definitions should be placed under this object.
unisStrunkTrapPrex OBJECT IDENTIFIER ::= { unisStrunkTrap 0 }

unisStrunkMemberStatusChange NOTIFICATION-TYPE
    OBJECTS
        {   unisStrunkMemberType,
            unisStrunkMemberId,
            unisStrunkMemberStatus,
            unisStrunkMemberReason
        }
    STATUS       current
    DESCRIPTION
        "This trap indicates that S-Trunk member role changed."
    ::= { unisStrunkTrapPrex 1 }

unisStrunkStatusChange NOTIFICATION-TYPE
    OBJECTS {   unisStrunkGroupId,
                unisStrunkGroupStatus,
                unisStrunkGroupReason
            }
    STATUS       current
    DESCRIPTION
        "This trap indicates that S-Trunk Group role changed."
    ::= { unisStrunkTrapPrex 2 }

-- All objects used for TRAP only are defined here.
unisStrunkTrapOjbects OBJECT IDENTIFIER ::= { unisStrunkTrap 1 }

unisStrunkMemberType OBJECT-TYPE
    SYNTAX  INTEGER {
         bagg(1),
         ragg(2)
     }
    MAX-ACCESS   accessible-for-notify
    STATUS       current
    DESCRIPTION
        "The member type of the S-Trunk.
        bagg: The bridge aggregation type.
        ragg: The route aggregation type."
    ::= { unisStrunkTrapOjbects 1 }

unisStrunkMemberId OBJECT-TYPE
    SYNTAX       Integer32
    MAX-ACCESS   accessible-for-notify
    STATUS       current
    DESCRIPTION
        "The member id of the S-Trunk."
    ::= { unisStrunkTrapOjbects 2 }

unisStrunkMemberStatus OBJECT-TYPE
    SYNTAX  INTEGER {
         primary(1),
         secondary(2)
     }
    MAX-ACCESS   accessible-for-notify
    STATUS       current
    DESCRIPTION
        "The status of the S-Trunk.
        primary: The S-Trunk member is primary role.
        secondary: The S-Trunk member is secondary role."
    ::= { unisStrunkTrapOjbects 3 }

unisStrunkMemberReason OBJECT-TYPE
    SYNTAX OCTET STRING (SIZE (0..255))
    MAX-ACCESS   accessible-for-notify
    STATUS       current
    DESCRIPTION
        " The S-Trunk member change reason."
    ::= { unisStrunkTrapOjbects 4 }

unisStrunkGroupId OBJECT-TYPE
    SYNTAX Integer32
    MAX-ACCESS   accessible-for-notify
    STATUS       current
    DESCRIPTION
        " The group id of the S-Trunk."
    ::= { unisStrunkTrapOjbects 5 }

unisStrunkGroupStatus OBJECT-TYPE
    SYNTAX  INTEGER {
            init(1),
            primary(2),
            secondary(3)
        }
    MAX-ACCESS   accessible-for-notify
    STATUS       current
    DESCRIPTION
        "The group status of the S-Trunk.
        init: The S-Trunk group is primary role.
        primary: The S-Trunk group is primary role.
        secondary: The S-Trunk group is secondary role."
    ::= { unisStrunkTrapOjbects 6 }

unisStrunkGroupReason OBJECT-TYPE
    SYNTAX OCTET STRING (SIZE (0..255))
    MAX-ACCESS   accessible-for-notify
    STATUS       current
    DESCRIPTION
        " The S-Trunk group change reason."
    ::= { unisStrunkTrapOjbects 7 }
END
