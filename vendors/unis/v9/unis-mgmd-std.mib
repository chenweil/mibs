-- ============================================================================
-- Copyright (c) 2022 Unisyue Technologies Co., Ltd.  All rights reserved.
--
-- Description: Multicast Group Membership Discovery (MGMD) Management
--              Information Base (MIB).
-- Reference:
-- Version: V1.0
-- History:
-- V1.0 2022-03-28 Created by QIU YINGZHE
-- ============================================================================
--
-- Variables and types be imported
--
-- ============================================================================

UNIS-MGMD-STD-MIB DEFINITIONS ::= BEGIN


IMPORTS

    MODULE-IDENTITY,OBJECT-TYPE,NOTIFICATION-TYPE,
    Unsigned32
        FROM SNMPv2-SMI

    DisplayString
        FROM SNMPv2-TC

    unisCommon
        FROM UNIS-OID-MIB

    InetAddressType,InetAddress
        FROM INET-ADDRESS-MIB

    InterfaceIndex
        FROM IF-MIB;

unisMgmdStd MODULE-IDENTITY
    LAST-UPDATED "202203281100Z"
    ORGANIZATION
        "Unisyue Technologies Co., Ltd."
    CONTACT-INFO
        ""
    DESCRIPTION
        "The Management MIB for Internet Group Management Protocol
        (IGMP) and Multicast Listener Discover (MLD)"

    -- Revision history.
    REVISION "202203281100Z"
    DESCRIPTION
        "The initial version of this MIB file."
    ::= { unisCommon 223 }


unisMgmdStdNotifications   OBJECT IDENTIFIER ::= { unisMgmdStd 0 }
unisMgmdStdTrapBindObjects OBJECT IDENTIFIER ::= { unisMgmdStd 1 }
unisMgmdStdObjects      OBJECT IDENTIFIER ::= { unisMgmdStd 2 }


unisMgmdStdInterfaceName OBJECT-TYPE
    SYNTAX     DisplayString (SIZE(1..64))
    MAX-ACCESS accessible-for-notify
    STATUS     current
    DESCRIPTION
            "The interface name of the interface for which IGMP or MLD
            is enabled."
    ::= { unisMgmdStdTrapBindObjects 1 }

unisMgmdStdInterfaceIfIndex OBJECT-TYPE
    SYNTAX     InterfaceIndex
    MAX-ACCESS accessible-for-notify
    STATUS     current
    DESCRIPTION
            "The ifIndex value of the interface for which IGMP or MLD
            is enabled.  The table is indexed by the ifIndex value and
            the InetAddressType to allow for interfaces which may be
            configured in both IPv4 and IPv6 modes."
    ::= { unisMgmdStdTrapBindObjects 2 }

unisMgmdStdGmpJoinVersion OBJECT-TYPE
    SYNTAX     Unsigned32(1..3)
    MAX-ACCESS accessible-for-notify
    STATUS     current
    DESCRIPTION
            "The version of MGMD which is running on this interface.
            Value 1 applies to IGMPv1 and MLDv1 version.  Value 2 applies
            to IGMPv2 and MLDv2 version, and value 3 applies to IGMPv3
            version.
            This object can be used to configure a router capable of
            running either version.  For IGMP and MLD to function
            correctly, all routers on a Local Area Network (LAN)
            must be configured to run the same version on that LAN.
            This object MAY be modified under any rowstatus condition."
    DEFVAL     { 2 }
    ::= { unisMgmdStdTrapBindObjects 3 }

unisMgmdStdAddressType OBJECT-TYPE
    SYNTAX     InetAddressType
    MAX-ACCESS accessible-for-notify
    STATUS     current
    DESCRIPTION
            "The address type of this IGMP or MLD message."
    ::= { unisMgmdStdTrapBindObjects 4}

unisMgmdStdGmpJoinSrcAddr OBJECT-TYPE
    SYNTAX     InetAddress
    MAX-ACCESS accessible-for-notify
    STATUS     current
    DESCRIPTION
           "The IGMP or MLD source address to join."
    ::= { unisMgmdStdTrapBindObjects 5 }

unisMgmdStdGmpJoinGrpAddr OBJECT-TYPE
    SYNTAX     InetAddress
    MAX-ACCESS accessible-for-notify
    STATUS     current
    DESCRIPTION
           "The IGMP or MLD group address to join."
    ::= { unisMgmdStdTrapBindObjects 6 }

unisMgmdStdGmpJoinSenderIp OBJECT-TYPE
    SYNTAX     InetAddress
    MAX-ACCESS accessible-for-notify
    STATUS     current
    DESCRIPTION
           "The host IP address for sending membership report."
    ::= { unisMgmdStdTrapBindObjects 7 }

unisMgmdStdInstanceName OBJECT-TYPE
    SYNTAX     DisplayString (SIZE (0..255))
    MAX-ACCESS accessible-for-notify
    STATUS     current
    DESCRIPTION
            "The Name of the Protocol Independent Multicast (PIM) instance."
    ::= { unisMgmdStdTrapBindObjects 8 }

unisMgmdStdGmpJoin NOTIFICATION-TYPE
    OBJECTS { unisMgmdStdInterfaceName,
              unisMgmdStdInterfaceIfIndex,
              unisMgmdStdGmpJoinVersion,
              unisMgmdStdAddressType,
              unisMgmdStdGmpJoinSrcAddr,
              unisMgmdStdGmpJoinGrpAddr,
              unisMgmdStdGmpJoinSenderIp,
              unisMgmdStdInstanceName
            }
    STATUS     current
    DESCRIPTION
            "An unisMgmdStdGmpJoin notification signifies the IGMP or MLD
            join message was received."
    ::= { unisMgmdStdNotifications 1 }

unisMgmdStdGmpLeave NOTIFICATION-TYPE
    OBJECTS { unisMgmdStdInterfaceName,
              unisMgmdStdInterfaceIfIndex,
              unisMgmdStdAddressType,
              unisMgmdStdGmpJoinSrcAddr,
              unisMgmdStdGmpJoinGrpAddr,
              unisMgmdStdGmpJoinSenderIp,
              unisMgmdStdInstanceName
            }
    STATUS     current
    DESCRIPTION
            "An unisMgmdStdGmpLeave notification signifies the IGMP or MLD
            group leaved."
    ::= { unisMgmdStdNotifications 2 }

unisMgmdStdGmpJoinNotifPeriod OBJECT-TYPE
    SYNTAX     Unsigned32 (0..65535)
    UNITS      "seconds"
    MAX-ACCESS read-write
    STATUS     current
    DESCRIPTION
            "The minimum time that must elapse between unisMgmdStdGmpJoin
            notifications originated by this router.  The maximum value
            65535 represents an 'infinite' time, in which case, no
            GmpJoin notifications are ever sent."
    DEFVAL { 65535 }
    ::= { unisMgmdStdObjects 1 }

unisMgmdStdGmpLeaveNotifPeriod OBJECT-TYPE
    SYNTAX     Unsigned32 (0..65535)
    UNITS      "seconds"
    MAX-ACCESS read-write
    STATUS     current
    DESCRIPTION
            "The minimum time that must elapse between unisMgmdStdGmpLeave
            notifications originated by this router.  The maximum value
            65535 represents an 'infinite' time, in which case, no
            GmpLeave notifications are ever sent."
    DEFVAL { 65535 }
    ::= { unisMgmdStdObjects 2 }

END
