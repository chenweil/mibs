-- ===================================================================
-- Copyright (c) 2022 Unisyue Technologies Co., Ltd.  All rights reserved.
--
-- Description: V1.0
-- History:
--   V1.0 Created by zhangjitong
--        Initial version 2022-01-25
-- ====================================================================
UNIS-KPI-MIB DEFINITIONS ::= BEGIN

IMPORTS
        unisCommon
    FROM UNIS-OID-MIB
        Integer32, OBJECT-TYPE, NOTIFICATION-TYPE, MODULE-IDENTITY
    FROM SNMPv2-SMI;

unisKPI MODULE-IDENTITY
    LAST-UPDATED "202204081635Z"
    ORGANIZATION
        "Unisyue Technologies Co., Ltd."
    CONTACT-INFO
        ""
    DESCRIPTION
        "The MIB module is used for managing KPI."
    REVISION "202204081635Z"
    DESCRIPTION
        "Modify the SYNTAX of unisKPIDataTimeStamp from TimeStamp to OCTET STRING."
    REVISION "202201251502Z"
    DESCRIPTION
        "The initial revision of this KPI module."
    ::= { unisCommon 221 }

unisKPINotification OBJECT IDENTIFIER ::= {unisKPI 1}

unisKPINotificationPrefix OBJECT IDENTIFIER ::= { unisKPINotification 0 }

-- All Notifications definitions should be placed under this object
unisKPIDataOverThreshold NOTIFICATION-TYPE
    OBJECTS
    {
        unisKPIDataChassis,
        unisKPIDataSlot,
        unisKPIDataCPUID,
        unisKPIDataModuleName,
        unisKPIDataTimeStamp,
        unisKPIDataObjectName,
        unisKPIDataIndicatorName,
        unisKPIDataIndicatorValue,
        unisKPIDataThreshold
    }
    STATUS       current
    DESCRIPTION
        "This notification is generated when the KPI value exceeds the threshold."
    ::= { unisKPINotificationPrefix 1 }

unisKPIDataRecover NOTIFICATION-TYPE
    OBJECTS
    {
        unisKPIDataChassis,
        unisKPIDataSlot,
        unisKPIDataCPUID,
        unisKPIDataModuleName,
        unisKPIDataTimeStamp,
        unisKPIDataObjectName,
        unisKPIDataIndicatorName,
        unisKPIDataIndicatorValue,
        unisKPIDataThreshold
    }
    STATUS       current
    DESCRIPTION
        "This notification is generated when the KPI value returns within the threshold range."
    ::= { unisKPINotificationPrefix 2 }

unisKPIPredictDataOverThreshold NOTIFICATION-TYPE
    OBJECTS
    {
        unisKPIDataChassis,
        unisKPIDataSlot,
        unisKPIDataCPUID,
        unisKPIDataModuleName,
        unisKPIDataTimeStamp,
        unisKPIDataObjectName,
        unisKPIDataIndicatorName,
        unisKPIDataIndicatorValue,
        unisKPIDataPredictCycle,
        unisKPIDataThreshold
    }
    STATUS       current
    DESCRIPTION
        "This notification is generated when the predicted KPI value exceeds the
        threshold after n cycles."
    ::= { unisKPINotificationPrefix 3 }

unisKPIPredictDataRecover NOTIFICATION-TYPE
    OBJECTS
    {
        unisKPIDataChassis,
        unisKPIDataSlot,
        unisKPIDataCPUID,
        unisKPIDataModuleName,
        unisKPIDataTimeStamp,
        unisKPIDataObjectName,
        unisKPIDataIndicatorName,
        unisKPIDataIndicatorValue,
        unisKPIDataPredictCycle,
        unisKPIDataThreshold
    }
    STATUS       current
    DESCRIPTION
        "This notification is generated when the predicted KPI value returns within the threshold range."
    ::= { unisKPINotificationPrefix 4 }

unisKPINotificationDefinitions OBJECT IDENTIFIER ::= {unisKPINotification 1}
-- All objects used for Notification only are defined here

unisKPIDataChassis OBJECT-TYPE
    SYNTAX Integer32(0..65535)
    MAX-ACCESS  accessible-for-notify
    STATUS  current
    DESCRIPTION
        "Number of the chassis where the KPI data is collected."
    ::= { unisKPINotificationDefinitions 1 }

unisKPIDataSlot OBJECT-TYPE
    SYNTAX Integer32(0..65535)
    MAX-ACCESS accessible-for-notify
    STATUS current
    DESCRIPTION
        "Number of the slot where the KPI data is collected."
    ::= { unisKPINotificationDefinitions 2 }

unisKPIDataCPUID OBJECT-TYPE
    SYNTAX Integer32(0..65535)
    MAX-ACCESS accessible-for-notify
    STATUS current
    DESCRIPTION
        "Number of the CPU where the KPI data is collected."
    ::= { unisKPINotificationDefinitions 3 }

unisKPIDataModuleName OBJECT-TYPE
    SYNTAX OCTET STRING (SIZE(1..8))
    MAX-ACCESS accessible-for-notify
    STATUS current
    DESCRIPTION
        "Name of the module where the KPI data is collected."
    ::= { unisKPINotificationDefinitions 4 }

unisKPIDataTimeStamp OBJECT-TYPE
    SYNTAX OCTET STRING (SIZE(1..32))
    MAX-ACCESS accessible-for-notify
    STATUS current
    DESCRIPTION
        "Time when the KPI data is collected."
    ::= { unisKPINotificationDefinitions 5 }

unisKPIDataObjectName OBJECT-TYPE
    SYNTAX OCTET STRING (SIZE(1..64))
    MAX-ACCESS accessible-for-notify
    STATUS current
    DESCRIPTION
        "Name of the object where the KPI data is collected."
    ::= { unisKPINotificationDefinitions 6 }

unisKPIDataIndicatorName OBJECT-TYPE
    SYNTAX OCTET STRING (SIZE(1..64))
    MAX-ACCESS accessible-for-notify
    STATUS current
    DESCRIPTION
        "Name of the KPI indicator."
    ::= { unisKPINotificationDefinitions 7 }

unisKPIDataIndicatorValue OBJECT-TYPE
    SYNTAX OCTET STRING (SIZE(1..32))
    MAX-ACCESS accessible-for-notify
    STATUS current
    DESCRIPTION
        "Value of the KPI indicator."
    ::= { unisKPINotificationDefinitions 8 }

unisKPIDataPredictCycle OBJECT-TYPE
    SYNTAX Integer32(0..65535)
    MAX-ACCESS accessible-for-notify
    STATUS current
    DESCRIPTION
        "Number of cycles after which the threshold will be exceeded."
    ::= { unisKPINotificationDefinitions 9 }

unisKPIDataThreshold OBJECT-TYPE
    SYNTAX OCTET STRING (SIZE(1..32))
    MAX-ACCESS accessible-for-notify
    STATUS current
    DESCRIPTION
        "Upper/Lower threshold, that is, the maximum/minimum value of the KPI data."
    ::= { unisKPINotificationDefinitions 10 }

END
