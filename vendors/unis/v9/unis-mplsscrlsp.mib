-- =============================================================================
-- Copyright (c) 2023 Unisyue Technologies Co., Ltd.  All rights reserved.
--
-- Description: Multiprotocol Label Switching Static Crlsp MIB
-- Reference:
-- Version: V1.1
-- History:
--   V1.0 2022-06-08 Initial version Created by Zhouwan
--   V1.1 2023-03-14 Modified by Long lewen, Modified unisMplsExtNotifications
-- =============================================================================
UNIS-MPLSSCRLSP-MIB DEFINITIONS ::= BEGIN
IMPORTS
    MODULE-IDENTITY, OBJECT-TYPE, NOTIFICATION-TYPE
        FROM SNMPv2-SMI
    unisCommon
        FROM UNIS-OID-MIB
    ;

-- =============================================================================
-- module identity part
-- =============================================================================
unisMplsScrlsp    MODULE-IDENTITY
    LAST-UPDATED
        "202303141400Z"   -- Mar 14, 2023 at 14:00 GMT
    ORGANIZATION
        "Unisyue Technologies Co., Ltd."
    CONTACT-INFO
        ""
    DESCRIPTION
        "Multiprotocol Label Switching Static Crlsp MIB"
    REVISION
        "202303141400Z"   -- Mar 14, 2023 at 14:00 GMT
    DESCRIPTION
        "Modified unisMplsExtNotifications"
    REVISION
        "202206070920Z"   -- June 07, 2022 at 09:20 GMT
    DESCRIPTION
        "Initial version of this MIB."
    ::= { unisCommon 231 }

-- =============================================================================
-- Top level components of this MIB module.
-- =============================================================================
unisMplsScrlspNotifications OBJECT IDENTIFIER ::= { unisMplsScrlsp 0 }

unisMplsScrlspObjects       OBJECT IDENTIFIER ::= { unisMplsScrlsp 1 }

unisMplsScrlspScalarGroup   OBJECT IDENTIFIER ::= { unisMplsScrlspObjects 1 }

unisMplsScrlspBaseInfo    OBJECT-TYPE
    SYNTAX      OCTET STRING (SIZE (1..127))
    MAX-ACCESS  accessible-for-notify
    STATUS      current
    DESCRIPTION
        "The base information of MPLS static CRLSP."
    ::= { unisMplsScrlspScalarGroup 1 }

unisMplsScrlspExtInfo    OBJECT-TYPE
    SYNTAX      OCTET STRING (SIZE (1..127))
    MAX-ACCESS  accessible-for-notify
    STATUS      current
    DESCRIPTION
        "The external information of MPLS static CRLSP"
    ::= { unisMplsScrlspScalarGroup 2 }

-- =============================================================================
-- Notifications
-- =============================================================================
unisMplsScrlspDown  NOTIFICATION-TYPE
    OBJECTS {
            unisMplsScrlspBaseInfo,
            unisMplsScrlspExtInfo
            }
    STATUS      current
    DESCRIPTION
      "This notification is generated when the Static CRLSP changed to Down."
    ::= { unisMplsScrlspNotifications 1 }

unisMplsScrlspUp  NOTIFICATION-TYPE
    OBJECTS {
            unisMplsScrlspBaseInfo,
            unisMplsScrlspExtInfo
            }
    STATUS      current
    DESCRIPTION
      "This notification is generated when the Static CRLSP changed to Up."
    ::= { unisMplsScrlspNotifications 2 }

unisMplsScrlspLabelConflict    NOTIFICATION-TYPE
    OBJECTS {
            unisMplsScrlspBaseInfo,
            unisMplsScrlspExtInfo
            }
    STATUS      current
    DESCRIPTION
      "This notification is generated when the Segment Routing label is
      configured for another prefix segment."
    ::= { unisMplsScrlspNotifications 3 }

unisMplsScrlspLabelDup     NOTIFICATION-TYPE
    OBJECTS {
            unisMplsScrlspBaseInfo,
            unisMplsScrlspExtInfo
            }
    STATUS      current
    DESCRIPTION
      "This notification is generated when the Incoming label is duplicate."
    ::= { unisMplsScrlspNotifications 4 }

-- =============================================================================
-- End of notifications.
-- =============================================================================

END
