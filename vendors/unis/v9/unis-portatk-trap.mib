-- ============================================================================
-- Copyright (c) 2022 Unisyue Technologies Co., Ltd.  All rights reserved.
--
-- Description: The purpose of this MIB file is to provide the definition of
--              the portatk trap.
-- Reference:
-- Version: V1.0
-- History:
-- V1.0 2022-09-02
--   Initial version, created by shaojunjun
-- ============================================================================
UNIS-PORTATK-TRAP-MIB DEFINITIONS ::= BEGIN

IMPORTS
        unisCommon
    FROM UNIS-OID-MIB
        DisplayString
    FROM SNMPv2-TC
        OBJECT-TYPE, MODULE-IDENTITY, NOTIFICATION-TYPE
    FROM SNMPv2-SMI;

-- Node definitions
unisPortAtkTrap MODULE-IDENTITY
    LAST-UPDATED "202209011800Z"        -- Sep 2, 2022 at 18:00 GMT
    ORGANIZATION
        "Unisyue Technologies Co., Ltd."
    CONTACT-INFO
        ""
    DESCRIPTION
        "This MIB file defines the port attack trap warning feature only."
    REVISION "202209011800Z"
    DESCRIPTION
        "The initial version of this MIB file."
    ::= { unisCommon 250}

-- unisPortAtkTrapPacket
unisPortAtkTrapPacket OBJECT IDENTIFIER ::= { unisPortAtkTrap 0 }

unisPortAtkTrapPtkAlarm NOTIFICATION-TYPE
    OBJECTS
        {
            unisPortAtkTrapPacketIf,
            unisPortAtkTrapPacketType
        }
    STATUS      current
    DESCRIPTION
         "If the protocol packet sending rate on a port exceeded the rate limit,
          a trap message is generated and sent to the remote monitoring device."
    ::= { unisPortAtkTrapPacket 1 }

unisPortAtkTrapPtkResume NOTIFICATION-TYPE
    OBJECTS
        {
            unisPortAtkTrapPacketIf,
            unisPortAtkTrapPacketType
        }
    STATUS      current
    DESCRIPTION
        "If the protocol packet sending rate on a port dropped below the rate limit,
        a trap message is generated and sent to the remote monitoring device."
    ::= { unisPortAtkTrapPacket 2 }

unisPortAtkTrapPtkObjs OBJECT IDENTIFIER  ::= { unisPortAtkTrap 1 }

unisPortAtkTrapPacketIf OBJECT-TYPE
    SYNTAX      DisplayString(SIZE (0..255))
    MAX-ACCESS  accessible-for-notify
    STATUS      current
    DESCRIPTION
        "Interface that received the protocol packets."
    ::= { unisPortAtkTrapPtkObjs 1}

unisPortAtkTrapPacketType OBJECT-TYPE
    SYNTAX INTEGER
    {
        isis(1),
        esis(2),
        clnp(3),
        vrrp(4),
        unknownIpv4Mc(5),
        unknownIpv6Mc(6),
        ipv4McastRip(7),
        ipv4BcastRip(8),
        mcastNtp(9),
        bcastNtp(10),
        ipv4McastOspfDip5(11),
        ipv4McastOspfDip6(12),
        ipv4UcastOspf(13),
        ipv4McastPim(14),
        ipv4UcastPim(15),
        ipv4Igmp(16),
        ucastLdp(17),
        ipv6McastPim(18),
        ipv6UcastPim(19),
        ipv6Mld(20),
        ipv6Ripng(21),
        ipv6UcastOspfv3(22),
        ipv6McastOspfv3Dip5(23),
        ipv6McastOspfv3Dip6(24),
        ipv6Ldp(25),
        ipv6Vrrp(26),
        rrpp(27),
        ipv4Autorp(28),
        dot1x(29),
        stp(30),
        lacp(31),
        gvrp(32),
        hgmp(33),
        ucastBgp(34),
        ucastIcmp(35),
        ucastTtl(36),
        ucastIpOption(37),
        ipv6Bgp(38),
        ipv6NdPass(39),
        ipv6NdDest(40),
        lldp(41),
        dldp(42),
        bpduTunnelDmac3(43),
        bpduTunnelDmac0(44),
        bpduTunnelDmac1(45),
        bpduTunnelDmac2(46),
        msdp(47),
        telnetSsh(48),
        httpHttps(49),
        snmp(50),
        smlk(51),
        dot1ag(52),
        cdp(53),
        acsei(54),
        ucastNtp(55),
        md(56),
        ipv4UcDhcp(57),
        ipv4UcOspfTtl(58),
        ipv4UcPimTtl(59),
        ipv6Icmp(60),
        gmrp(61),
        pvst(62),
        oam(63),
        hgmpBc(64),
        eapolBridgemac(65),
        wpiBridgemac(66),
        cfdBridgemac(67),
        hgmpBridgemac(68),
        acseiBridgemac(69),
        ipv6DhcpUcClient(70),
        ipv6DhcpUcRelay(71),
        l2Stationmove(72),
        icmpRdm(73),
        ipv6CpudstCar(74),
        ptp(75),
        fcoeFipUc(76),
        fcoeToCpu(77),
        ipv6UcastRtrenum(78),
        ipv6McastRtrenum(79),
        ipv6UcastNtp(80),
        ipv6McastNtp(81),
        trillAllisis(82),
        drcp(83),
        rlinkHigh(84),
        rlinkMiddle(85),
        vdp(86),
        ipv4McastCbt(87),
        arp(88),
        arpReply(89),
        ipv6Ttl(90),
        ipv6Ping(91),
        snapCis(92),
        macBasevlan(93),
        trillStp(94),
        routeToCpuMask(95),
        spbm(96),
        ipv6IpOption(97),
        ipv4UcBgpTtl(98),
        dhcpClient(99),
        dhcpServer(100),
        dhcpRelayClient(101),
        dhcpRelayServer(102),
        ipv6Dhcp(103),
        ipv6DhcpClient(104),
        ipv6DhcpServer(105),
        ipv6DhcpRelayServer(106),
        bfdEcho(107),
        bfdCtrl(108),
        bfdMultihop(109),
        bfdIntfCtrl(110),
        lspPing(111),
        loopbackDetection(112),
        loopTest(113),
        ipv6TelnetSsh(114),
        mplsRsvp(115),
        rrppFd(116),
        ptpUdp(117),
        ofpMiss(118),
        ofpMatch(119),
        ofpDevconfTtl(120),
        ofpMacipMiss(121),
        ftpCtrl(122),
        vxlanUdp(123),
        capwap(124),
        rlinkextNormal(125),
        rlinkextMiddle(126),
        rlinkextHigh(127),
        ipv4Siph225(128),
        ipv4Siph245(129),
        typeErps(130),
        esmc(131),
        rlinkNormal(132),
        onvifv4(133),
        onvifv6(134),
        ipv4Sip(135),
        twamp(136),
        pppoe(137),
        ipv6RaGuard(138),
        tcpToCpuLow(139),
        ipv4BcmpServer(140),
        wlanAcToCpu(141),
        lwappAcToCpu(142),
        smartmcUc(143),
        smartmcBc(144),
        rlinkLow(145),
        drniUdp(146),
        sipSnooping(147),
        douPsg(148),
        h323Snooping(149),
        mdns(150),
        erps(151),
        sadp(152),
        dhcpProtectionClient(153),
        dhcpProtectionServer(154),
        bfdMultihopVxlan(155),
        rarp(156),
        inof(157),
        inofMobile(158),
        ipv6UcBgpTtl(159),
        ipv4McastOspf5High(160),
        ipv4McastOspf6High(161),
        ipv6Drcp(162),
        l2ptusr(163),
        rarpReply(164)
    }
    MAX-ACCESS  accessible-for-notify
    STATUS      current
    DESCRIPTION
        "Type of the protocol packets received on the port."
    ::= { unisPortAtkTrapPtkObjs 2}

END
