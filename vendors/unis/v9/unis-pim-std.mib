-- ==================================================================
-- Copyright (c) 2024 Unisyue Technologies Co., Ltd.  All rights reserved.
--
-- Description: PIM MIB
-- Reference:
-- Version: V1.1
-- History:
-- V1.0 2021-12-14 Created by Ma Xiaozhong
--      Add UnisPimMode, UnisPimGroupMappingOriginType,
--      unisPimRPMappingChange, unisPimGroupMappingOrigin,
--      unisPimGroupMappingAddressType, unisPimGroupMappingGrpAddress,
--      unisPimGroupMappingGrpPrefixLen, unisPimGroupMappingRPAddressType,
--      unisPimGroupMappingRPAddress, unisPimGroupMappingPimMode,
--      unisPimGroupMappingPrecedence, unisPimInterfaceElection,
--      unisPimInterfaceIfIndex, unisPimInterfaceAddress,
--      unisPimInterfaceIPVersion, unisPimInterfaceAddressType,
--      unisPimNeighborLoss, unisPimNeighborUpTime,
--      unisPimNeighborLossReason, unisPimNeighborIfName,
--      unisPimInterfaceName by jiayunda
-- V1.1 2023-06-19 Updated by likangping
--      Add unisPimVrfRouteThresholdExceed, unisPimVrfRouteThExceedClear，
--      unisPimVrfRouteExceed，unisPimVrfRouteExceedClear
-- ==================================================================
--
-- Variables and types be imported
--
-- ==================================================================
UNIS-PIM-STD-MIB DEFINITIONS ::= BEGIN

IMPORTS

    MODULE-IDENTITY,OBJECT-TYPE,NOTIFICATION-TYPE,Unsigned32,
    TimeTicks
        FROM SNMPv2-SMI

    TEXTUAL-CONVENTION,DisplayString
        FROM SNMPv2-TC

    unisCommon
        FROM UNIS-OID-MIB

    InetAddressType,InetAddress,InetAddressPrefixLength,InetVersion
        FROM INET-ADDRESS-MIB

    InterfaceIndex
        FROM IF-MIB;

unisPimStd MODULE-IDENTITY
    LAST-UPDATED "202306190000Z"
    ORGANIZATION
        "Unisyue Technologies Co., Ltd."
    CONTACT-INFO
        ""
    DESCRIPTION
        "PIM(Protocol Independent Multicast) Management MIB"
    -- Revision history.
    REVISION "202306190000Z"
    DESCRIPTION
       "Add unisPimVrfRouteThresholdExceed, unisPimVrfRouteThExceedClear,
        unisPimVrfRouteExceed,unisPimVrfRouteExceedClear"
    REVISION "202207211350Z"
    DESCRIPTION
       "Add UnisPimMode, UnisPimGroupMappingOriginType,
        unisPimRPMappingChange, unisPimGroupMappingOrigin,
        unisPimGroupMappingAddressType, unisPimGroupMappingGrpAddress,
        unisPimGroupMappingGrpPrefixLen, unisPimGroupMappingRPAddressType,
        unisPimGroupMappingRPAddress, unisPimGroupMappingPimMode,
        unisPimGroupMappingPrecedence, unisPimInterfaceElection,
        unisPimInterfaceIfIndex, unisPimInterfaceAddress,
        unisPimInterfaceIPVersion, unisPimInterfaceAddressType,
        unisPimNeighborLoss, unisPimNeighborUpTime,
        unisPimNeighborLossReason, unisPimNeighborIfName,
        unisPimInterfaceName"
    REVISION "202112141400Z"
    DESCRIPTION
        "The initial version of this MIB file."
    ::= { unisCommon 213 }

UnisPimMode ::= TEXTUAL-CONVENTION
    STATUS     current
    DESCRIPTION
            "The PIM mode in which a group is operating.
            none:The group is not using PIM, which may be the
                 case if, for example, it is a link-local or
                 unroutable group address.
            ssm:Source-Specific Multicast (SSM) with PIM Sparse Mode.
            asm:Any Source Multicast (ASM) with PIM Spars Mode.
            bidir:Bidirectional PIM.
            dm:PIM Dense Mode.
            other:Any other PIM mode."

    SYNTAX     INTEGER {
                  none(1),
                  ssm(2),
                  asm(3),
                  bidir(4),
                  dm(5),
                  other(6)
                }

UnisPimGroupMappingOriginType ::= TEXTUAL-CONVENTION
    STATUS     current
    DESCRIPTION
            "The mechanism by which a PIM group mapping was learned.
            fixed:Link-local or unroutable group mappings.
            configRp:Local static RP configuration.
            configSsm:Local SSM Group configuration.
            bsr:The PIM Bootstrap Router (BSR) mechanism.
            autoRP:Cisco's Auto-RP mechanism.
            embedded:The Embedded-RP mechanism where the RP address
                         is embedded in the multicast group address.
            other:Any other mechanism."
    SYNTAX     INTEGER {
                  fixed(1),
                  configRp(2),
                  configSsm(3),
                  bsr(4),
                  autoRP(5),
                  embedded(6),
                  other(7)
               }

unisPimNotifications OBJECT IDENTIFIER ::= { unisPimStd 0 }
unisPimTrapBindObjects OBJECT IDENTIFIER ::= { unisPimStd 1 }

unisPimInstanceID OBJECT-TYPE
    SYNTAX     Unsigned32
    MAX-ACCESS accessible-for-notify
    STATUS     current
    DESCRIPTION
            "The ID of the PIM instance."
    ::= { unisPimTrapBindObjects 1 }

unisPimInstanceName OBJECT-TYPE
    SYNTAX     DisplayString (SIZE (0..255))
    MAX-ACCESS accessible-for-notify
    STATUS     current
    DESCRIPTION
            "The Name of the PIM instance."
    ::= { unisPimTrapBindObjects 2 }

unisPimNeighborExpiryTime OBJECT-TYPE
    SYNTAX     TimeTicks
    MAX-ACCESS accessible-for-notify
    STATUS     current
    DESCRIPTION
            "The minimum time remaining before this PIM neighbor will
             time out.  The value zero indicates that this PIM neighbor
             will never time out."
    ::= { unisPimTrapBindObjects 3 }

unisPimNotificationLimitType OBJECT-TYPE
    SYNTAX     INTEGER {
                         smStarGroup(1),
                         smSourceGroup(2)
    }
    MAX-ACCESS accessible-for-notify
    STATUS     current
    DESCRIPTION
            "The entry type:
             The smStarGroup indicates that the current restricted table
              item type is PIM-SM (*,G) table item
             The smSourceGroup indicates that the current restricted table
              item type is PIM-SM (S,G) table item;"
    ::= { unisPimTrapBindObjects 4 }

unisPimNotificationAddressFamily OBJECT-TYPE
    SYNTAX     InetAddressType
    MAX-ACCESS accessible-for-notify
    STATUS     current
    DESCRIPTION
            "The address family of PIM."
    ::= { unisPimTrapBindObjects 5 }

unisPimNotificationEntryCount OBJECT-TYPE
    SYNTAX     Unsigned32
    MAX-ACCESS accessible-for-notify
    STATUS     current
    DESCRIPTION
            "The current PIM entry count."
    ::= { unisPimTrapBindObjects 6 }

unisPimNotificationLimitCount OBJECT-TYPE
    SYNTAX     Unsigned32
    MAX-ACCESS accessible-for-notify
    STATUS     current
    DESCRIPTION
            "The maxmum limit of PIM entry."
    ::= { unisPimTrapBindObjects 7 }

unisPimNotificationThresholdCnt OBJECT-TYPE
    SYNTAX     Unsigned32
    MAX-ACCESS accessible-for-notify
    STATUS     current
    DESCRIPTION
            "The Threshold value of PIM table entry."
    ::= { unisPimTrapBindObjects 8 }

unisPimThresholdReasonType OBJECT-TYPE
    SYNTAX     INTEGER {
                         entryCreated(1),
                         configurationChanged(2)
    }
    MAX-ACCESS accessible-for-notify
    STATUS     current
    DESCRIPTION
        "Describe the reason for trap sending:
         The smStarGroup indicates that the current restricted table
         item type is PIM-SM (*,G) table item
         The smSourceGroup indicates that the current restricted table
         item type is PIM-SM (S,G) table item;"
    ::= { unisPimTrapBindObjects 9 }

unisPimRouteEClearReasonType OBJECT-TYPE
    SYNTAX     INTEGER {
                         entryDeleted(1),
                         configurationChanged(2)
    }
    MAX-ACCESS accessible-for-notify
    STATUS     current
    DESCRIPTION
        "Describe the reason for trap sending:
         The smStarGroup indicates that the current restricted table
         item type is PIM-SM (*,G) table item.
         The smSourceGroup indicates that the current restricted table
         item type is PIM-SM (S,G) table item."
    ::= { unisPimTrapBindObjects 10 }

unisPimThresholdClearReasonType OBJECT-TYPE
    SYNTAX     INTEGER {
                         entryDeleted(1),
                         configurationChanged(2)
    }
    MAX-ACCESS accessible-for-notify
    STATUS     current
    DESCRIPTION
        "Describe the reason for trap sending:
         The smStarGroup indicates that the current threshold limit table
         item type is PIM-SM (*,G) table item.
         The smSourceGroup indicates that the current threshold limit
         table item type is PIM-SM (S,G) table item."
    ::= { unisPimTrapBindObjects 11 }

unisPimNotificationSourceAddress OBJECT-TYPE
    SYNTAX     InetAddress
    MAX-ACCESS accessible-for-notify
    STATUS     current
    DESCRIPTION
            "The source IP address of the PIM entry."
    ::= { unisPimTrapBindObjects 12 }

unisPimNotificationGroupAddress OBJECT-TYPE
    SYNTAX     InetAddress
    MAX-ACCESS accessible-for-notify
    STATUS     current
    DESCRIPTION
            "The group IP address of the PIM entry."
    ::= { unisPimTrapBindObjects 13 }

unisPimNbrAddressIfIndex OBJECT-TYPE
    SYNTAX     InterfaceIndex
    MAX-ACCESS accessible-for-notify
    STATUS     current
    DESCRIPTION
            "The value of ifIndex for the interface used to reach this
            PIM neighbor."
    ::= { unisPimTrapBindObjects 14 }

unisPimNbrAddressType OBJECT-TYPE
    SYNTAX     InetAddressType
    MAX-ACCESS accessible-for-notify
    STATUS     current
    DESCRIPTION
            "The address type of this PIM neighbor."
    ::= { unisPimTrapBindObjects 15}

unisPimNbrAddress OBJECT-TYPE
    SYNTAX     InetAddress (SIZE (4|8|16|20))
    MAX-ACCESS read-only
    STATUS     current
    DESCRIPTION
            "The IP address of this PIM neighbor. The InetAddressType
            is specified by the unispimNbrAddressType object."
    ::= { unisPimTrapBindObjects 16 }

unisPimNeighborUpTime OBJECT-TYPE
    SYNTAX     TimeTicks
    MAX-ACCESS accessible-for-notify
    STATUS     current
    DESCRIPTION
            "The time since the PIM neighbor was created as
             a neighbor of the local router."
    ::= { unisPimTrapBindObjects 17 }

unisPimGroupMappingOrigin OBJECT-TYPE
    SYNTAX     UnisPimGroupMappingOriginType
    MAX-ACCESS accessible-for-notify
    STATUS     current
    DESCRIPTION
            "The mechanism by which this group mapping was learned."
    ::= { unisPimTrapBindObjects 18 }

unisPimGroupMappingAddressType OBJECT-TYPE
    SYNTAX     InetAddressType
    MAX-ACCESS accessible-for-notify
    STATUS     current
    DESCRIPTION
            "The address type of the IP multicast group prefix."
    ::= { unisPimTrapBindObjects 19 }

unisPimGroupMappingGrpAddress OBJECT-TYPE
    SYNTAX     InetAddress (SIZE (4|8|16|20))
    MAX-ACCESS accessible-for-notify
    STATUS     current
    DESCRIPTION
            "This object is represented as an IP multicast group address."
    ::= { unisPimTrapBindObjects 20 }

unisPimGroupMappingGrpPrefixLen OBJECT-TYPE
    SYNTAX     InetAddressPrefixLength (4..128)
    MAX-ACCESS accessible-for-notify
    STATUS     current
    DESCRIPTION
            "This object represents the group address mask length."
    ::= { unisPimTrapBindObjects 21 }

unisPimGroupMappingRPAddressType OBJECT-TYPE
    SYNTAX     InetAddressType
    MAX-ACCESS accessible-for-notify
    STATUS     current
    DESCRIPTION
            "This object represents the address type of an RP"
    ::= { unisPimTrapBindObjects 22 }

unisPimGroupMappingRPAddress OBJECT-TYPE
    SYNTAX     InetAddress (SIZE (0|4|8|16|20))
    MAX-ACCESS accessible-for-notify
    STATUS     current
    DESCRIPTION
            "The IP address of the RP to be used for groups within this
            group prefix."
    ::= { unisPimTrapBindObjects 23 }

unisPimGroupMappingPimMode OBJECT-TYPE
    SYNTAX     UnisPimMode
    MAX-ACCESS accessible-for-notify
    STATUS     current
    DESCRIPTION
            "This object represents the currently running PIM mode."
    ::= { unisPimTrapBindObjects 24 }

unisPimGroupMappingPrecedence OBJECT-TYPE
    SYNTAX     Unsigned32
    MAX-ACCESS accessible-for-notify
    STATUS     current
    DESCRIPTION
            "This object represents the corresponding priority of different
             RP types. The higher the value, the lower the priority, and
             0 means the highest priority"
    ::= { unisPimTrapBindObjects 25 }

unisPimInterfaceIfIndex OBJECT-TYPE
    SYNTAX     InterfaceIndex
    MAX-ACCESS accessible-for-notify
    STATUS     current
    DESCRIPTION
            "The ifIndex value of this PIM interface."
    ::= { unisPimTrapBindObjects 26 }

unisPimInterfaceIPVersion OBJECT-TYPE
    SYNTAX     InetVersion
    MAX-ACCESS accessible-for-notify
    STATUS     current
    DESCRIPTION
            "This object represents the IP version of the PIM interface
             , which can be IPv4 or IPv6"
    ::= { unisPimTrapBindObjects 27 }

unisPimInterfaceAddressType OBJECT-TYPE
    SYNTAX     InetAddressType
    MAX-ACCESS accessible-for-notify
    STATUS     current
    DESCRIPTION
            "The address type of this PIM interface."
    ::= { unisPimTrapBindObjects 28 }

unisPimInterfaceAddress OBJECT-TYPE
    SYNTAX     InetAddress (SIZE (0|4|8|16|20))
    MAX-ACCESS accessible-for-notify
    STATUS     current
    DESCRIPTION
            "The primary IP address of this router on this PIM
            interface.  The InetAddressType is given by the
            unisPimInterfaceAddress object."
    ::= { unisPimTrapBindObjects 29 }

unisPimNeighborLossReason OBJECT-TYPE
    SYNTAX     INTEGER {
                         holdTimeTimeout(1),
             notReceiveHelloForALongTime(2),
                           interfaceDown(3),
                       receiveHelloAgain(4),
                        neighbourDeleted(5),
                            alarmTimeOut(6),
                      receiveHelloCancel(7),
                        bfdSessionIsDown(8),
                           userOperation(9),
                            alarmClear(100)
    }
    MAX-ACCESS accessible-for-notify
    STATUS     current
    DESCRIPTION
        "Describe the reason for trap sending:
         holdTimeTimeout:Neighbor's holdtime timer timed out.
         interfaceDown:The interface state of the neighbor changes to down.
         neighbourDeleted:Neighbor deletion.
         receiveHelloCancel:Received a neighbor message with holdtime 0.
         bfdSessionIsDown:Neighbor's BFD session down."
    ::= { unisPimTrapBindObjects 30 }

unisPimNeighborIfName OBJECT-TYPE
    SYNTAX     DisplayString (SIZE (1..64))
    MAX-ACCESS accessible-for-notify
    STATUS     current
    DESCRIPTION
            "The name of the PIM neighbor interface."
    ::= { unisPimTrapBindObjects 31 }

unisPimInterfaceName OBJECT-TYPE
    SYNTAX     DisplayString (SIZE (1..64))
    MAX-ACCESS accessible-for-notify
    STATUS     current
    DESCRIPTION
            "The name of the PIM interface."
    ::= { unisPimTrapBindObjects 32 }

--
-- trap
--
unisPimNeighborAdd NOTIFICATION-TYPE
    OBJECTS { unisPimNeighborExpiryTime,
              unisPimInstanceID,
              unisPimInstanceName,
              unisPimNbrAddressType,
              unisPimNbrAddressIfIndex,
              unisPimNbrAddress
            }
    STATUS     current
    DESCRIPTION
            "A notification sent when PIM add a new neighbor."
    ::= { unisPimNotifications 1 }

unisPimRouteThresholdExceed NOTIFICATION-TYPE
    OBJECTS { unisPimNotificationLimitType,
              unisPimNotificationAddressFamily,
              unisPimNotificationEntryCount,
              unisPimNotificationThresholdCnt,
              unisPimThresholdReasonType
            }
    STATUS     current
    DESCRIPTION
            "A notification sent when the number of pim entries
            exceeded the global entry threshold."
    ::= { unisPimNotifications 2 }

unisPimRouteThresholdExceedClear NOTIFICATION-TYPE
    OBJECTS { unisPimNotificationLimitType,
              unisPimNotificationAddressFamily,
              unisPimNotificationEntryCount,
              unisPimNotificationThresholdCnt,
              unisPimThresholdClearReasonType
            }
    STATUS     current
    DESCRIPTION
            "A notification sent when the number of pim entries
            fell below the global entry threshold."
    ::= { unisPimNotifications 3 }

unisPimRouteExceed NOTIFICATION-TYPE
    OBJECTS { unisPimNotificationLimitType,
              unisPimNotificationAddressFamily,
              unisPimNotificationSourceAddress,
              unisPimNotificationGroupAddress,
              unisPimNotificationEntryCount,
              unisPimNotificationLimitCount,
              unisPimInstanceName
            }
    STATUS     current
    DESCRIPTION
            "A notification sent when the number of pim entries
            exceeded the global entry limit."
    ::= { unisPimNotifications 4 }

unisPimRouteExceedClear NOTIFICATION-TYPE
    OBJECTS { unisPimNotificationLimitType,
              unisPimNotificationAddressFamily,
              unisPimNotificationSourceAddress,
              unisPimNotificationGroupAddress,
              unisPimNotificationEntryCount,
              unisPimNotificationLimitCount,
              unisPimInstanceName,
              unisPimRouteEClearReasonType
            }
    STATUS     current
    DESCRIPTION
            "A notification sent when the number of pim entries
             fell below the global entry threshold."
    ::= { unisPimNotifications 5 }

unisPimNeighborLoss NOTIFICATION-TYPE
    OBJECTS { unisPimNbrAddressIfIndex,
              unisPimNbrAddressType,
              unisPimNbrAddress,
              unisPimNeighborUpTime,
              unisPimNeighborIfName,
              unisPimInstanceID,
              unisPimInstanceName,
              unisPimNeighborLossReason
            }
    STATUS     current
    DESCRIPTION
            "The unisPimNeighborLoss notification is generated
             when PIM lost a neighbor."
    ::= { unisPimNotifications 6 }

unisPimRPMappingChange NOTIFICATION-TYPE
    OBJECTS { unisPimGroupMappingOrigin,
              unisPimGroupMappingAddressType,
              unisPimGroupMappingGrpAddress,
              unisPimGroupMappingGrpPrefixLen,
              unisPimGroupMappingRPAddressType,
              unisPimGroupMappingRPAddress,
              unisPimGroupMappingPimMode,
              unisPimGroupMappingPrecedence,
              unisPimInstanceID,
              unisPimInstanceName
            }
    STATUS      current
    DESCRIPTION
            "The unisPimRPMappingChange notification is generated when
             the active RP mapping on this device is changed"
    ::= { unisPimNotifications 7 }

unisPimInterfaceElection NOTIFICATION-TYPE
    OBJECTS { unisPimInterfaceIfIndex,
              unisPimInterfaceName,
              unisPimInterfaceIPVersion,
              unisPimInterfaceAddressType,
              unisPimInterfaceAddress,
              unisPimInstanceID,
              unisPimInstanceName
            }
    STATUS      current
    DESCRIPTION
            "The unisPimInterfaceElection notification is generated when the
             new DR or DF has been elected on a network."
    ::= { unisPimNotifications 8 }

unisPimVrfRouteThresholdExceed NOTIFICATION-TYPE
    OBJECTS { unisPimNotificationLimitType,
              unisPimNotificationAddressFamily,
              unisPimInstanceName,
              unisPimNotificationEntryCount,
              unisPimNotificationThresholdCnt,
              unisPimThresholdReasonType
            }
    STATUS      current
    DESCRIPTION
            "If the number of PIM routing table entries in the public network
             or VPN instance exceeds the warning threshold, this alarm will be output."
    ::= { unisPimNotifications 9 }

unisPimVrfRouteThExceedClear NOTIFICATION-TYPE
    OBJECTS { unisPimNotificationLimitType,
              unisPimNotificationAddressFamily,
              unisPimInstanceName,
              unisPimNotificationEntryCount,
              unisPimNotificationThresholdCnt,
              unisPimThresholdClearReasonType
            }
    STATUS      current
    DESCRIPTION
            "If the number of PIM routing table entries in the public network
             or VPN instance drops below the warning threshold, this alarm will be output."
    ::= { unisPimNotifications 10 }

unisPimVrfRouteExceed NOTIFICATION-TYPE
    OBJECTS { unisPimNotificationLimitType,
              unisPimNotificationAddressFamily,
              unisPimInstanceName,
              unisPimNotificationEntryCount,
              unisPimNotificationLimitCount,
              unisPimNotificationSourceAddress,
              unisPimNotificationGroupAddress
            }
    STATUS      current
    DESCRIPTION
            "If the number of PIM table entries in the public network or VPN
             instance reaches the maximum allowed value by the device, this alarm will be output."
    ::= { unisPimNotifications 11 }

unisPimVrfRouteExceedClear NOTIFICATION-TYPE
    OBJECTS { unisPimNotificationLimitType,
              unisPimNotificationAddressFamily,
              unisPimInstanceName,
              unisPimNotificationEntryCount,
              unisPimNotificationLimitCount,
              unisPimNotificationSourceAddress,
              unisPimNotificationGroupAddress,
              unisPimRouteEClearReasonType
            }
    STATUS      current
    DESCRIPTION
            "If the number of PIM table entries in the public network or VPN
             instance drops below the maximum allowed value of the device, this alarm will be output."
    ::= { unisPimNotifications 12 }

END
