-- =================================================================
-- Copyright (c) 2023 Unisyue Technologies Co., Ltd.  All rights reserved.
--
-- Description: Password Control MIB
-- Reference:
-- Version: V1.0
-- History:
--  V1.0 2023-10-17 Initial version, create by jiangzuhuan
-- =================================================================
UNIS-PASSWORD-CONTROL-MIB DEFINITIONS ::= BEGIN


IMPORTS
    unisCommon
        FROM UNIS-OID-MIB
    NOTIFICATION-TYPE, MODULE-IDENTITY
        FROM SNMPv2-SMI;

unisPwdctl MODULE-IDENTITY
    LAST-UPDATED "202310171800Z"            -- October 17, 2023 at 18:00 GMT
    ORGANIZATION
        "Unisyue Technologies Co., Ltd."
    CONTACT-INFO
        ""
    DESCRIPTION
        "The MIB module is used for managing password control."
    REVISION "202310171800Z"        -- October 17, 2023 at 18:00 GMT
    DESCRIPTION
         "The initial version."
    ::= { unisCommon 267 }

-- ----------------------------------------------------------------------
-- unisPwdctlTraps Table
-- ----------------------------------------------------------------------
unisPwdctlTraps      OBJECT IDENTIFIER ::= { unisPwdctl 1 }
unisPwdctlTrapsDefine      OBJECT IDENTIFIER ::= { unisPwdctlTraps 0 }

unisPwdctlFailedCopyFileTrap NOTIFICATION-TYPE
    STATUS current
    DESCRIPTION
        "This notification is generated when the device is unable to copy
         password control file to the backup control board."
    ::= { unisPwdctlTrapsDefine 1 }

unisPwdctlFailedWritePwdTrap NOTIFICATION-TYPE
    STATUS current
    DESCRIPTION
        "This notification is generated when the device is unable to write
        the password records to the password control file."
    ::= { unisPwdctlTrapsDefine 2 }

unisPwdctlFailedOpenFileTrap NOTIFICATION-TYPE
    STATUS current
    DESCRIPTION
        "This notification is generated when the device fails to create or open
         the password control file."
    ::= { unisPwdctlTrapsDefine 3 }

unisPwdctlNoEnoughSpaceTrap NOTIFICATION-TYPE
    STATUS current
    DESCRIPTION
        "This notification is generated when the storage medium
        where the password control file is located does not have
        sufficient storage space."
    ::= { unisPwdctlTrapsDefine 4 }

unisPwdctlNotifyWriteFileTrap NOTIFICATION-TYPE
    STATUS current
    DESCRIPTION
        "This notification is generated when the device fails to notify
         the event of writing password records to the password control file."
    ::= { unisPwdctlTrapsDefine 5 }

unisPwdctlRecFormatConvTrap NOTIFICATION-TYPE
    STATUS current
    DESCRIPTION
        "This notification is generated when the device fails to convert
        the password record format."
    ::= { unisPwdctlTrapsDefine 6 }

END
