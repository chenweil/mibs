-- =================================================================
-- Copyright (c) 2020 Unisyue Technologies Co., Ltd.  All rights reserved.
--
-- Description: The MIB of data and configuration on control plane.
-- Reference:
-- Version: V1.0
-- History:
--   V1.0 Created by huanglei
--     Initial version 2020-09-10
-- =================================================================
UNIS-CUPM-CP-MIB DEFINITIONS ::= BEGIN

IMPORTS
        unisCommon
    FROM UNIS-OID-MIB
        InetAddressType, InetAddress
    FROM INET-ADDRESS-MIB
        OBJECT-TYPE, MODULE-IDENTITY, NOTIFICATION-TYPE,
        Integer32
    FROM SNMPv2-SMI
        RowStatus
    FROM SNMPv2-TC;

unisCupmCp MODULE-IDENTITY
    LAST-UPDATED "202009110000Z"
    ORGANIZATION
        "Unisyue Technologies Co., Ltd."
    CONTACT-INFO
        ""
    DESCRIPTION
        "This MIB provides config information of CP(Control Plane)."
    REVISION "202009110000Z"
    DESCRIPTION
        "The initial revision of this MIB module."
    ::= { unisCommon 194 }

--
-- Node definitions
--

-- Traps are defined below.
unisCupmCpNotifications OBJECT IDENTIFIER ::= { unisCupmCp 0 }

unisCupmCpProtoTnlUp NOTIFICATION-TYPE
    OBJECTS
        {
            unisCupmCpVbUpID,
            unisCupmCpVbVxlanID,
            unisCupmCpVbSrcAddrType,
            unisCupmCpVbSrcAddr,
            unisCupmCpVbDestAddrType,
            unisCupmCpVbDestAddr,
            unisCupmCpVbVpnName,
            unisCupmCpVbVxlanState
        }
    STATUS current
    DESCRIPTION
        "The notification is generated when
         CP device connects to VXLAN tunnel."
    ::= { unisCupmCpNotifications 1 }

unisCupmCpProtoTnlDown NOTIFICATION-TYPE
    OBJECTS
        {
            unisCupmCpVbUpID,
            unisCupmCpVbVxlanID,
            unisCupmCpVbSrcAddrType,
            unisCupmCpVbSrcAddr,
            unisCupmCpVbDestAddrType,
            unisCupmCpVbDestAddr,
            unisCupmCpVbVpnName,
            unisCupmCpVbVxlanState
        }
    STATUS current
    DESCRIPTION
        "The notification is generated when
         CP device disconnects to VXLAN tunnel."
    ::= { unisCupmCpNotifications 2 }

-- =================================================================
unisCupmCpNotifyVarObjects OBJECT IDENTIFIER ::= { unisCupmCp 1 }

unisCupmCpVbUpID OBJECT-TYPE
    SYNTAX      Integer32 (1..2147483647)
    MAX-ACCESS  accessible-for-notify
    STATUS      current
    DESCRIPTION
        "The number of UP device."
    ::= { unisCupmCpNotifyVarObjects 1 }

unisCupmCpVbVxlanID OBJECT-TYPE
    SYNTAX      Integer32 (1..16777215)
    MAX-ACCESS  accessible-for-notify
    STATUS      current
    DESCRIPTION
        "Part of the index for this table, this value
         identifies the VXLAN protocol tunnel."
    ::= { unisCupmCpNotifyVarObjects 2 }

unisCupmCpVbSrcAddrType OBJECT-TYPE
    SYNTAX      InetAddressType
    MAX-ACCESS  accessible-for-notify
    STATUS      current
    DESCRIPTION
        "Specifies the type of local address to be used at a remote
         host for connecting VXLAN protocol tunnel."
    ::= { unisCupmCpNotifyVarObjects 3 }

unisCupmCpVbSrcAddr OBJECT-TYPE
    SYNTAX      InetAddress
    MAX-ACCESS  accessible-for-notify
    STATUS      current
    DESCRIPTION
        "Specifies the local address to be used at a remote
         host for connecting VXLAN protocol tunnel.  The host
         address type is determined by the object value of corresponding
         unisCupmCpProtoTnlSrcAddrType."
    ::= { unisCupmCpNotifyVarObjects 4 }

unisCupmCpVbDestAddrType OBJECT-TYPE
    SYNTAX      InetAddressType
    MAX-ACCESS  accessible-for-notify
    STATUS      current
    DESCRIPTION
        "Specifies the type of remote host for connecting the VXLAN
         protocol tunnel."
    ::= { unisCupmCpNotifyVarObjects 5 }

unisCupmCpVbDestAddr OBJECT-TYPE
    SYNTAX      InetAddress
    MAX-ACCESS  accessible-for-notify
    STATUS      current
    DESCRIPTION
        "Specifies the remote host for connecting the VXLAN
         protocol tunnel."
    ::= { unisCupmCpNotifyVarObjects 6 }


unisCupmCpVbVpnName OBJECT-TYPE
    SYNTAX      OCTET STRING (SIZE(0..31))
    MAX-ACCESS  accessible-for-notify
    STATUS      current
    DESCRIPTION
         "The VPN name, to which the rule will be applied.
         Default value is zero-length."
    ::= { unisCupmCpNotifyVarObjects 7 }

unisCupmCpVbVxlanState OBJECT-TYPE
    SYNTAX      INTEGER
    {
        unknown  (0),
        up  (1),
        down  (2)
    }
    MAX-ACCESS  accessible-for-notify
    STATUS      current
    DESCRIPTION
        "The state of VXLAN protocol tunnel.
         0 (unknown) The VXLAN protocol tunnel is in unknown state.
         1 (up) The VXLAN protocol tunnel is in connected state.
         2 (down) The VXLAN protocol tunnel is in disconnected state."
    ::= { unisCupmCpNotifyVarObjects 8 }

-- =================================================================
-- Scalar MIB objects, which are considered as global variables.
unisCupmCpScalarObjects OBJECT IDENTIFIER ::= { unisCupmCp 2 }

unisCupmUpNum OBJECT-TYPE
    SYNTAX      Integer32 (1..2147483647)
    MAX-ACCESS  read-only
    STATUS      current
    DESCRIPTION
        "The number of UP device."
    ::= { unisCupmCpScalarObjects 1 }

-- =================================================================
-- All table objects are defined below.

unisCupmCpTableObjects OBJECT IDENTIFIER ::= { unisCupmCp 3 }

unisCupmUpListTable OBJECT-TYPE
    SYNTAX      SEQUENCE OF UnisCupmUpListEntry
    MAX-ACCESS  not-accessible
    STATUS      current
    DESCRIPTION
        "A table of UP management information."
    ::= { unisCupmCpTableObjects 1 }

unisCupmUpListEntry OBJECT-TYPE
    SYNTAX      UnisCupmUpListEntry
    MAX-ACCESS  not-accessible
    STATUS      current
    DESCRIPTION
        "Entry items."
    INDEX
        {
            unisCupmUpID
        }
    ::= { unisCupmUpListTable 1 }

UnisCupmUpListEntry ::= SEQUENCE
    {
        unisCupmUpID               Integer32,
        unisCupmUpDescr            OCTET STRING,
        unisCupmUpListRowStatus    RowStatus
    }

unisCupmUpID OBJECT-TYPE
    SYNTAX      Integer32 (1..2147483647)
    MAX-ACCESS  accessible-for-notify
    STATUS      current
    DESCRIPTION
        "The index value used to identify the UP device."
    ::= { unisCupmUpListEntry 1 }

unisCupmUpDescr OBJECT-TYPE
    SYNTAX      OCTET STRING (SIZE(0..255))
    MAX-ACCESS  read-create
    STATUS      current
    DESCRIPTION
        "A textual description of the entity.  This value could
         include the full name and status of UP device."
    DEFVAL  { "" }
    ::= { unisCupmUpListEntry 2 }

unisCupmUpListRowStatus OBJECT-TYPE
    SYNTAX      RowStatus
    MAX-ACCESS  read-create
    STATUS      current
    DESCRIPTION
        "Three status columns are supported, including 'active',
         'createAndGo' and 'destroy'.  The column of 'active' is used
         for modifying value of unisCupmUpDescr."
    ::= { unisCupmUpListEntry 3 }

-- =================================================================
unisCupmCpProtoTnlTable OBJECT-TYPE
    SYNTAX      SEQUENCE OF UnisCupmCpProtoTnlEntry
    MAX-ACCESS  not-accessible
    STATUS      current
    DESCRIPTION
        "The table that controls configuration of VXLAN tunnel on CP device."
    ::= { unisCupmCpTableObjects 2 }

unisCupmCpProtoTnlEntry OBJECT-TYPE
    SYNTAX      UnisCupmCpProtoTnlEntry
    MAX-ACCESS  not-accessible
    STATUS      current
    DESCRIPTION
        "Entry items."
    INDEX
        {
            unisCupmUpID,
            unisCupmCpProtoTnlVxlanID,
            unisCupmCpProtoTnlSrcAddrType,
            unisCupmCpProtoTnlSrcAddr,
            unisCupmCpProtoTnlDstAddrType,
            unisCupmCpProtoTnlDstAddr
        }
    ::= { unisCupmCpProtoTnlTable 1 }

UnisCupmCpProtoTnlEntry ::= SEQUENCE
    {
        unisCupmCpProtoTnlVxlanID        Integer32,
        unisCupmCpProtoTnlSrcAddrType    InetAddressType,
        unisCupmCpProtoTnlSrcAddr        InetAddress,
        unisCupmCpProtoTnlDstAddrType    InetAddressType,
        unisCupmCpProtoTnlDstAddr        InetAddress,
        unisCupmCpProtoTnlVpnName        OCTET STRING,
        unisCupmCpProtoTnlState          INTEGER,
        unisCupmCpProtoTnlRowStatus      RowStatus
    }

unisCupmCpProtoTnlVxlanID OBJECT-TYPE
    SYNTAX      Integer32 (1..16777215)
    MAX-ACCESS  read-only
    STATUS      current
    DESCRIPTION
        "Part of the index for this table, this value
         identifies the VXLAN protocol tunnel."
    ::= { unisCupmCpProtoTnlEntry 1 }

unisCupmCpProtoTnlSrcAddrType OBJECT-TYPE
    SYNTAX      InetAddressType
    MAX-ACCESS  read-only
    STATUS      current
    DESCRIPTION
        "Specifies the type of local address to be used at a remote
         host for connecting VXLAN protocol tunnel."
    ::= { unisCupmCpProtoTnlEntry 2 }

unisCupmCpProtoTnlSrcAddr OBJECT-TYPE
    SYNTAX      InetAddress
    MAX-ACCESS  read-only
    STATUS      current
    DESCRIPTION
        "Specifies the local address to be used at a remote
         host for connecting VXLAN protocol tunnel.  The host
         address type is determined by the object value of corresponding
         unisCupmCpProtoTnlSrcAddrType."
    ::= { unisCupmCpProtoTnlEntry 3 }

unisCupmCpProtoTnlDstAddrType OBJECT-TYPE
    SYNTAX      InetAddressType
    MAX-ACCESS  read-only
    STATUS      current
    DESCRIPTION
        "Specifies the type of remote host for connecting the VXLAN
         protocol tunnel."
    ::= { unisCupmCpProtoTnlEntry 4 }

unisCupmCpProtoTnlDstAddr OBJECT-TYPE
    SYNTAX      InetAddress
    MAX-ACCESS  read-only
    STATUS      current
    DESCRIPTION
        "Specifies the remote host for connecting the VXLAN
         protocol tunnel."
    ::= { unisCupmCpProtoTnlEntry 5 }

unisCupmCpProtoTnlVpnName OBJECT-TYPE
    SYNTAX      OCTET STRING (SIZE(0..31))
    MAX-ACCESS  read-create
    STATUS      current
    DESCRIPTION
        "The VPN name, to which the rule will be applied.
         Default value is zero-length."
    DEFVAL { "" }
    ::= { unisCupmCpProtoTnlEntry 6 }

unisCupmCpProtoTnlState OBJECT-TYPE
    SYNTAX      INTEGER
    {
        unknown  (0),
        up  (1),
        down  (2)
    }
    MAX-ACCESS  read-only
    STATUS      current
    DESCRIPTION
        "The state of VXLAN protocol tunnel.
         0 (unknown) The VXLAN protocol tunnel is in unknown state.
         1 (up) The VXLAN protocol tunnel is in connected state.
         2 (down) The VXLAN protocol tunnel is in disconnected state."
    ::= { unisCupmCpProtoTnlEntry 7 }

unisCupmCpProtoTnlRowStatus OBJECT-TYPE
    SYNTAX      RowStatus
    MAX-ACCESS  read-create
    STATUS      current
    DESCRIPTION
       "This object is responsible for managing the creation, deletion and
        modification of rows, which support active status and CreateAndGo,
        Destroy operation.  To create a new row, unisCupmUpID must be specified."

    ::= { unisCupmCpProtoTnlEntry 8 }

-- =================================================================
unisCupmAgtProtoTnlTable OBJECT-TYPE
    SYNTAX      SEQUENCE OF UnisCupmAgtProtoTnlEntry
    MAX-ACCESS  not-accessible
    STATUS      current
    DESCRIPTION
        "Thie table provides VXLAN tunnel configuration of UP
         device which under control of CP device.  This protocol tunnel
         allows to make configuration of UP device."
    ::= { unisCupmCpTableObjects 3 }

unisCupmAgtProtoTnlEntry OBJECT-TYPE
    SYNTAX      UnisCupmAgtProtoTnlEntry
    MAX-ACCESS  not-accessible
    STATUS      current
    DESCRIPTION
        "Entry items."
    INDEX
        {
            unisCupmUpID,
            unisCupmAgtProtoTnlVxlanID,
            unisCupmAgtProtoTnlSrcAddrType,
            unisCupmAgtProtoTnlSrcAddr,
            unisCupmAgtProtoTnlDstAddrType,
            unisCupmAgtProtoTnlDstAddr
        }
    ::= { unisCupmAgtProtoTnlTable 1 }

UnisCupmAgtProtoTnlEntry ::= SEQUENCE
    {
        unisCupmAgtProtoTnlVxlanID           Integer32,
        unisCupmAgtProtoTnlSrcAddrType       InetAddressType,
        unisCupmAgtProtoTnlSrcAddr           InetAddress,
        unisCupmAgtProtoTnlDstAddrType       InetAddressType,
        unisCupmAgtProtoTnlDstAddr           InetAddress,
        unisCupmAgtProtoTnlVpnName           OCTET STRING,
        unisCupmAgtProtoTnlRowStatus         RowStatus
    }

unisCupmAgtProtoTnlVxlanID OBJECT-TYPE
    SYNTAX      Integer32 (1..16777215)
    MAX-ACCESS  read-only
    STATUS      current
    DESCRIPTION
        "Part of the index for this table, this value
         identifies the VXLAN protocol tunnel."
    ::= { unisCupmAgtProtoTnlEntry 1 }

unisCupmAgtProtoTnlSrcAddrType OBJECT-TYPE
    SYNTAX      InetAddressType
    MAX-ACCESS  read-only
    STATUS      current
    DESCRIPTION
        "Specifies the type of local address to be used at a remote
         host for connecting VXLAN protocol tunnel."
    ::= { unisCupmAgtProtoTnlEntry 2 }

unisCupmAgtProtoTnlSrcAddr OBJECT-TYPE
    SYNTAX      InetAddress
    MAX-ACCESS  read-only
    STATUS      current
    DESCRIPTION
        "Specifies the local address to be used at a remote
         host for connecting VXLAN protocol tunnel.  The host
         address type is determined by the object value of corresponding
         unisCupmCpProtoTnlSrcAddrType."
    ::= { unisCupmAgtProtoTnlEntry 3 }

unisCupmAgtProtoTnlDstAddrType OBJECT-TYPE
    SYNTAX      InetAddressType
    MAX-ACCESS  read-only
    STATUS      current
    DESCRIPTION
        "Specifies the type of remote host for connecting the VXLAN
         protocol tunnel."
    ::= { unisCupmAgtProtoTnlEntry 4 }

unisCupmAgtProtoTnlDstAddr OBJECT-TYPE
    SYNTAX      InetAddress
    MAX-ACCESS  read-only
    STATUS      current
    DESCRIPTION
        "Specifies the remote host for connecting the VXLAN
         protocol tunnel."
    ::= { unisCupmAgtProtoTnlEntry 5 }

unisCupmAgtProtoTnlVpnName OBJECT-TYPE
    SYNTAX      OCTET STRING (SIZE(0..31))
    MAX-ACCESS  read-create
    STATUS      current
    DESCRIPTION
        "The VPN name, to which the rule will be applied.
         Default value is zero-length."
    DEFVAL { "" }
    ::= { unisCupmAgtProtoTnlEntry 6 }

unisCupmAgtProtoTnlRowStatus OBJECT-TYPE
    SYNTAX      RowStatus
    MAX-ACCESS  read-create
    STATUS      current
    DESCRIPTION
       "This object is responsible for managing the creation, deletion and
        modification of rows, which support active status and CreateAndGo,
        Destroy operation.  To create a new row, unisCupmUpID must be specified."
    ::= { unisCupmAgtProtoTnlEntry 7 }

END
