-- =================================================================
-- Copyright (c) 2023 Unisyue Technologies Co., Ltd.  All rights reserved.
--
-- Description: Alarm MIB
-- Reference:
-- Version: V1.0
-- History:
--     V1.0 Initial version 2023-10-31
-- =================================================================
UNIS-ALARM-MIB DEFINITIONS ::= BEGIN

IMPORTS
    Integer32, OBJECT-TYPE, MODULE-IDENTITY, Unsigned32, Counter64, NOTIFICATION-TYPE
        FROM SNMPv2-SMI
    DisplayString, TruthValue, RowStatus, DateAndTime
        FROM SNMPv2-TC
    SnmpAdminString
        FROM SNMP-FRAMEWORK-MIB
    snmpTargetAddrName
        FROM SNMP-TARGET-MIB
    unisCommon
        FROM UNIS-OID-MIB;

unisAlarm MODULE-IDENTITY
    LAST-UPDATED "202208030000Z"
    ORGANIZATION
        "Unisyue Technologies Co., Ltd."
    CONTACT-INFO
        ""
    DESCRIPTION
        "This MIB contains objects for alarm info"
    REVISION "202208030000Z"
    DESCRIPTION
        "Initial version."
    ::= { unisCommon 243 }

--
-- Node definitions
--

unisAlarmObjects OBJECT IDENTIFIER ::= { unisAlarm 1 }

unisAlarmScalarGroup OBJECT IDENTIFIER ::= { unisAlarmObjects 1 }

unisAlarmGroup OBJECT IDENTIFIER ::= { unisAlarmObjects 2 }

unisAlarmUuid OBJECT-TYPE
    SYNTAX OCTET STRING (SIZE(1..255))
    MAX-ACCESS read-only
    STATUS current
    DESCRIPTION
        "
        Alarm UUID.
        Format:xxxxxxxx-xxxx-4xxx-yxxx-xxxxxxxxxxxx
        x:0-9, a-f.  y:8, 9, a or b
        E.g.412f7b66-0090-475f-bc87-936ab2d127e1
        "
    ::= { unisAlarmScalarGroup 1 }

unisAlarmTrap OBJECT IDENTIFIER ::= { unisAlarm 2 }

unisAlarmTrapPrex OBJECT IDENTIFIER ::= { unisAlarmTrap 0 }

unisAlarmClearedReportTrap NOTIFICATION-TYPE
    OBJECTS
        {
            unisAlarmClearedNum,
            unisAlarmClearedSnList
        }
    STATUS current
    DESCRIPTION
        "Send the alarm cleared report trap."
    ::= { unisAlarmTrapPrex 1 }

-- Begin define Alarm SyncIndex range table
unisAlarmSyncIndexRangeTable OBJECT-TYPE
    SYNTAX SEQUENCE OF UnisAlarmSyncIndexRangeEntry
    MAX-ACCESS not-accessible
    STATUS current
    DESCRIPTION
        "Alarm retransmission index range table."
    ::= { unisAlarmGroup 1 }

unisAlarmSyncIndexRangeEntry OBJECT-TYPE
    SYNTAX UnisAlarmSyncIndexRangeEntry
    MAX-ACCESS not-accessible
    STATUS current
    DESCRIPTION
        "Alarm retransmission index range entry."
    INDEX { snmpTargetAddrName }
    ::= { unisAlarmSyncIndexRangeTable 1 }

UnisAlarmSyncIndexRangeEntry ::=
    SEQUENCE {
        unisAlarmSyncIndexMin         Counter64,
        unisAlarmSyncIndexMax         Counter64
    }

unisAlarmSyncIndexMin OBJECT-TYPE
    SYNTAX Counter64
    MAX-ACCESS read-only
    STATUS current
    DESCRIPTION
        "Minimum retransmission index."
    ::= { unisAlarmSyncIndexRangeEntry 1 }

unisAlarmSyncIndexMax OBJECT-TYPE
    SYNTAX Counter64
    MAX-ACCESS read-only
    STATUS current
    DESCRIPTION
        "Maximum retransmission index."
    ::= { unisAlarmSyncIndexRangeEntry 2 }

-- End define  Alarm SyncIndex range table

-- Begin define Alarm operate table
unisAlarmOperateTable OBJECT-TYPE
    SYNTAX SEQUENCE OF UnisAlarmOperateEntry
    MAX-ACCESS not-accessible
    STATUS current
    DESCRIPTION
        "Alarm retransmission request table."
    ::= { unisAlarmGroup 2 }

unisAlarmOperateEntry OBJECT-TYPE
    SYNTAX UnisAlarmOperateEntry
    MAX-ACCESS not-accessible
    STATUS current
    DESCRIPTION
        "Alarm retransmission request entry."
    INDEX { unisAlarmOperateIndex }
    ::= { unisAlarmOperateTable 1 }

UnisAlarmOperateEntry ::=
    SEQUENCE
        {
            unisAlarmOperateIndex                    Integer32,
            unisAlarmOperateTargetAddress            SnmpAdminString,
            unisAlarmOperateType                     INTEGER,
            unisAlarmOperateStartSynIdxHi            Unsigned32,
            unisAlarmOperateStartSynIdxLo            Unsigned32,
            unisAlarmOperateEndSynIdxHi              Unsigned32,
            unisAlarmOperateEndSynIdxLo              Unsigned32,
            unisAlarmOperateRowStatus                RowStatus
        }

unisAlarmOperateIndex OBJECT-TYPE
    SYNTAX Integer32 (1..2147483647)
    MAX-ACCESS not-accessible
    STATUS current
    DESCRIPTION
    "Index of the alarm retransmission request table."
    ::= { unisAlarmOperateEntry 1 }

unisAlarmOperateTargetAddress OBJECT-TYPE
    SYNTAX SnmpAdminString (SIZE(1..255))
    MAX-ACCESS read-create
    STATUS current
    DESCRIPTION
        "Alarm retransmission target host address, which must be specified in the alarm retransmission request table."
    ::= { unisAlarmOperateEntry 2 }

unisAlarmOperateType OBJECT-TYPE
    SYNTAX INTEGER
    {
        resendSyncAlarm(1),
        resendActiveAlarm(2)
    }
    MAX-ACCESS read-create
    STATUS current
    DESCRIPTION
        "Alarm retransmission method."
    ::= { unisAlarmOperateEntry 3 }

unisAlarmOperateStartSynIdxHi OBJECT-TYPE
    SYNTAX Unsigned32
    MAX-ACCESS read-create
    STATUS current
    DESCRIPTION
        "The highest 32 bits of the minimum alarm retransmission index."
    ::= { unisAlarmOperateEntry 4 }

unisAlarmOperateStartSynIdxLo OBJECT-TYPE
    SYNTAX Unsigned32
    MAX-ACCESS read-create
    STATUS current
    DESCRIPTION
        "The lowest 32 bits of the minimum alarm retransmission index."
    ::= { unisAlarmOperateEntry 5 }

unisAlarmOperateEndSynIdxHi OBJECT-TYPE
    SYNTAX Unsigned32
    MAX-ACCESS read-create
    STATUS current
    DESCRIPTION
        "The highest 32 bits of the maximum alarm retransmission index."
    ::= { unisAlarmOperateEntry 6 }

unisAlarmOperateEndSynIdxLo OBJECT-TYPE
    SYNTAX Unsigned32
    MAX-ACCESS read-create
    STATUS current
    DESCRIPTION
        "The lowest 32 bits of the maximum alarm retransmission index."
    ::= { unisAlarmOperateEntry 7 }

unisAlarmOperateRowStatus OBJECT-TYPE
    SYNTAX RowStatus
    MAX-ACCESS read-create
    STATUS current
    DESCRIPTION
        "Row status of this table entry."
    ::= { unisAlarmOperateEntry 8 }

unisAlarmTrapObjects OBJECT IDENTIFIER ::= { unisAlarmTrap 1 }

unisAlarmSyncIndex OBJECT-TYPE
    SYNTAX Counter64
    MAX-ACCESS accessible-for-notify
    STATUS current
    DESCRIPTION
        "Alarm retransmission index."
    ::= { unisAlarmTrapObjects 1 }

unisAlarmDateAndTime OBJECT-TYPE
    SYNTAX DateAndTime
    MAX-ACCESS accessible-for-notify
    STATUS current
    DESCRIPTION
        "
        Time when the alarm was triggered.
        "
    ::= { unisAlarmTrapObjects 2 }

unisAlarmActiveIndex OBJECT-TYPE
    SYNTAX Integer32 (1..2147483647)
    MAX-ACCESS accessible-for-notify
    STATUS current
    DESCRIPTION
        "Number of the active alarm."
    ::= { unisAlarmTrapObjects 3 }

unisAlarmOrEventFlag OBJECT-TYPE
    SYNTAX INTEGER
    {
        alarm(1),
        event(2)
    }
    MAX-ACCESS accessible-for-notify
    STATUS current
    DESCRIPTION
        "Alarm or event flag."
    ::= { unisAlarmTrapObjects 4 }

unisAlarmSeverity OBJECT-TYPE
    SYNTAX DisplayString (SIZE (0..255))
    MAX-ACCESS accessible-for-notify
    STATUS current
    DESCRIPTION
        "
        Alarm severity.
        E.g.Critical
        E.g.Major
        "
    ::= { unisAlarmTrapObjects 5 }

unisAlarmPVFlag OBJECT-TYPE
    SYNTAX DisplayString (SIZE (0..255))
    MAX-ACCESS accessible-for-notify
    STATUS current
    DESCRIPTION
        "Alarm PV flag."
    ::= { unisAlarmTrapObjects 6 }

unisAlarmSyncFlag OBJECT-TYPE
    SYNTAX INTEGER
    {
        realTime(1),
        syncResend(2)
    }
    MAX-ACCESS accessible-for-notify
    STATUS current
    DESCRIPTION
        "
        Trap transmission status:
        realTime: The trap is transmitted in real time.
        syncResend: The trap is retransmitted.
        "
    ::= { unisAlarmTrapObjects 7 }

unisAlarmStatus OBJECT-TYPE
    SYNTAX TruthValue
    MAX-ACCESS accessible-for-notify
    STATUS current
    DESCRIPTION
        "
        Alarm status.
        True:alarm active
        False:alarm recover
        "
    ::= { unisAlarmTrapObjects 8 }

unisAlarmObjectID OBJECT-TYPE
    SYNTAX DisplayString (SIZE (0..255))
    MAX-ACCESS accessible-for-notify
    STATUS current
    DESCRIPTION
        "Name and unique identifier of the device that reported the alarm."
    ::= { unisAlarmTrapObjects 9 }

unisAlarmCode OBJECT-TYPE
    SYNTAX Integer32 (1..2147483647)
    MAX-ACCESS accessible-for-notify
    STATUS current
    DESCRIPTION
        "Unique ID of the alarm type."
    ::= { unisAlarmTrapObjects 10 }

unisAlarmType OBJECT-TYPE
    SYNTAX DisplayString (SIZE (0..255))
    MAX-ACCESS accessible-for-notify
    STATUS current
    DESCRIPTION
        "
        Alarm type.
        E.g.CommunicationAlarm
        "
    ::= { unisAlarmTrapObjects 11 }

unisAlarmSource OBJECT-TYPE
    SYNTAX DisplayString (SIZE (0..255))
    MAX-ACCESS accessible-for-notify
    STATUS current
    DESCRIPTION
        "Alarm source information."
    ::= { unisAlarmTrapObjects 12 }

unisAlarmSpecificProblem OBJECT-TYPE
    SYNTAX DisplayString (SIZE (0..1024))
    MAX-ACCESS accessible-for-notify
    STATUS current
    DESCRIPTION
        "Specific reason for the alarm."
    ::= { unisAlarmTrapObjects 13 }

unisAlarmAdditionalText OBJECT-TYPE
    SYNTAX DisplayString (SIZE (0..255))
    MAX-ACCESS accessible-for-notify
    STATUS current
    DESCRIPTION
        "Additional information for the alarm."
    ::= { unisAlarmTrapObjects 14 }

unisAlarmTargetAddress OBJECT-TYPE
    SYNTAX SnmpAdminString (SIZE(1..255))
    MAX-ACCESS accessible-for-notify
    STATUS current
    DESCRIPTION
        "Alarm target host address."
    ::= { unisAlarmTrapObjects 15 }

unisAlarmClearedNum OBJECT-TYPE
    SYNTAX Unsigned32
    MAX-ACCESS accessible-for-notify
    STATUS current
    DESCRIPTION
        "Number of the cleared alarm."
    ::= { unisAlarmTrapObjects 16 }

unisAlarmClearedSnList OBJECT-TYPE
    SYNTAX DisplayString (SIZE (0..1024))
    MAX-ACCESS accessible-for-notify
    STATUS current
    DESCRIPTION
        "List of the cleared alarm."
    ::= { unisAlarmTrapObjects 17 }
END
