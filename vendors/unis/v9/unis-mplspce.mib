-- =============================================================================
-- Copyright (c) 2022 Unisyue Technologies Co., Ltd.  All rights reserved.
--
-- Description: Multiprotocol Label Switching Path Computation Element MIB
-- Reference:
-- Version: V1.0
-- History:
--   V1.0 2022-07-13 Initial version Created by Zhujieyi
--        2022-08-23 Modified by Zhujieyi, Added unisMplsPceDelegationInfo
-- =============================================================================
UNIS-MPLSPCE-MIB DEFINITIONS ::= BEGIN
IMPORTS
    MODULE-IDENTITY, OBJECT-TYPE, NOTIFICATION-TYPE
        FROM SNMPv2-SMI
    unisCommon
        FROM UNIS-OID-MIB
    ;

-- =============================================================================
-- module identity part
-- =============================================================================
unisMplsPce MODULE-IDENTITY
    LAST-UPDATED
        "202208230300Z"   -- August 23, 2022 at 03:00 GMT
    ORGANIZATION
        "Unisyue Technologies Co., Ltd."
    CONTACT-INFO
        ""
    DESCRIPTION
        "Multiprotocol Label Switching Path Computation Element MIB"
    REVISION
        "202208230300Z"   -- August 23, 2022 at 03:00 GMT
    DESCRIPTION
        "Added unisMplsPceDelegationInfo."
    REVISION
        "202207130853Z"   -- July 13, 2022 at 08:54 GMT
    DESCRIPTION
        "Initial version of this MIB."
    ::= { unisCommon 240 }

-- =============================================================================
-- Top level components of this MIB module.
-- =============================================================================
unisMplsPceNotifications OBJECT IDENTIFIER  ::= { unisMplsPce 0 }

unisMplsPceObjects       OBJECT IDENTIFIER  ::= { unisMplsPce 1 }

unisMplsPceScalarGroup   OBJECT IDENTIFIER  ::= { unisMplsPceObjects 1 }

unisMplsPcePcepSessInfo    OBJECT-TYPE
    SYNTAX      OCTET STRING (SIZE (1..127))
    MAX-ACCESS  accessible-for-notify
    STATUS      current
    DESCRIPTION
        "The base information of MPLS PCEP Session."
    ::= { unisMplsPceScalarGroup 1 }

unisMplsPceDelegationInfo    OBJECT-TYPE
    SYNTAX      OCTET STRING (SIZE (1..127))
    MAX-ACCESS  accessible-for-notify
    STATUS      current
    DESCRIPTION
        "The base information of MPLS PCE Delegation."
    ::= { unisMplsPceScalarGroup 2 }

-- =============================================================================
-- Notifications
-- =============================================================================
unisMplsPcePcepSessDown  NOTIFICATION-TYPE
    OBJECTS {  unisMplsPcePcepSessInfo  }
    STATUS      current
    DESCRIPTION
      "This notification is generated when the PCEP Session changed to Down."
    ::= { unisMplsPceNotifications 1 }

unisMplsPcePcepSessUp  NOTIFICATION-TYPE
    OBJECTS {  unisMplsPcePcepSessInfo  }
    STATUS      current
    DESCRIPTION
      "This notification is generated when the PCEP Session changed to Up."
    ::= { unisMplsPceNotifications 2 }

unisMplsPceRetDelegation  NOTIFICATION-TYPE
    OBJECTS {  unisMplsPceDelegationInfo  }
    STATUS      current
    DESCRIPTION
      "This notification is generated when the PCE returned delegation
      for MPLS TE Tunnel."
    ::= { unisMplsPceNotifications 3 }

unisMplsPceRetDelegationClear  NOTIFICATION-TYPE
    OBJECTS {  unisMplsPceDelegationInfo  }
    STATUS      current
    DESCRIPTION
      "This notification is generated when the PCE delegated MPLS TE Tunnel."
    ::= { unisMplsPceNotifications 4 }

-- =============================================================================
-- End of notifications.
-- =============================================================================

END
