-- =============================================================================
-- Copyright (c) 2020 Unisyue Technologies Co., Ltd.  All rights reserved.
--
-- Description: Multiprotocol Label Switching Traffic Engineering MIB
-- Reference:
-- Version: V1.0
-- History:
--   V1.0 2013-06-13 Initial version Created by Neng Yan
-- =============================================================================
UNIS-MPLSTE-MIB DEFINITIONS ::= BEGIN
IMPORTS
    MODULE-IDENTITY, OBJECT-TYPE, Unsigned32
        FROM SNMPv2-SMI
    RowStatus, TruthValue
        FROM SNMPv2-TC
    unisCommon
        FROM UNIS-OID-MIB
    ;

-- =============================================================================
-- module identity part
-- =============================================================================
unisMplsTe MODULE-IDENTITY
    LAST-UPDATED
        "201306131800Z"        -- Jan 13, 2013 at 18:00 GMT
    ORGANIZATION
        "Unisyue Technologies Co., Ltd."
    CONTACT-INFO
        ""
    DESCRIPTION
        "Multiprotocol Label Switching Traffic Engineering MIB"
    REVISION
        "201306131800Z"   -- Jan 13, 2013 at 18:00 GMT
    DESCRIPTION
        "Initial version of this MIB."
    ::= { unisCommon 143 }

-- =============================================================================
-- object definition begin
-- =============================================================================
unisMplsTeObjects      OBJECT IDENTIFIER ::= { unisMplsTe 1 }

unisMplsTeScalarGroup  OBJECT IDENTIFIER ::= { unisMplsTeObjects 1 }

unisMplsTeStatus    OBJECT-TYPE
    SYNTAX      TruthValue
    MAX-ACCESS  read-write
    STATUS      current
    DESCRIPTION
        "The global configuration of MPLS(Multiprotocol Label Switching)
        TE(Traffic Engineering)."
    ::= { unisMplsTeScalarGroup 1 }

unisMplsTeRsvpStatus    OBJECT-TYPE
    SYNTAX      TruthValue
    MAX-ACCESS  read-write
    STATUS      current
    DESCRIPTION
        "The global configuration of RSVP(Resource Reservation Protocol)."
    ::= { unisMplsTeScalarGroup 2 }

-- =============================================================================
-- unisMplsTeTable Definition
-- =============================================================================
unisMplsTeTable     OBJECT-TYPE
    SYNTAX      SEQUENCE OF UnisMplsTeEntry
    MAX-ACCESS  not-accessible
    STATUS      current
    DESCRIPTION
        "A table for configuring MPLS TE parameters."
    ::= { unisMplsTeObjects 2 }

unisMplsTeEntry     OBJECT-TYPE
    SYNTAX      UnisMplsTeEntry
    MAX-ACCESS  not-accessible
    STATUS      current
    DESCRIPTION
        "An entry for configuring MPLS TE parameters."
    INDEX
    {
        unisMplsTeIndex
    }
    ::= { unisMplsTeTable 1 }

UnisMplsTeEntry ::=
    SEQUENCE
    {
        unisMplsTeIndex                 Unsigned32,
        unisMplsTeCapability            TruthValue,
        unisMplsTeRowStatus             RowStatus
    }

unisMplsTeIndex     OBJECT-TYPE
    SYNTAX      Unsigned32(1..4294967295)
    MAX-ACCESS  not-accessible
    STATUS      current
    DESCRIPTION
        "Index of TE interface."
    ::= { unisMplsTeEntry 1 }

unisMplsTeCapability    OBJECT-TYPE
    SYNTAX      TruthValue
    MAX-ACCESS  read-create
    STATUS      current
    DESCRIPTION
        "The TE capability of an interface."
    DEFVAL { false }
    ::= { unisMplsTeEntry 2 }

unisMplsTeRowStatus     OBJECT-TYPE
    SYNTAX      RowStatus
    MAX-ACCESS  read-create
    STATUS      current
    DESCRIPTION
        "Operation status of this table entry.  A row entry cannot
        be modified when the value of this object is 'active'."
    ::= { unisMplsTeEntry 3 }
-- =============================================================================
-- End of unisMplsTeTable Definition
-- =============================================================================

-- =============================================================================
-- unisMplsTeRsvpTable Definition
-- =============================================================================
unisMplsTeRsvpTable     OBJECT-TYPE
    SYNTAX      SEQUENCE OF UnisMplsTeRsvpEntry
    MAX-ACCESS  not-accessible
    STATUS      current
    DESCRIPTION
        "A table for configuring RSVP(Resource Reservation Protocol)
        TE parameters."
    ::= { unisMplsTeObjects 3 }

unisMplsTeRsvpEntry     OBJECT-TYPE
    SYNTAX      UnisMplsTeRsvpEntry
    MAX-ACCESS  not-accessible
    STATUS      current
    DESCRIPTION
        "An entry for configuring RSVP TE parameters."
    INDEX
    {
        unisMplsTeRsvpIndex
    }
    ::= { unisMplsTeRsvpTable 1 }

UnisMplsTeRsvpEntry ::=
    SEQUENCE
    {
        unisMplsTeRsvpIndex                 Unsigned32,
        unisMplsTeRsvpCapability            TruthValue,
        unisMplsTeRsvpRowStatus             RowStatus
    }

unisMplsTeRsvpIndex     OBJECT-TYPE
    SYNTAX      Unsigned32(1..4294967295)
    MAX-ACCESS  not-accessible
    STATUS      current
    DESCRIPTION
        "Index of RSVP interface."
    ::= { unisMplsTeRsvpEntry 1 }

unisMplsTeRsvpCapability    OBJECT-TYPE
    SYNTAX      TruthValue
    MAX-ACCESS  read-create
    STATUS      current
    DESCRIPTION
        "The RSVP capability of an interface."
    DEFVAL { false }
    ::= { unisMplsTeRsvpEntry 2 }

unisMplsTeRsvpRowStatus     OBJECT-TYPE
    SYNTAX      RowStatus
    MAX-ACCESS  read-create
    STATUS      current
    DESCRIPTION
        "Operation status of this table entry.  A row entry cannot
        be modified when the value of this object is 'active'."
    ::= { unisMplsTeRsvpEntry 3 }
-- =============================================================================
-- End of unisMplsTeRsvpTable Definition
-- =============================================================================

END
