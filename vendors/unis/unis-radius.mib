-- =================================================================
-- Copyright (c) 2020 Unisyue Technologies Co., Ltd.  All rights reserved.
--
-- Description:
--
-- A configuration management and statistical MIB, includes configuration of
-- RADIUS Server, and statistics about accounting server which complements
-- the IETF standard MIB as described in RFC2620.  In addition, there are four
-- traps supported to notify client the RADIUS Server's down and up state.
--
-- Reference: RFC2866, RADIUS-AUTH-CLIENT-MIB, RADIUS-ACC-CLIENT-MIB
-- Version: V2.6
-- History:
--  V1.0 Initial version 2004-07-13
--  V1.1 2004-10-12 updated by gaolong
--       Set size of DisplayString from 0 to 255.
--  V1.2 2005-03-10 updated by xulei
--       Modified description of this MIB
--       Modified MAX-ACCESS of nodes in unisRdInfoTable
--       Modified description of nodes in unisRdInfoTable
--       Added nodes of unisRdInfoTable
--       Added unisRdAccInfoTable
--       Added unisRadiusAccServerTable
--       Added Traps
--  V1.3 2005-05-08 updated by xulei
--       Modified MAX-ACCESS of unisRdPrimAccState and unisRdSecAccState
--  V1.4 2005-06-03 updated by xulei
--       Modified SYNTAX and DESCRIPTION of unisRdAccPacketUnit
--  V1.5 2008-05-19 updated by yangxu
--       Added nodes of unisRdAccInfoTable
--       Added node of unisRdAcctOnEnable
--       Added node of unisRdAcctOnSendTimes
--       Added node of unisRdAcctOnSendInterval
--  V1.6 2008-07-18 updated by d04528
--       Added nodes of unisRadiusAuthenticating
--       Added node of unisRadiusAuthClient
--       Added node of unisRadiusAuthServerTable
--       Added node of unisRadiusAuthServerEntry
--       Added node of unisRadiusAuthFailureTimes
--       Added node of unisRadiusAuthTimeoutTimes
--       Added node of unisRadiusAuthRejectTimes
--  V1.7 2009-04-30 update by h02978
--       Added node of unisRdSecKey
--       Added node of unisRdSecAccKey
--       Added node of unisRadiusAuthServerUpTrap
--       Added node of unisRadiusAccServerUpTrap
--  V1.8 2009-08-05 update by h02978
--       Added node of unisRadiusAuthErrThreshold
--       Added node of unisRadiusAuthErrTrap
--  V1.9 2010-03-29 Modifyed by x04730
--       Modify SYNTAX of unisRdAccRealTime
--       2010-07-14 Modifyed by x04730
--       Modify SYNTAX of unisRdQuietTime
--       Modify SYNTAX of unisRdAccQuietTime
--       2010-08-26 update by y06401
--       Added unisRadiusSchAuthTable
--       Added unisRadiusSchAccTable
--  V2.0 2010-03-29 Modifyed by y07111
--       Added nodes of unisRadiusStatistic
--       Added node of unisRadiusStatAccReq
--       Added node of unisRadiusStatAccAck
--       Added node of unisRadiusStatLogoutReq
--       Added node of unisRadiusStatLogoutAck
--  V2.1 2011-11-28, Added by xuyonggang
--       Added node of unisRadiusServerTrapVarObjects
--       2012-02-28 Modifyed by y002965
--       Added table of unisRdSecondaryAuthServerTable
--       Added table of unisRdSecondaryAcctServerTable
--       Added node of unisRdPrimVpnName
--       Added node of unisRdSecVpnName
--       Added node of unisRdAuthNasIpAddrType
--       Added node of unisRdAuthNasIpAddr
--       Added node of unisRdPrimAccVpnName
--       Added node of unisRdSecAccVpnName
--       Added node of unisRdAccNasIpAddrType
--       Added node of unisRdAccNasIpAddr
--       Change the length of unisRdSecAccKey
--       Change the length of unisRdAccKey
--       Change the length of unisRdSecKey
--       Change the length of unisRdKey
--  V2.2 2012-10-11, Added by liubo
--       Added node of unisRdAuthNasIpv6Addr
--       Added node of unisRdAccNasIpv6Addr
--       Modified the length of unisRdSecAccKey
--       Modified the length of unisRdAccKey
--       Modified the length of unisRdSecKey
--       Modified the length of unisRdKey
--       Modified the length of unisRdPrimVpnName
--       Modified the length of unisRdSecVpnName
--       Modified the length of unisRdPrimAccVpnName
--       Modified the length of unisRdSecAccVpnName
--       Modified the length of unisRdSecondaryAuthVpnName
--       Modified the length of unisRdSecondaryAccVpnName
--       Modified the length of unisRdSecondaryAuthKey
--       Modified the length of unisRdSecondaryAccKey
--       Modified the default value and description of unisRdAcctOnSendTimes
--  V2.3 2013-03-30, Modified by luyu
--       Modified description of unisRdSecondaryAccUdpPort
--       Modified the default value and description of unisRadiusSchAccPrimUdpPort
--       Modified the default value and description of unisRadiusSchAccSecUdpPort
--  V2.4 2014-06-07, Modified by liubo
--       Modified description of unisRdSecondaryAuthRowStatus
--       Modified description of unisRdSecondaryAccRowStatus
--  V2.5 2016-11-03, Modified by yemingxia
--       Modified the value range of unisRdAccRealTime
--       Added node of unisRdAccRealTimeUnit
--  V2.6 2019-01-12, Modified by yuhua
--       Added node of unisRadiusAuthenticationServerUpTrap
--       Added node of unisRadiusAccountingServerUpTrap
--       Added node of unisRadiusAuthenticationServerDownTrap
--       Added node of unisRadiusAccountingServerDownTrap
-- =================================================================
UNIS-RADIUS-MIB DEFINITIONS ::= BEGIN
    IMPORTS
        unisCommon
            FROM UNIS-OID-MIB
        IpAddress, Integer32, Counter32, OBJECT-TYPE, MODULE-IDENTITY, NOTIFICATION-TYPE,
        Unsigned32,Counter64, TimeTicks
            FROM SNMPv2-SMI
        RowStatus, TruthValue, DisplayString
            FROM SNMPv2-TC
        InetAddressType, InetAddress
            FROM INET-ADDRESS-MIB
        Ipv6Address
            FROM IPV6-TC
        radiusAuthServerIndex, radiusAuthServerAddress, radiusAuthClientServerPortNumber
            FROM RADIUS-AUTH-CLIENT-MIB
        radiusAccServerIndex, radiusAccServerAddress, radiusAccClientServerPortNumber
            FROM RADIUS-ACC-CLIENT-MIB;

    unisRadius MODULE-IDENTITY
    LAST-UPDATED "201901121800Z"            -- January 12, 2019 at 18:00 GMT
    ORGANIZATION
        "Unisyue Technologies Co., Ltd."
    CONTACT-INFO
        ""
    DESCRIPTION
        "The UNIS-RADIUS-MIB contains objects to
        Manage configuration and Monitor running state
        for RADIUS feature."
    REVISION "201901121800Z"        -- January 12, 2019 at 18:00 GMT
    DESCRIPTION
        "Added node of unisRadiusAuthenticationServerUpTrap.
         Added node of unisRadiusAccountingServerUpTrap.
         Added node of unisRadiusAuthenticationServerDownTrap.
         Added node of unisRadiusAccountingServerDownTrap"
    REVISION "201611031800Z"        -- November 3, 2016 at 18:00 GMT
    DESCRIPTION
        "Modified the value range of unisRdAccRealTime.
        Added node of unisRdAccRealTimeUnit"
    REVISION "201406071800Z"        -- June 7, 2014 at 18:00 GMT
    DESCRIPTION
        "Modified description of unisRdSecondaryAuthRowStatus.
        Modified description of unisRdSecondaryAccRowStatus"
    ::= { unisCommon 13 }

    unisRdObjects OBJECT IDENTIFIER ::= { unisRadius 1 }

    unisRdInfoTable  OBJECT-TYPE
        SYNTAX SEQUENCE OF UnisRdInfoEntry
        MAX-ACCESS not-accessible
        STATUS current
        DESCRIPTION
        "The (conceptual) table listing RADIUS authentication servers."
    ::= { unisRdObjects 1 }

    unisRdInfoEntry OBJECT-TYPE
        SYNTAX UnisRdInfoEntry
        MAX-ACCESS not-accessible
        STATUS current
        DESCRIPTION
        "An entry (conceptual row) representing a RADIUS authentication server."
        INDEX { unisRdGroupName }
    ::= { unisRdInfoTable 1 }

    UnisRdInfoEntry ::= SEQUENCE {
        unisRdGroupName          DisplayString,
        unisRdPrimAuthIp         IpAddress,
        unisRdPrimUdpPort        Integer32,
        unisRdPrimState          INTEGER,
        unisRdSecAuthIp          IpAddress,
        unisRdSecUdpPort         Integer32,
        unisRdSecState           INTEGER,
        unisRdKey                DisplayString,
        unisRdRetry              Integer32,
        unisRdTimeout            Integer32,
        unisRdPrimAuthIpAddrType InetAddressType,
        unisRdPrimAuthIpAddr     InetAddress,
        unisRdSecAuthIpAddrType  InetAddressType,
        unisRdSecAuthIpAddr      InetAddress,
        unisRdServerType         INTEGER,
        unisRdQuietTime          Integer32,
        unisRdUserNameFormat     INTEGER,
        unisRdRowStatus          RowStatus,
        unisRdSecKey             DisplayString,
        unisRdPrimVpnName        DisplayString,
        unisRdSecVpnName         DisplayString,
        unisRdAuthNasIpAddrType  InetAddressType,
        unisRdAuthNasIpAddr      IpAddress,
        unisRdAuthNasIpv6Addr    Ipv6Address
        }

    unisRdGroupName OBJECT-TYPE
        SYNTAX DisplayString(SIZE (1..32))
        MAX-ACCESS not-accessible
        STATUS current
        DESCRIPTION
        "The name of the RADIUS authentication group referred to in this table
        entry."
    ::= { unisRdInfoEntry 1 }


    unisRdPrimAuthIp OBJECT-TYPE
        SYNTAX IpAddress
        MAX-ACCESS read-create
        STATUS deprecated
        DESCRIPTION
        "The IP address of primary RADIUS authentication server."
    ::= { unisRdInfoEntry 2 }

    unisRdPrimUdpPort OBJECT-TYPE
        SYNTAX Integer32
        MAX-ACCESS read-create
        STATUS current
        DESCRIPTION
        "The UDP port the client is using to send requests to
        primary RADIUS authentication server.  Default value is 1812."
    ::= { unisRdInfoEntry 3 }

    unisRdPrimState OBJECT-TYPE
        SYNTAX INTEGER
        {
            active(1),
            block(2)
        }
        MAX-ACCESS read-create
        STATUS current
        DESCRIPTION
        "The state of the primary RADIUS authentication server.
        1 (active) The primary authentication server is in active state.
        2 (block)  The primary authentication server is in block state."
    ::= { unisRdInfoEntry 4 }

    unisRdSecAuthIp OBJECT-TYPE
        SYNTAX IpAddress
        MAX-ACCESS read-create
        STATUS deprecated
        DESCRIPTION
        "The IP address of secondary RADIUS authentication server."
    ::= { unisRdInfoEntry 5 }

    unisRdSecUdpPort OBJECT-TYPE
        SYNTAX Integer32
        MAX-ACCESS read-create
        STATUS current
        DESCRIPTION
        "The UDP port the client is using to send requests to
        secondary RADIUS authentication server.  Default value is 1812."
    ::= { unisRdInfoEntry 6 }

    unisRdSecState OBJECT-TYPE
        SYNTAX INTEGER
        {
            active(1),
            block(2)
        }
        MAX-ACCESS read-create
        STATUS current
        DESCRIPTION
        "The state of the secondary RADIUS authentication server.
        1 (active) The secondary authentication server is in active state.
        2 (block)  The secondary authentication server is in block state."
    ::= { unisRdInfoEntry 7 }

    unisRdKey OBJECT-TYPE
        SYNTAX DisplayString(SIZE (0..64))
        MAX-ACCESS read-create
        STATUS current
        DESCRIPTION
        "The secret shared between the RADIUS client and RADIUS
        authentication server used in encoding and decoding
        sensitive data.
        When read, unisRdKey always returns an Octet String of length zero."
    ::= { unisRdInfoEntry 8 }

    unisRdRetry OBJECT-TYPE
        SYNTAX Integer32
        MAX-ACCESS read-create
        STATUS current
        DESCRIPTION
        "The number of attempts the client will make when trying to send
        requests to a server before it will consider the attempt failed.
        Default value is 3."
    ::= { unisRdInfoEntry 9 }

    unisRdTimeout OBJECT-TYPE
        SYNTAX Integer32
        MAX-ACCESS read-create
        STATUS current
        DESCRIPTION
        "The timeout value the client will use when sending requests to a server.
        The unit is second.  Default value is 3."
    ::= { unisRdInfoEntry 10 }

    unisRdPrimAuthIpAddrType OBJECT-TYPE
        SYNTAX InetAddressType
        MAX-ACCESS read-create
        STATUS current
        DESCRIPTION
        "The IP addresses type (IPv4 or IPv6) of primary RADIUS authentication
        server."
    ::= { unisRdInfoEntry 11 }

    unisRdPrimAuthIpAddr OBJECT-TYPE
        SYNTAX InetAddress
        MAX-ACCESS read-create
        STATUS current
        DESCRIPTION
        "The IP address of primary RADIUS authentication server."
    ::= { unisRdInfoEntry 12 }

    unisRdSecAuthIpAddrType OBJECT-TYPE
        SYNTAX InetAddressType
        MAX-ACCESS read-create
        STATUS current
        DESCRIPTION
        "The IP addresses type (IPv4 or IPv6) of secondary RADIUS authentication
        server."
    ::= { unisRdInfoEntry 13 }

    unisRdSecAuthIpAddr OBJECT-TYPE
        SYNTAX InetAddress
        MAX-ACCESS read-create
        STATUS current
        DESCRIPTION
        "The IP address of secondary RADIUS authentication server."
    ::= { unisRdInfoEntry 14 }

    unisRdServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { unisRdInfoEntry 15 }

    unisRdQuietTime OBJECT-TYPE
        SYNTAX Integer32 (0..255)
        MAX-ACCESS read-create
        STATUS current
        DESCRIPTION
        "The time for server returning active.  The unit is minute.
         When the value is 0, the server state retains active.  Default value is 5."
    ::= { unisRdInfoEntry 16 }

    unisRdUserNameFormat OBJECT-TYPE
        SYNTAX INTEGER
        {
            withoutdomain(1),
            withdomain(2),
            keeporignal(3)
        }
        MAX-ACCESS read-create
        STATUS current
        DESCRIPTION
        "Specify the user-name format that is sent to RADIUS server.
        1 (withoutdomain) - send the user-name without domain.
        2 (withdomain) - send the user-name with domain.
        3 (keeporignal) - send the user-name as it is entered.
        Default format is withdomain."
    ::= { unisRdInfoEntry 17 }


    unisRdRowStatus   OBJECT-TYPE
        SYNTAX   RowStatus
        MAX-ACCESS  read-create
        STATUS   current
        DESCRIPTION
        "This object is responsible for managing the creation, deletion and
        modification of rows, which support active status and CreateAndGo,
        Destroy operation.  To create a new row, unisRdGroupName must be specified.
        To destroy an existent row, the unisRdGroupName MUST NOT be referred by
        unisDomainTable in unisDomainRadiusGroupName column."
    ::= { unisRdInfoEntry 18 }


    unisRdSecKey OBJECT-TYPE
        SYNTAX DisplayString(SIZE (0..64))
        MAX-ACCESS read-create
        STATUS current
        DESCRIPTION
        "The secret shared between the RADIUS client and the secondary RADIUS
        authentication server used in encoding and decoding
        sensitive data.
        When read, unisRdSecKey always returns an Octet String of length zero."
    ::= { unisRdInfoEntry 19 }

    unisRdPrimVpnName OBJECT-TYPE
        SYNTAX DisplayString(SIZE (0..31))
        MAX-ACCESS  read-create
        STATUS current
        DESCRIPTION
        "The human-readable name of the VPN in which the primary RADIUS
        authentication server is placed."
    ::= { unisRdInfoEntry 20 }

    unisRdSecVpnName OBJECT-TYPE
        SYNTAX DisplayString(SIZE (0..31))
        MAX-ACCESS  read-create
        STATUS current
        DESCRIPTION
        "The human-readable name of the VPN in which the secondary RADIUS
        authentication server is placed."
    ::= { unisRdInfoEntry 21 }

    unisRdAuthNasIpAddrType OBJECT-TYPE
        SYNTAX InetAddressType
        MAX-ACCESS read-create
        STATUS current
        DESCRIPTION
        "The type (IPv4 or IPv6) of the source IP used to communicate with
        RADIUS authentication server."
    ::= { unisRdInfoEntry 22 }

    unisRdAuthNasIpAddr OBJECT-TYPE
        SYNTAX IpAddress
        MAX-ACCESS read-create
        STATUS current
        DESCRIPTION
        "The source IPv4 address used to communicate with the RADIUS authentication
        server."
    ::= { unisRdInfoEntry 23 }

    unisRdAuthNasIpv6Addr OBJECT-TYPE
        SYNTAX Ipv6Address
        MAX-ACCESS read-create
        STATUS current
        DESCRIPTION
        "The source IPv6 address used to communicate with the RADIUS authentication
        server."
    ::= { unisRdInfoEntry 24 }

-- ***********************************************************************
--
--  Accounting Server Table
--
-- ***********************************************************************
    unisRdAccInfoTable  OBJECT-TYPE
        SYNTAX SEQUENCE OF UnisRdAccInfoEntry
        MAX-ACCESS not-accessible
        STATUS current
        DESCRIPTION
        "The (conceptual) table listing RADIUS accounting servers."
    ::= { unisRdObjects 2 }

    unisRdAccInfoEntry OBJECT-TYPE
        SYNTAX UnisRdAccInfoEntry
        MAX-ACCESS not-accessible
        STATUS current
        DESCRIPTION
        "An entry (conceptual row) representing a RADIUS accounting server."
        INDEX { unisRdAccGroupName }
    ::= { unisRdAccInfoTable 1 }


    UnisRdAccInfoEntry ::= SEQUENCE {
        unisRdAccGroupName           DisplayString,
        unisRdPrimAccIpAddrType      InetAddressType,
        unisRdPrimAccIpAddr          InetAddress,
        unisRdPrimAccUdpPort         Integer32,
        unisRdPrimAccState           INTEGER,
        unisRdSecAccIpAddrType       InetAddressType,
        unisRdSecAccIpAddr           InetAddress,
        unisRdSecAccUdpPort          Integer32,
        unisRdSecAccState            INTEGER,
        unisRdAccKey                 DisplayString,
        unisRdAccRetry               Integer32,
        unisRdAccTimeout             Integer32,
        unisRdAccServerType          INTEGER,
        unisRdAccQuietTime           Integer32,
        unisRdAccFailureAction       INTEGER,
        unisRdAccRealTime            Integer32,
        unisRdAccRealTimeRetry       Integer32,
        unisRdAccSaveStopPktEnable   TruthValue,
        unisRdAccStopRetry           Integer32,
        unisRdAccDataFlowUnit        INTEGER,
        unisRdAccPacketUnit          INTEGER,
        unisRdAccRowStatus           RowStatus,
        unisRdAcctOnEnable           TruthValue,
        unisRdAcctOnSendTimes        Integer32,
        unisRdAcctOnSendInterval     Integer32,
        unisRdSecAccKey              DisplayString,
        unisRdPrimAccVpnName         DisplayString,
        unisRdSecAccVpnName          DisplayString,
        unisRdAccNasIpAddrType       InetAddressType,
        unisRdAccNasIpAddr           IpAddress,
        unisRdAccNasIpv6Addr         Ipv6Address,
        unisRdAccRealTimeUnit        INTEGER
        }

    unisRdAccGroupName OBJECT-TYPE
        SYNTAX DisplayString(SIZE (1..32))
        MAX-ACCESS not-accessible
        STATUS current
        DESCRIPTION
        "The name of the RADIUS group referred to in this table entry."
    ::= { unisRdAccInfoEntry 1 }

    unisRdPrimAccIpAddrType OBJECT-TYPE
        SYNTAX      InetAddressType
        MAX-ACCESS  read-create
        STATUS      current
        DESCRIPTION
        "The IP addresses type (IPv4 or IPv6) of primary RADIUS accounting server."
    ::= { unisRdAccInfoEntry 2 }

    unisRdPrimAccIpAddr OBJECT-TYPE
        SYNTAX      InetAddress
        MAX-ACCESS  read-create
        STATUS      current
        DESCRIPTION
        "The IP address of primary RADIUS accounting server."
    ::= { unisRdAccInfoEntry 3 }

    unisRdPrimAccUdpPort OBJECT-TYPE
        SYNTAX      Integer32
        MAX-ACCESS  read-create
        STATUS      current
        DESCRIPTION
        "The UDP port the client is using to send requests to primary
        RADIUS accounting server.  Default value is 1813."
    ::= { unisRdAccInfoEntry 4 }

    unisRdPrimAccState OBJECT-TYPE
        SYNTAX INTEGER
        {
            active(1),
            block(2)
        }
        MAX-ACCESS  read-create
        STATUS      current
        DESCRIPTION
        "The state of the primary RADIUS accounting server.
        1 (active) The primary accounting server is in active state.
        2 (block)  The primary accounting server is in block state."
    ::= { unisRdAccInfoEntry 5 }

    unisRdSecAccIpAddrType OBJECT-TYPE
        SYNTAX      InetAddressType
        MAX-ACCESS  read-create
        STATUS      current
        DESCRIPTION
        "The IP addresses type (IPv4 or IPv6) of secondary RADIUS accounting
        server."
    ::= { unisRdAccInfoEntry 6 }

    unisRdSecAccIpAddr OBJECT-TYPE
        SYNTAX      InetAddress
        MAX-ACCESS  read-create
        STATUS      current
        DESCRIPTION
        "The IP address of secondary RADIUS accounting server."
    ::= { unisRdAccInfoEntry 7 }

    unisRdSecAccUdpPort OBJECT-TYPE
        SYNTAX      Integer32
        MAX-ACCESS  read-create
        STATUS      current
        DESCRIPTION
        "The UDP port the client is using to send requests to secondary
        RADIUS accounting server.  Default value is 1813."
    ::= { unisRdAccInfoEntry 8 }

    unisRdSecAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { unisRdAccInfoEntry 9 }

    unisRdAccKey OBJECT-TYPE
        SYNTAX DisplayString(SIZE (0..64))
        MAX-ACCESS read-create
        STATUS current
        DESCRIPTION
        "The secret shared between the RADIUS client and RADIUS
        accounting server used in encoding and decoding sensitive data.
        When read, unisRdAccKey always returns an Octet String of length zero."
    ::= { unisRdAccInfoEntry 10 }


    unisRdAccRetry OBJECT-TYPE
        SYNTAX Integer32
        MAX-ACCESS read-create
        STATUS current
        DESCRIPTION
        "The number of attempt the client will make when trying to send
        requests to a server before it will consider the attempt failed.
        Default value is 3."
    ::= { unisRdAccInfoEntry 11 }

    unisRdAccTimeout OBJECT-TYPE
        SYNTAX Integer32
        MAX-ACCESS read-create
        STATUS current
        DESCRIPTION
        "The timeout value the client will use when sending requests to a server.
        The unit is second.  Default value is 3."
    ::= { unisRdAccInfoEntry 12 }

    unisRdAccServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { unisRdAccInfoEntry 13 }

    unisRdAccQuietTime OBJECT-TYPE
        SYNTAX Integer32 (0..255)
        MAX-ACCESS read-create
        STATUS current
        DESCRIPTION
        "The time for server returning active.  The unit is minute.
         When the value is 0, the server state retains active.  Default value is 5."
    ::= { unisRdAccInfoEntry 14 }

    unisRdAccFailureAction OBJECT-TYPE
        SYNTAX INTEGER
        {
            ignore(1),
            reject(2)
        }
        MAX-ACCESS read-create
        STATUS current
        DESCRIPTION
        "Defines the action that authentication should take if
        authentication succeeds but the associated accounting start
        fails.
        1 (ignore) - treat as authentication success; ignore
            accounting start failure.
        2 (reject) - treat as authentication failed if
            corresponding accounting start fails.
        Default value is 1(reject)."
    ::= { unisRdAccInfoEntry 15 }

    unisRdAccRealTime OBJECT-TYPE
        SYNTAX Integer32 (0..71582)
        MAX-ACCESS read-create
        STATUS current
        DESCRIPTION
        "Interval of realtime-accounting packets.
        The unit is defined by unisRdAccRealTimeUnit.
        When the value is 0, the device doesn't send realtime-accounting
        packets.  Default value is 12 minutes."
    ::= { unisRdAccInfoEntry 16 }

    unisRdAccRealTimeRetry OBJECT-TYPE
        SYNTAX Integer32 (1..255)
        MAX-ACCESS read-create
        STATUS current
        DESCRIPTION
        "The number of attempt the client will make when trying to send
        realtime-accounting packet to accounting server before it will
        consider the attempt failed.  Default value is 5."
        DEFVAL { 5 }
    ::= { unisRdAccInfoEntry 17 }

    unisRdAccSaveStopPktEnable OBJECT-TYPE
        SYNTAX TruthValue
        MAX-ACCESS read-create
        STATUS current
        DESCRIPTION
        "The control of whether save stop-accounting packet in local buffer
        and resend later when the accounting server doesn't respond.  When
        SaveStopPktEnable is set to false, the value of AccStopRetry will be
        ignored.  Default value is true."
    ::= { unisRdAccInfoEntry 18 }

    unisRdAccStopRetry OBJECT-TYPE
        SYNTAX Integer32 (10..65535)
        MAX-ACCESS read-create
        STATUS current
        DESCRIPTION
        "The number of attempt the client will make when trying to send
        stop-accounting packet to accounting server.  Default value is 500."
    ::= { unisRdAccInfoEntry 19 }

    unisRdAccDataFlowUnit OBJECT-TYPE
        SYNTAX INTEGER
        {
            byte(1),
            kiloByte(2),
            megaByte(3),
            gigaByte(4)
        }
        MAX-ACCESS read-create
        STATUS current
        DESCRIPTION
        "Specify data flow format that is sent to RADIUS server.  The value
        SHOULD be set the same as the value of corresponding server.
        1 (byte) -  Specify 'byte' as the unit of data flow.
        2 (kiloByte) - Specify 'kilo-byte' as the unit of data flow.
        3 (megaByte) - Specify 'mega-byte' as the unit of data flow.
        4 (gigaByte) - Specify 'giga-byte' as the unit of data flow.
        Default value is 1."
    ::= { unisRdAccInfoEntry 20 }

    unisRdAccPacketUnit OBJECT-TYPE
        SYNTAX INTEGER
        {
            onePacket(1),
            kiloPacket(2),
            megaPacket(3),
            gigaPacket(4)
        }
        MAX-ACCESS read-create
        STATUS current
        DESCRIPTION
        "Specify packet format that is sent to RADIUS server.  The value
        SHOULD be set the same as the value of corresponding server.
        1 (onePacket)  - Specify 'one-packet' as the unit of packet.
        2 (kiloPacket) - Specify 'kilo-packet' as the unit of packet.
        3 (megaPacket) - Specify 'mega-packet' as the unit of packet.
        4 (gigaPacket) - Specify 'giga-packet' as the unit of packet.
        Default value is 1."
    ::= { unisRdAccInfoEntry 21 }

    unisRdAccRowStatus   OBJECT-TYPE
        SYNTAX   RowStatus
        MAX-ACCESS  read-create
        STATUS   current
        DESCRIPTION
        "This object is responsible for managing the creation, deletion and
        modification of rows, which support active status and CreateAndGo,
        Destroy operation.  To create a new row, unisRdAccGroupName must be specified.
        To destroy an existent row, the unisRdAccGroupName MUST NOT be referred by
        unisDomainTable in unisDomainRadiusGroupName column."
    ::= { unisRdAccInfoEntry 22 }

    unisRdAcctOnEnable OBJECT-TYPE
        SYNTAX TruthValue
        MAX-ACCESS read-create
        STATUS current
        DESCRIPTION
        "The control of Accounting-On function.  The Accounting-On function is
        used by the client to mark the start of accounting (for example, upon
        booting) by sending Accounting-On packets and to mark the end of
        accounting (for example, just before a scheduled reboot) by sending
        Accounting-Off packets.  Default value is false."
    ::= { unisRdAccInfoEntry 23 }

    unisRdAcctOnSendTimes OBJECT-TYPE
        SYNTAX Integer32
        MAX-ACCESS read-create
        STATUS current
        DESCRIPTION
        "The number of Accounting-On packets the client will send before it
        considers the accounting server failed.  Default value is 50."
        DEFVAL { 50 }
    ::= { unisRdAccInfoEntry 24 }

    unisRdAcctOnSendInterval OBJECT-TYPE
        SYNTAX Integer32
        MAX-ACCESS read-create
        STATUS current
        DESCRIPTION
        "Interval of Accounting-On packets.  The unit is second.
        Default value is 3."
        DEFVAL { 3 }
    ::= { unisRdAccInfoEntry 25 }


    unisRdSecAccKey OBJECT-TYPE
        SYNTAX DisplayString(SIZE (0..64))
        MAX-ACCESS read-create
        STATUS current
        DESCRIPTION
        "The secret shared between the RADIUS client and the secondary RADIUS
        accounting server used in encoding and decoding sensitive data.
        When read, unisRdSecAccKey always returns an Octet String of length zero."
    ::= { unisRdAccInfoEntry 26 }

    unisRdPrimAccVpnName OBJECT-TYPE
        SYNTAX DisplayString(SIZE (0..31))
        MAX-ACCESS  read-create
        STATUS current
        DESCRIPTION
        "The human-readable name of the VPN in which the primary RADIUS
        accounting server is placed."
    ::= { unisRdAccInfoEntry 27 }

    unisRdSecAccVpnName OBJECT-TYPE
        SYNTAX DisplayString(SIZE (0..31))
        MAX-ACCESS  read-create
        STATUS current
        DESCRIPTION
        "The human-readable name of the VPN in which the secondary RADIUS
        accounting server is placed."
    ::= { unisRdAccInfoEntry 28 }

    unisRdAccNasIpAddrType OBJECT-TYPE
        SYNTAX InetAddressType
        MAX-ACCESS read-create
        STATUS current
        DESCRIPTION
        "The type (IPv4 or IPv6) of the source IP used to communicate with
        RADIUS accounting server."
    ::= { unisRdAccInfoEntry 29 }

    unisRdAccNasIpAddr OBJECT-TYPE
        SYNTAX IpAddress
        MAX-ACCESS read-create
        STATUS current
        DESCRIPTION
        "The source IPv4 address used to communicate with the RADIUS accounting
        server."
    ::= { unisRdAccInfoEntry 30 }

    unisRdAccNasIpv6Addr OBJECT-TYPE
        SYNTAX Ipv6Address
        MAX-ACCESS read-create
        STATUS current
        DESCRIPTION
        "The source IPv6 address used to communicate with the RADIUS accounting
        server."
    ::= { unisRdAccInfoEntry 31 }

    unisRdAccRealTimeUnit OBJECT-TYPE
        SYNTAX INTEGER
        {
            minute(0),
            second(1)
        }
        MAX-ACCESS read-create
        STATUS current
        DESCRIPTION
        "The interval unit of realtime-accounting packets.
        0  - minute.
        1  - second."
        DEFVAL { minute }
    ::= { unisRdAccInfoEntry 32 }

-- ***********************************************************************
--
--  Global configurations
--
-- ***********************************************************************
    unisRadiusGlobalConfig OBJECT IDENTIFIER ::= { unisRdObjects 3 }

    unisRadiusAuthErrThreshold OBJECT-TYPE
        SYNTAX Unsigned32 (1..100)
        UNITS "percentage"
        MAX-ACCESS read-write
        STATUS current
        DESCRIPTION
            "The threshold of authentication failure trap.  A trap will be sent
            when the percent of the unsuccessful authentication exceeds this threshold."
        DEFVAL { 30 }
        ::= { unisRadiusGlobalConfig 1 }


-- ***********************************************************************
--
--  Secondary Authentication Server Table
--
-- ***********************************************************************
    unisRdSecondaryAuthServerTable  OBJECT-TYPE
        SYNTAX SEQUENCE OF UnisRdSecondaryAuthServerEntry
        MAX-ACCESS not-accessible
        STATUS current
        DESCRIPTION
        "The (conceptual) table listing RADIUS secondary authentication servers."
    ::= { unisRdObjects 4 }

    unisRdSecondaryAuthServerEntry OBJECT-TYPE
        SYNTAX UnisRdSecondaryAuthServerEntry
        MAX-ACCESS not-accessible
        STATUS current
        DESCRIPTION
        "An entry (conceptual row) representing a RADIUS secondary authentication server."
        INDEX { unisRdGroupName, unisRdSecondaryAuthIpAddrType, unisRdSecondaryAuthIpAddr,
                unisRdSecondaryAuthVpnName, unisRdSecondaryAuthUdpPort }
    ::= { unisRdSecondaryAuthServerTable 1 }

    UnisRdSecondaryAuthServerEntry ::= SEQUENCE {
        unisRdSecondaryAuthIpAddrType       InetAddressType,
        unisRdSecondaryAuthIpAddr           InetAddress,
        unisRdSecondaryAuthVpnName          DisplayString,
        unisRdSecondaryAuthUdpPort          Integer32,
        unisRdSecondaryAuthState            INTEGER,
        unisRdSecondaryAuthKey              DisplayString,
        unisRdSecondaryAuthRowStatus        RowStatus
        }

    unisRdSecondaryAuthIpAddrType OBJECT-TYPE
        SYNTAX      InetAddressType
        MAX-ACCESS  not-accessible
        STATUS      current
        DESCRIPTION
        "The IP addresses type (IPv4 or IPv6) of secondary RADIUS authentication server."
    ::= { unisRdSecondaryAuthServerEntry 1 }

    unisRdSecondaryAuthIpAddr OBJECT-TYPE
        SYNTAX      InetAddress
        MAX-ACCESS  not-accessible
        STATUS      current
        DESCRIPTION
        "The IP address of secondary RADIUS authentication server."
    ::= { unisRdSecondaryAuthServerEntry 2 }

    unisRdSecondaryAuthVpnName OBJECT-TYPE
        SYNTAX DisplayString(SIZE (0..31))
        MAX-ACCESS  not-accessible
        STATUS current
        DESCRIPTION
        "The human-readable name of the VPN in which the secondary RADIUS
        authentication server is placed."
    ::= { unisRdSecondaryAuthServerEntry 3 }

    unisRdSecondaryAuthUdpPort OBJECT-TYPE
        SYNTAX      Integer32(1..65535)
        MAX-ACCESS  not-accessible
        STATUS      current
        DESCRIPTION
        "The UDP port the client is using to send requests to secondary
        RADIUS authentication server.  Default value is 1812."
    ::= { unisRdSecondaryAuthServerEntry 4 }

    unisRdSecondaryAuthState OBJECT-TYPE
        SYNTAX INTEGER
        {
            active(1),
            block(2)
        }
        MAX-ACCESS  read-create
        STATUS      current
        DESCRIPTION
        "The state of the secondary RADIUS authentication server.
        1 (active) The secondary authentication server is in active state.
        2 (block)  The secondary authentication server is in block state."
    ::= { unisRdSecondaryAuthServerEntry 5 }

    unisRdSecondaryAuthKey OBJECT-TYPE
        SYNTAX DisplayString(SIZE (0..64))
        MAX-ACCESS read-create
        STATUS current
        DESCRIPTION
        "The secret shared between the RADIUS client and the secondary RADIUS
        authentication server used in encoding and decoding sensitive data.
        When read, unisRdSecondaryAuthKey always returns an Octet String of length zero."
    ::= { unisRdSecondaryAuthServerEntry 6 }

    unisRdSecondaryAuthRowStatus   OBJECT-TYPE
        SYNTAX   RowStatus
        MAX-ACCESS  read-create
        STATUS   current
        DESCRIPTION
        "This object is responsible for managing the creation, deletion and
        modification of rows, which support active status and CreateAndGo,
        Destroy operation.  To create a new row, unisRdGroupName must be specified.
        The number of rows with the same unisRdGroupName can't be more than 16."
    ::= { unisRdSecondaryAuthServerEntry 7 }

-- ***********************************************************************
--
--  Secondary Accounting Server Table
--
-- ***********************************************************************
    unisRdSecondaryAccServerTable  OBJECT-TYPE
        SYNTAX SEQUENCE OF UnisRdSecondaryAccServerEntry
        MAX-ACCESS not-accessible
        STATUS current
        DESCRIPTION
        "The (conceptual) table listing RADIUS secondary accounting servers."
    ::= { unisRdObjects 5 }

    unisRdSecondaryAccServerEntry OBJECT-TYPE
        SYNTAX UnisRdSecondaryAccServerEntry
        MAX-ACCESS not-accessible
        STATUS current
        DESCRIPTION
        "An entry (conceptual row) representing a RADIUS secondary accounting server."
        INDEX { unisRdAccGroupName, unisRdSecondaryAccIpAddrType, unisRdSecondaryAccIpAddr,
                unisRdSecondaryAccVpnName, unisRdSecondaryAccUdpPort }
    ::= { unisRdSecondaryAccServerTable 1 }

    UnisRdSecondaryAccServerEntry ::= SEQUENCE {
        unisRdSecondaryAccIpAddrType       InetAddressType,
        unisRdSecondaryAccIpAddr           InetAddress,
        unisRdSecondaryAccVpnName          DisplayString,
        unisRdSecondaryAccUdpPort          Integer32,
        unisRdSecondaryAccState            INTEGER,
        unisRdSecondaryAccKey              DisplayString,
        unisRdSecondaryAccRowStatus        RowStatus
        }

    unisRdSecondaryAccIpAddrType OBJECT-TYPE
        SYNTAX      InetAddressType
        MAX-ACCESS  not-accessible
        STATUS      current
        DESCRIPTION
        "The IP addresses type (IPv4 or IPv6) of secondary RADIUS accounting server."
    ::= { unisRdSecondaryAccServerEntry 1 }

    unisRdSecondaryAccIpAddr OBJECT-TYPE
        SYNTAX      InetAddress
        MAX-ACCESS  not-accessible
        STATUS      current
        DESCRIPTION
        "The IP address of secondary RADIUS accounting server."
    ::= { unisRdSecondaryAccServerEntry 2 }

    unisRdSecondaryAccVpnName OBJECT-TYPE
        SYNTAX DisplayString(SIZE (0..31))
        MAX-ACCESS  not-accessible
        STATUS current
        DESCRIPTION
        "The human-readable name of the VPN in which the secondary RADIUS
        accounting server is placed."
    ::= { unisRdSecondaryAccServerEntry 3 }

    unisRdSecondaryAccUdpPort OBJECT-TYPE
        SYNTAX      Integer32(1..65535)
        MAX-ACCESS  not-accessible
        STATUS      current
        DESCRIPTION
        "The UDP port the client is using to send requests to secondary
        RADIUS accounting server.  Default value is 1813."
    ::= { unisRdSecondaryAccServerEntry 4 }

    unisRdSecondaryAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { unisRdSecondaryAccServerEntry 5 }

    unisRdSecondaryAccKey OBJECT-TYPE
        SYNTAX DisplayString(SIZE (0..64))
        MAX-ACCESS read-create
        STATUS current
        DESCRIPTION
        "The secret shared between the RADIUS client and the secondary RADIUS
        accounting server used in encoding and decoding sensitive data.
        When read, unisRdSecondaryAccKey always returns an Octet String of length zero."
    ::= { unisRdSecondaryAccServerEntry 6 }

    unisRdSecondaryAccRowStatus   OBJECT-TYPE
        SYNTAX   RowStatus
        MAX-ACCESS  read-create
        STATUS   current
        DESCRIPTION
        "This object is responsible for managing the creation, deletion and
        modification of rows, which support active status and CreateAndGo,
        Destroy operation.  To create a new row, unisRdAccGroupName must be specified.
        The number of rows with the same unisRdAccGroupName can't be more than 16."
    ::= { unisRdSecondaryAccServerEntry 7 }


-- ***********************************************************************
--
--  Supplement to RFC2620 RADIUS-ACC-CLIENT-MIB
--
-- ***********************************************************************

    unisRadiusAccounting OBJECT IDENTIFIER ::= { unisRadius 2 }

    unisRadiusAccClient OBJECT IDENTIFIER ::= { unisRadiusAccounting 1 }

    unisRadiusAccServerTable OBJECT-TYPE
        SYNTAX  SEQUENCE OF UnisRadiusAccServerEntry
        MAX-ACCESS  not-accessible
        STATUS  current
        DESCRIPTION
        "The (conceptual) table listing the RADIUS accounting
        servers with which the client shares a secret."
    ::= { unisRadiusAccClient 1 }

    unisRadiusAccServerEntry OBJECT-TYPE
        SYNTAX  UnisRadiusAccServerEntry
        MAX-ACCESS  not-accessible
        STATUS  current
        DESCRIPTION
        "An entry (conceptual row) representing a RADIUS accounting
        server with which a client shares a secret."
        INDEX { radiusAccServerIndex }
    ::= { unisRadiusAccServerTable 1 }

    UnisRadiusAccServerEntry ::= SEQUENCE {
        unisRadiusAccClientStartRequests         Counter32,
        unisRadiusAccClientStartResponses        Counter32,
        unisRadiusAccClientInterimRequests       Counter32,
        unisRadiusAccClientInterimResponses      Counter32,
        unisRadiusAccClientStopRequests          Counter32,
        unisRadiusAccClientStopResponses         Counter32 }

    unisRadiusAccClientStartRequests   OBJECT-TYPE
        SYNTAX  Counter32
        MAX-ACCESS  read-only
        STATUS  current
        DESCRIPTION
        "The number of RADIUS accounting start request sent to this
        server."
    ::= { unisRadiusAccServerEntry  1 }

    unisRadiusAccClientStartResponses   OBJECT-TYPE
        SYNTAX  Counter32
        MAX-ACCESS  read-only
        STATUS  current
        DESCRIPTION
        "The number of RADIUS accounting start response received
        from this server."
    ::= { unisRadiusAccServerEntry  2 }

    unisRadiusAccClientInterimRequests   OBJECT-TYPE
        SYNTAX  Counter32
        MAX-ACCESS  read-only
        STATUS  current
        DESCRIPTION
        "The number of RADIUS interim accounting request sent to
        this server."
    ::= { unisRadiusAccServerEntry  3 }

    unisRadiusAccClientInterimResponses   OBJECT-TYPE
        SYNTAX  Counter32
        MAX-ACCESS  read-only
        STATUS  current
        DESCRIPTION
        "The number of RADIUS interim accounting response received
        from this server."
    ::= { unisRadiusAccServerEntry  4 }

    unisRadiusAccClientStopRequests   OBJECT-TYPE
        SYNTAX  Counter32
        MAX-ACCESS  read-only
        STATUS  current
        DESCRIPTION
        "The number of RADIUS stop accounting request sent to
        this RADIUS server."
    ::= { unisRadiusAccServerEntry  5 }

    unisRadiusAccClientStopResponses   OBJECT-TYPE
        SYNTAX  Counter32
        MAX-ACCESS  read-only
        STATUS  current
        DESCRIPTION
        "The number of RADIUS stop accounting response received
        from this server."
    ::= { unisRadiusAccServerEntry  6 }

--------------------------------------------------------------
-- Traps
--------------------------------------------------------------

-- All trap definitions should be placed under this object.
    unisRadiusServerTrap OBJECT IDENTIFIER ::= { unisRadius 3 }

    unisRadiusAuthServerDownTrap NOTIFICATION-TYPE
        OBJECTS     { radiusAuthServerAddress,
                     radiusAuthClientServerPortNumber,
                     unisRadiusServerFirstTrapTime}
        STATUS      obsolete
        DESCRIPTION
        "This trap is generated when the authentication RADIUS server
        does not respond to the client's requests for a period of time.
        This node is replaced by unisRadiusAuthenticationServerDownTrap."
    ::= { unisRadiusServerTrap 1 }

    unisRadiusAccServerDownTrap NOTIFICATION-TYPE
        OBJECTS     { radiusAccServerAddress,
                     radiusAccClientServerPortNumber,
                     unisRadiusServerFirstTrapTime}
        STATUS      obsolete
        DESCRIPTION
        "This trap is generated when the accounting RADIUS server
        does not respond to the client's requests for a period of time.
        This node is replaced by unisRadiusAccountingServerDownTrap."
    ::= { unisRadiusServerTrap 2 }

    unisRadiusServerTrapPrefix OBJECT IDENTIFIER ::= { unisRadiusServerTrap 0 }

    unisRadiusAuthServerUpTrap NOTIFICATION-TYPE
        OBJECTS     { radiusAuthServerAddress,
                     radiusAuthClientServerPortNumber,
                     unisRadiusServerFirstTrapTime }
        STATUS      obsolete
        DESCRIPTION
        "This trap is generated when the device finds that the state of the
        RADIUS authentication server changes from unreachable to reachable.
        This node is replaced by unisRadiusAuthenticationServerUpTrap."
    ::= { unisRadiusServerTrapPrefix 1 }

    unisRadiusAccServerUpTrap NOTIFICATION-TYPE
        OBJECTS     { radiusAccServerAddress,
                     radiusAccClientServerPortNumber,
                     unisRadiusServerFirstTrapTime }
        STATUS      obsolete
        DESCRIPTION
        "This trap is generated when the device finds that the state of the
        RADIUS accounting server changes from unreachable to unreachable.
        This node is replaced by unisRadiusAccountingServerUpTrap."
    ::= { unisRadiusServerTrapPrefix 2 }

    unisRadiusAuthErrTrap NOTIFICATION-TYPE
        OBJECTS     { radiusAuthServerAddress,
                      radiusAuthClientServerPortNumber }
        STATUS      current
        DESCRIPTION
        "This trap is generated when the device finds that the percent of
        unsuccessful authentication exceeds a threshold, and the threshold
        is the value of node unisRadiusAuthErrThreshold."
    ::= { unisRadiusServerTrapPrefix 3 }

    unisRadiusAuthenticationServerUpTrap NOTIFICATION-TYPE
        OBJECTS     { radiusAuthServerAddress,
                     radiusAuthClientServerPortNumber,
                     unisRadiusServerFirstTrapTime }
        STATUS      current
        DESCRIPTION
        "This trap is generated when the device finds that the state of the
        RADIUS authentication server changes from unreachable to reachable.
        The node replaces unisRadiusAuthServerUpTrap."
    ::= { unisRadiusServerTrapPrefix 4 }

    unisRadiusAccountingServerUpTrap NOTIFICATION-TYPE
        OBJECTS     { radiusAccServerAddress,
                     radiusAccClientServerPortNumber,
                     unisRadiusServerFirstTrapTime }
        STATUS      current
        DESCRIPTION
        "This trap is generated when the device finds that the state of the
        RADIUS accounting server changes from unreachable to reachable.
        The node replaces unisRadiusAccServerUpTrap."
    ::= { unisRadiusServerTrapPrefix 5 }

    unisRadiusAuthenticationServerDownTrap NOTIFICATION-TYPE
        OBJECTS     { radiusAuthServerAddress,
                     radiusAuthClientServerPortNumber,
                     unisRadiusServerFirstTrapTime}
        STATUS      current
        DESCRIPTION
        "This trap is generated when the authentication RADIUS server
        does not respond to the client's requests for a period of time.
        The node replaces unisRadiusAuthServerDownTrap."
    ::= { unisRadiusServerTrapPrefix 6 }

    unisRadiusAccountingServerDownTrap NOTIFICATION-TYPE
        OBJECTS     { radiusAccServerAddress,
                     radiusAccClientServerPortNumber,
                     unisRadiusServerFirstTrapTime}
        STATUS      current
        DESCRIPTION
        "This trap is generated when the accounting RADIUS server
        does not respond to the client's requests for a period of time.
        The node replaces unisRadiusAccServerDownTrap."
    ::= { unisRadiusServerTrapPrefix 7 }

-- ***********************************************************************
--
--  Supplement to RFC2618 RADIUS-AUTH-CLIENT-MIB
--
-- ***********************************************************************

    unisRadiusAuthenticating OBJECT IDENTIFIER ::= { unisRadius 4 }

    unisRadiusAuthClient OBJECT IDENTIFIER ::= { unisRadiusAuthenticating 1 }

    unisRadiusAuthServerTable OBJECT-TYPE
        SYNTAX  SEQUENCE OF UnisRadiusAuthServerEntry
        MAX-ACCESS  not-accessible
        STATUS  current
        DESCRIPTION
        "The (conceptual) table listing the RADIUS authenticating
        servers with which the client shares a secret."
    ::= { unisRadiusAuthClient 1 }

    unisRadiusAuthServerEntry OBJECT-TYPE
        SYNTAX  UnisRadiusAuthServerEntry
        MAX-ACCESS  not-accessible
        STATUS  current
        DESCRIPTION
        "An entry (conceptual row) representing a RADIUS authenticating
        server with which a client shares a secret."
        INDEX { radiusAuthServerIndex }
    ::= { unisRadiusAuthServerTable 1 }

    UnisRadiusAuthServerEntry ::= SEQUENCE {
        unisRadiusAuthFailureTimes         Counter32,
        unisRadiusAuthTimeoutTimes        Counter32,
        unisRadiusAuthRejectTimes       Counter32}

    unisRadiusAuthFailureTimes   OBJECT-TYPE
        SYNTAX  Counter32
        MAX-ACCESS  read-only
        STATUS  current
        DESCRIPTION
        "The number of RADIUS authenticating failed to this server."
    ::= { unisRadiusAuthServerEntry  1 }

    unisRadiusAuthTimeoutTimes   OBJECT-TYPE
        SYNTAX  Counter32
        MAX-ACCESS  read-only
        STATUS  current
        DESCRIPTION
        "The number of RADIUS authenticating timeout to this server."
    ::= { unisRadiusAuthServerEntry  2 }

    unisRadiusAuthRejectTimes   OBJECT-TYPE
        SYNTAX  Counter32
        MAX-ACCESS  read-only
        STATUS  current
        DESCRIPTION
        "The number of RADIUS authenticating rejected to this server."
    ::= { unisRadiusAuthServerEntry  3 }


-- ***********************************************************************
--
--  Radius Extend
--
-- ***********************************************************************
    unisRadiusExtend OBJECT IDENTIFIER ::= { unisRadius 5 }

    unisRadiusExtendObjects OBJECT IDENTIFIER ::= { unisRadiusExtend 1 }
    unisRadiusExtendTables OBJECT IDENTIFIER ::= { unisRadiusExtend 2 }
    unisRadiusExtendTraps OBJECT IDENTIFIER ::= { unisRadiusExtend 3 }

-- ***********************************************************************
--
--  Radius Scheme Authentication Table
--
-- ***********************************************************************
    unisRadiusSchAuthTable OBJECT-TYPE
        SYNTAX SEQUENCE OF UnisRadiusSchAuthEntry
        MAX-ACCESS not-accessible
        STATUS current
        DESCRIPTION
        "The (conceptual) table listing RADIUS authentication servers."
    ::= { unisRadiusExtendTables 1 }

    unisRadiusSchAuthEntry OBJECT-TYPE
        SYNTAX UnisRadiusSchAuthEntry
        MAX-ACCESS not-accessible
        STATUS current
        DESCRIPTION
        "An entry (conceptual row) representing RADIUS authentication servers."
        INDEX { unisRadiusSchAuthGroupName}
    ::= { unisRadiusSchAuthTable 1 }

    UnisRadiusSchAuthEntry ::= SEQUENCE {
        unisRadiusSchAuthGroupName           DisplayString,
        unisRadiusSchAuthPrimIpAddr          IpAddress,
        unisRadiusSchAuthPrimUdpPort         Integer32,
        unisRadiusSchAuthPrimKey             DisplayString,
        unisRadiusSchAuthSecIpAddr           IpAddress,
        unisRadiusSchAuthSecUdpPort          Integer32,
        unisRadiusSchAuthSecKey              DisplayString,
        unisRadiusSchAuthRowStatus           RowStatus
        }

    unisRadiusSchAuthGroupName OBJECT-TYPE
        SYNTAX DisplayString
        MAX-ACCESS not-accessible
        STATUS current
        DESCRIPTION
        "The name of the RADIUS authentication server group referred to in this table entry."
    ::= { unisRadiusSchAuthEntry 1 }

    unisRadiusSchAuthPrimIpAddr OBJECT-TYPE
        SYNTAX      IpAddress
        MAX-ACCESS  read-create
        STATUS      current
        DESCRIPTION
        "The IP address of primary RADIUS authenticaiton server."
    ::= { unisRadiusSchAuthEntry 2 }

    unisRadiusSchAuthPrimUdpPort OBJECT-TYPE
        SYNTAX      Integer32
        MAX-ACCESS  read-create
        STATUS      current
        DESCRIPTION
        "The UDP port the client is using to send requests to primary
        RADIUS authentication server.  Default value is 1812."
        DEFVAL { 1812 }
    ::= { unisRadiusSchAuthEntry 3 }

    unisRadiusSchAuthPrimKey OBJECT-TYPE
        SYNTAX DisplayString
        MAX-ACCESS read-create
        STATUS current
        DESCRIPTION
        "The secret shared between the RADIUS client and the primary RADIUS
        authentication server used in encoding and decoding sensitive data."
    ::= { unisRadiusSchAuthEntry 4 }

    unisRadiusSchAuthSecIpAddr OBJECT-TYPE
        SYNTAX      IpAddress
        MAX-ACCESS  read-create
        STATUS      current
        DESCRIPTION
        "The IP address of secondary RADIUS authenticaiton server."
    ::= { unisRadiusSchAuthEntry 5 }

    unisRadiusSchAuthSecUdpPort OBJECT-TYPE
        SYNTAX      Integer32
        MAX-ACCESS  read-create
        STATUS      current
        DESCRIPTION
        "The UDP port the client is using to send requests to secondary
        RADIUS authentication server.  Default value is 1812."
        DEFVAL { 1812 }
    ::= { unisRadiusSchAuthEntry 6 }

    unisRadiusSchAuthSecKey OBJECT-TYPE
        SYNTAX DisplayString
        MAX-ACCESS read-create
        STATUS current
        DESCRIPTION
        "The secret shared between the RADIUS client and the secondary RADIUS
        authentication server used in encoding and decoding sensitive data."
    ::= { unisRadiusSchAuthEntry 7 }

    unisRadiusSchAuthRowStatus   OBJECT-TYPE
        SYNTAX   RowStatus
        MAX-ACCESS  read-create
        STATUS   current
        DESCRIPTION
        "This object is responsible for managing the creation, deletion and
        modification of rows, which support active status and CreateAndGo,
        Destroy operation.
        To create a new row, unisRadiusSchAuthGroupName must be specified,
        and this action will create a corresponding domain that
        unisDomainRadiusGroupName is the same as unisRadiusSchAuthGroupName.
        To destroy an existent row, the unisRadiusSchAuthGroupName MUST NOT be
        referred by unisDomainTable in unisDomainRadiusGroupName column."
    ::= { unisRadiusSchAuthEntry 8 }


-- ***********************************************************************
--
--  Radius Scheme Accounting Table
--
-- ***********************************************************************
    unisRadiusSchAccTable OBJECT-TYPE
        SYNTAX SEQUENCE OF UnisRadiusSchAccEntry
        MAX-ACCESS not-accessible
        STATUS current
        DESCRIPTION
        "The (conceptual) table listing RADIUS accounting servers."
    ::= { unisRadiusExtendTables 2 }

    unisRadiusSchAccEntry OBJECT-TYPE
        SYNTAX UnisRadiusSchAccEntry
        MAX-ACCESS not-accessible
        STATUS current
        DESCRIPTION
        "An entry (conceptual row) representing RADIUS accounting servers."
        INDEX { unisRadiusSchAccGroupName}
    ::= { unisRadiusSchAccTable 1 }

    UnisRadiusSchAccEntry ::= SEQUENCE {
        unisRadiusSchAccGroupName           DisplayString,
        unisRadiusSchAccPrimIpAddr          IpAddress,
        unisRadiusSchAccPrimUdpPort         Integer32,
        unisRadiusSchAccPrimKey             DisplayString,
        unisRadiusSchAccSecIpAddr           IpAddress,
        unisRadiusSchAccSecUdpPort          Integer32,
        unisRadiusSchAccSecKey              DisplayString,
        unisRadiusSchAccRowStatus           RowStatus
        }

    unisRadiusSchAccGroupName OBJECT-TYPE
        SYNTAX DisplayString
        MAX-ACCESS not-accessible
        STATUS current
        DESCRIPTION
        "The name of the RADIUS accounting server group referred to in this table entry."
    ::= { unisRadiusSchAccEntry 1 }

    unisRadiusSchAccPrimIpAddr OBJECT-TYPE
        SYNTAX      IpAddress
        MAX-ACCESS  read-create
        STATUS      current
        DESCRIPTION
        "The IP address of primary RADIUS accounting server."
    ::= { unisRadiusSchAccEntry 2 }

    unisRadiusSchAccPrimUdpPort OBJECT-TYPE
        SYNTAX      Integer32
        MAX-ACCESS  read-create
        STATUS      current
        DESCRIPTION
        "The UDP port the client is using to send requests to primary
        RADIUS accounting server.  Default value is 1813."
        DEFVAL { 1813 }
    ::= { unisRadiusSchAccEntry 3 }

    unisRadiusSchAccPrimKey OBJECT-TYPE
        SYNTAX DisplayString
        MAX-ACCESS read-create
        STATUS current
        DESCRIPTION
        "The secret shared between the RADIUS client and the primary RADIUS
        accounting server used in encoding and decoding sensitive data."
    ::= { unisRadiusSchAccEntry 4 }

    unisRadiusSchAccSecIpAddr OBJECT-TYPE
        SYNTAX      IpAddress
        MAX-ACCESS  read-create
        STATUS      current
        DESCRIPTION
        "The IP address of secondary RADIUS accounting server."
    ::= { unisRadiusSchAccEntry 5 }

    unisRadiusSchAccSecUdpPort OBJECT-TYPE
        SYNTAX      Integer32
        MAX-ACCESS  read-create
        STATUS      current
        DESCRIPTION
        "The UDP port the client is using to send requests to secondary
        RADIUS accounting server.  Default value is 1813."
        DEFVAL { 1813 }
    ::= { unisRadiusSchAccEntry 6 }

    unisRadiusSchAccSecKey OBJECT-TYPE
        SYNTAX DisplayString
        MAX-ACCESS read-create
        STATUS current
        DESCRIPTION
        "The secret shared between the RADIUS client and the secondary RADIUS
        accounting server used in encoding and decoding sensitive data."
    ::= { unisRadiusSchAccEntry 7 }

    unisRadiusSchAccRowStatus   OBJECT-TYPE
        SYNTAX   RowStatus
        MAX-ACCESS  read-create
        STATUS   current
        DESCRIPTION
        "This object is responsible for managing the creation, deletion and
        modification of rows, which support active status and CreateAndGo,
        Destroy operation.
        To create a new row, unisRadiusSchAccGroupName must be specified,
        and this action will create a corresponding domain that
        unisDomainRadiusGroupName is the same as unisRadiusSchAccGroupName.
        To destroy an existent row, the unisRadiusSchAccGroupName MUST NOT be
        referred by unisDomainTable in unisDomainRadiusGroupName column."
    ::= { unisRadiusSchAccEntry 8 }
-- ***********************************************************************
--
-- RADIUS ACCOUNT STATISTIC
--
-- ***********************************************************************
unisRadiusStatistic OBJECT IDENTIFIER ::= { unisRadius 6 }

unisRadiusStatAccReq OBJECT-TYPE
    SYNTAX      Counter64
    MAX-ACCESS  read-only
    STATUS      current
    DESCRIPTION
        "It shows the number of radius account request to the
        radius server."
    ::= { unisRadiusStatistic 1 }

unisRadiusStatAccAck OBJECT-TYPE
    SYNTAX      Counter64
    MAX-ACCESS  read-only
    STATUS      current
    DESCRIPTION
        "It shows the number of radius account response from the
         radius server."
    ::= { unisRadiusStatistic 2 }

unisRadiusStatLogoutReq OBJECT-TYPE
    SYNTAX      Counter64
    MAX-ACCESS  read-only
    STATUS      current
    DESCRIPTION
        "It shows the number of logout request to the radius server."
    ::= { unisRadiusStatistic 3 }

unisRadiusStatLogoutAck OBJECT-TYPE
    SYNTAX      Counter64
    MAX-ACCESS  read-only
    STATUS      current
    DESCRIPTION
        "It shows the number of logout response from the radius server."
    ::= { unisRadiusStatistic 4 }

unisRadiusServerTrapVarObjects OBJECT IDENTIFIER ::= { unisRadius 7 }

unisRadiusServerFirstTrapTime OBJECT-TYPE
    SYNTAX      TimeTicks
    MAX-ACCESS  accessible-for-notify
    STATUS      current
    DESCRIPTION
        "Represents the first trap time."
    ::= { unisRadiusServerTrapVarObjects 1 }

END
