-- ==================================================================
-- Copyright (c) 2020 Unisyue Technologies Co., Ltd.  All rights reserved.
--
-- Description:  HGMP Information MIB for LAN Switch
-- Reference:
-- Version: V1.8
-- History:
--   V1.0 2001.5.15 Created Ye dalu
--   V1.1 2004/7/20 Modify Object Name from UnisNDPNbEntry
--        to UnisNDPPortNbEntry
--   V1.2 2004/8/09 add notification unishgmpNetTopChange
--   V1.3 2004-09-24 modify value of STATUS clause from 'mandatory' to 'current' by gaolong
--   V1.4 2004-10-12 updated by gaolong
--        Import NOTIFICATION-TYPE.
--   V1.5 2004-11-02 updated by gaolong
--        Import Counter32.
--   V1.6 2005-12-9  added by zhanglin KF0176
--        add unishgmpClusterProtocolMac
--        add unishgmpWhitelistNbTable
--        add unishgmpWhitelistTable
--        add unishgmpBlacklistTable
--        2005-12-20 added by zushuzhi 03030
--        add unishgmpMemberPriPortTable
--        add unishgmpNTDPTopLinkStatus
--   V1.7 2006-04-30 modified by gaolong
--        relocate unishgmpProtocolMac, unishgmpTopologyManagement, unishgmpMemberPriPortTable
--        and the objects below them.
--        relocate unishgmpNTDPTopLinkStatus in unishgmpNTDPTopLinkStatus.
--   V1.8 2006-05-08 modify the description of unishgmpNTDPCollectTopTime by shanfeng
-- ==================================================================
-- ==================================================================
--
-- Varibles and types be imported
--
-- ==================================================================
UNIS-HGMP-MIB  DEFINITIONS ::= BEGIN
    IMPORTS
        unisRhw
            FROM UNIS-OID-MIB
        IpAddress, Integer32, OBJECT-TYPE, MODULE-IDENTITY, OBJECT-IDENTITY,
        NOTIFICATION-TYPE, Counter32, Unsigned32
            FROM SNMPv2-SMI
        RowStatus, MacAddress, TEXTUAL-CONVENTION, DisplayString
            FROM SNMPv2-TC;

    unisHgmp MODULE-IDENTITY
        LAST-UPDATED "200512061452Z"
        ORGANIZATION
            "Unisyue Technologies Co., Ltd."
        CONTACT-INFO
            ""
        DESCRIPTION
            "This MIB contains objects to manage the unishgmp operations,
            which are used on lanswitch products."
        ::= { unisRhw 7 }

-- ==================================================================
--
-- ======================= definition begin =========================
--
-- ==================================================================

--
-- cluster definitions
--

    unisClusterObject OBJECT-IDENTITY
        STATUS      current
        DESCRIPTION
            "This MIB contains objects to manage the cluster operations, which
            are used on lanswitch products."
        ::= { unisHgmp 1 }

    unishgmpSetVLANSecurity OBJECT-TYPE
        SYNTAX      INTEGER
            {
                noSecurity(0),
                security(1)
            }
        MAX-ACCESS  read-write
        STATUS      current
        DESCRIPTION
            "Configure whether to perform the VLAN check inside the cluster."
        DEFVAL { security }
        ::= { unisClusterObject 1 }

    unishgmpHandShakeInterval OBJECT-TYPE
        SYNTAX      Integer32(1..255)
        MAX-ACCESS  read-write
        STATUS      current
        DESCRIPTION
            "Handshaking interval of the cluster member switches."
        DEFVAL { 10 }
        ::= { unisClusterObject 2 }

    unishgmpHandShakeHoldtime OBJECT-TYPE
        SYNTAX      Integer32(1..255)
        MAX-ACCESS  read-write
        STATUS      current
        DESCRIPTION
            "Holdtime of administrator switch and member switch in the cluster."
        DEFVAL { 60 }
        ::= { unisClusterObject 3 }

    unishgmpGrpMemberTableChange OBJECT-TYPE
        SYNTAX      Integer32(0..65535)
        MAX-ACCESS  read-only
        STATUS      current
        DESCRIPTION
            "Add 1 to the member list after it changes. The administrator checks if
            the value has changed. If not, he will not read the list once more."
        DEFVAL { 0 }
        ::= { unisClusterObject 4 }

    unishgmpMemberDisconRate OBJECT-TYPE
        SYNTAX      Integer32
        MAX-ACCESS  read-only
        STATUS      current
        DESCRIPTION
            "Disconnection times of the member and administrator switches divided by
            member number times 1000."
        DEFVAL { 0 }
        ::= { unisClusterObject 5 }

    unishgmpCmdLanswitchFlag OBJECT-TYPE
        SYNTAX      INTEGER
            {
                false(0),
                true(1)
            }
        MAX-ACCESS  read-write
        STATUS      current
        DESCRIPTION
            "Administrator switch flag"
        DEFVAL { false }
        ::= { unisClusterObject 6 }

    unishgmpCmdClusterName OBJECT-TYPE
        SYNTAX      OCTET STRING(SIZE (0..8))
        MAX-ACCESS  read-write
        STATUS      current
        DESCRIPTION
            "Cluster name of the administrator switch"
        ::= { unisClusterObject 7 }

    unishgmpMngPriIpSegCMIP OBJECT-TYPE
        SYNTAX      IpAddress
        MAX-ACCESS  read-write
        STATUS      current
        DESCRIPTION
            "The private management IP address of the administrator switch,
            which can not be modified after the cluster has been created."
        ::= { unisClusterObject 8 }

    unishgmpMngPriIpMask OBJECT-TYPE
        SYNTAX      IpAddress
        MAX-ACCESS  read-write
        STATUS      current
        DESCRIPTION
            "The private management IP address mask assigned by the administrator
            switch, which cannot be modified after the cluster has been created."
        ::= { unisClusterObject 9 }

    unishgmpFtpServer OBJECT-TYPE
        SYNTAX      IpAddress
        MAX-ACCESS  read-write
        STATUS      current
        DESCRIPTION
            "The cluster members can access the Ftp Server through the administrator
            switch, which can only be configured and accessed on the administrator
            switch."
        ::= { unisClusterObject 10 }

    unishgmpTftpServer OBJECT-TYPE
        SYNTAX      IpAddress
        MAX-ACCESS  read-write
        STATUS      current
        DESCRIPTION
            "The cluster members can access the Tftp Server through the administrator
             switch, which can only be configured and accessed on the administrator
             switch."
        ::= { unisClusterObject 11 }

    unishgmpSnmpHost OBJECT-TYPE
        SYNTAX      IpAddress
        MAX-ACCESS  read-write
        STATUS      current
        DESCRIPTION
            "The Snmp Host to send the cluster trap packets, which can only be
            configured and accessed on the administrator switch."
        ::= { unisClusterObject 12 }

    unishgmpLogHost OBJECT-TYPE
        SYNTAX      IpAddress
        MAX-ACCESS  read-write
        STATUS      current
        DESCRIPTION
            "Log host of the cluster, which can only be configured and accessed on
            the administrator switch."
        ::= { unisClusterObject 13 }

--
-- TABLE: Group member table
--

    unishgmpGrpMemberTable OBJECT-TYPE
        SYNTAX      SEQUENCE OF UnisHgmpGrpMemberEntry
        MAX-ACCESS  not-accessible
        STATUS      current
        DESCRIPTION
            "Table of cluster member switches"
        ::= { unisClusterObject 14 }

    unishgmpGrpMemberEntry OBJECT-TYPE
        SYNTAX      UnisHgmpGrpMemberEntry
        MAX-ACCESS  not-accessible
        STATUS      current
        DESCRIPTION
            ""
        INDEX
            {
                unishgmpGrpMemberDeviceId
            }
        ::= { unishgmpGrpMemberTable 1 }

    UnisHgmpGrpMemberEntry ::=
        SEQUENCE
            {
                unishgmpGrpMemberDeviceId       OCTET STRING,
                unishgmpGrpMemberSerial         Integer32,
                unishgmpGrpMemberIpAddr         IpAddress,
                unishgmpGrpMemberName           OCTET STRING,
                unishgmpGrpMemberPassword       OCTET STRING,
                unishgmpGrpMemberPlatform       OCTET STRING,
                unishgmpGrpMemberStatus         INTEGER,
                unishgmpGrpMemberDisconCount    Integer32,
                unishgmpGrpMemberEnrollTime     Integer32,
                unishgmpGrpMemberOperate        RowStatus
            }

    unishgmpGrpMemberDeviceId OBJECT-TYPE
        SYNTAX      OCTET STRING(SIZE(0..10))
        MAX-ACCESS  read-only
        STATUS      current
        DESCRIPTION
            "4 bytes reserved as 0x0 + 6 bytes of MAC address, expressed as 
            a character string of the hexadecimal number."
        ::= { unishgmpGrpMemberEntry 1 }

    unishgmpGrpMemberSerial OBJECT-TYPE
        SYNTAX      Integer32(0..2047)
        MAX-ACCESS  read-only
        STATUS      current
        DESCRIPTION
            "When adding member switch to the cluster, the administrator switch
            will assign an unique integer to identify it."
        ::= { unishgmpGrpMemberEntry 2 }

    unishgmpGrpMemberIpAddr OBJECT-TYPE
        SYNTAX      IpAddress
        MAX-ACCESS  read-only
        STATUS      current
        DESCRIPTION
            "The private IP addresses of the member switches for the communication
            inside the cluster."
        ::= { unishgmpGrpMemberEntry 3 }

    unishgmpGrpMemberName OBJECT-TYPE
        SYNTAX      OCTET STRING(SIZE(0..32))
        MAX-ACCESS  read-only
        STATUS      current
        DESCRIPTION
            "Hostname of the member switch"
        ::= { unishgmpGrpMemberEntry 4 }

    unishgmpGrpMemberPassword OBJECT-TYPE
        SYNTAX      OCTET STRING
        MAX-ACCESS  read-write
        STATUS      current
        DESCRIPTION
            "Member password for joining a cluster"
        ::= { unishgmpGrpMemberEntry 5 }

    unishgmpGrpMemberPlatform OBJECT-TYPE
        SYNTAX      OCTET STRING
        MAX-ACCESS  read-only
        STATUS      current
        DESCRIPTION
            "Set the hardware platform. A null string indicates the information
            does not exist in the device adjacency table."
        ::= { unishgmpGrpMemberEntry 6 }

    unishgmpGrpMemberStatus OBJECT-TYPE
        SYNTAX      INTEGER
            {
                normal(0),
                fault(1)
            }
        MAX-ACCESS  read-only
        STATUS      current
        DESCRIPTION
            "Member status on the administrator switch, use for displaying the
            network management status."
        DEFVAL { fault }
        ::= { unishgmpGrpMemberEntry 7 }

    unishgmpGrpMemberDisconCount OBJECT-TYPE
        SYNTAX      Integer32
        MAX-ACCESS  read-only
        STATUS      current
        DESCRIPTION
            "Count of inside communication disconnection between the member switch
            and the administrator switch."
        ::= { unishgmpGrpMemberEntry 8 }

    unishgmpGrpMemberEnrollTime OBJECT-TYPE
        SYNTAX      Integer32
        MAX-ACCESS  read-only
        STATUS      current
        DESCRIPTION
            "Enrollment time of the member, measured in seconds."
        ::= { unishgmpGrpMemberEntry 9 }

    unishgmpGrpMemberOperate OBJECT-TYPE
        SYNTAX      RowStatus
        MAX-ACCESS  read-write
        STATUS      current
        DESCRIPTION
            "Operation indication field, indicates the operation of adding/removing
            a member by the network management agent."
        ::= { unishgmpGrpMemberEntry 10 }

--
-- TABLE: Member reset table
--

    unishgmpMemberResetTable OBJECT-TYPE
        SYNTAX      SEQUENCE OF UnisHgmpMemberResetEntry
        MAX-ACCESS  not-accessible
        STATUS      current
        DESCRIPTION
            "Reset a member switch in the cluster."
        ::= { unisClusterObject 15 }

    unishgmpMemberResetEntry OBJECT-TYPE
        SYNTAX      UnisHgmpMemberResetEntry
        MAX-ACCESS  not-accessible
        STATUS      current
        DESCRIPTION
            ""
        INDEX
            {
                unishgmpMemberResetMAC
            }
        ::= { unishgmpMemberResetTable 1 }

    UnisHgmpMemberResetEntry ::=
        SEQUENCE
            {
                unishgmpMemberResetMAC      OCTET STRING,
                unishgmpMemberEraseflash    INTEGER
            }

    unishgmpMemberResetMAC OBJECT-TYPE
        SYNTAX      OCTET STRING(SIZE(0..6))
        MAX-ACCESS  read-only
        STATUS      current
        DESCRIPTION
            "The management MAC address of the switch to be reset, which is the
            unique identifier of the switch."
        ::= { unishgmpMemberResetEntry  1 }

    unishgmpMemberEraseflash OBJECT-TYPE
        SYNTAX      INTEGER
            {
                noErase(0),
                erase(1),
                cannotget(65535)
            }
        MAX-ACCESS  read-write
        STATUS      current
        DESCRIPTION
            "Whether to erase the configuration file from the flash after
            resetting the switch. Read this node, cannotget(65535) will be
            returned."
        ::= { unishgmpMemberResetEntry  2 }

    unishgmpEventsV2 OBJECT-IDENTITY
        STATUS      current
        DESCRIPTION
            "Definition point for cluster notifications."
        ::= { unisClusterObject 0 }

    unishgmpMemberfailure NOTIFICATION-TYPE
        OBJECTS
            {
                unishgmpGrpMemberDeviceId
            }
        STATUS      current
        DESCRIPTION
            "When a cluster member failure, send a snmp trap to the network
            management."
        ::= { unishgmpEventsV2 1 }

    unishgmpMemberRecover NOTIFICATION-TYPE
        OBJECTS
            {
                unishgmpGrpMemberDeviceId
            }
        STATUS      current
        DESCRIPTION
            "When a cluster member recover, send a snmp trap to the network
            management."
        ::= { unishgmpEventsV2 2 }

    unishgmpMemberStatusChange NOTIFICATION-TYPE
        OBJECTS
            {
                unishgmpGrpMemberDeviceId,
                unishgmpNTDPCacheClusterRole
            }
        STATUS      current
        DESCRIPTION
            "When a cluster member status change, send a snmp trap to the
            network management."
        ::= { unishgmpEventsV2 3 }

    unishgmpNetTopChange NOTIFICATION-TYPE
        STATUS      current
        DESCRIPTION
            "When net topology of this cluster change, send a snmp trap
            to the network management."
        ::= { unishgmpEventsV2 4 }

    unishgmpClusterRole OBJECT-TYPE
        SYNTAX      INTEGER
            {
                roleCMDSW(1),
                roleMEMBERSW(2),
                roleBAKSW(3),
                roleCASW(16),
                roleUNISW(17)
            }
        MAX-ACCESS  read-only
        STATUS      current
        DESCRIPTION
            "This switch's role in cluster."
        DEFVAL { roleUNISW }
        ::= { unisClusterObject 16 }

    unishgmpClusterMaxPoolNum OBJECT-TYPE
        SYNTAX      INTEGER
        MAX-ACCESS  read-only
        STATUS      current
        DESCRIPTION
            "Max switch members that the cluster can support(include
            administrator switch)."
        ::= { unisClusterObject 17 }

    unishgmpClusterCmdSwMac OBJECT-TYPE
        SYNTAX      OCTET STRING(SIZE(0..6))
        MAX-ACCESS  read-only
        STATUS      current
        DESCRIPTION
            "The MAC address of administrator switch. It will be filled with
            zero when not be a member of cluster."
        ::= { unisClusterObject 18 }

    unishgmpRun OBJECT-TYPE
        SYNTAX      INTEGER
            {
                false(0),
                true(1)
            }
        MAX-ACCESS  read-write
        STATUS      current
        DESCRIPTION
            "Enable cluster on this switch."
        DEFVAL { true }
        ::= { unisClusterObject 19 }

--
-- cluster protocol MAC
--

    unishgmpProtocolMac OBJECT IDENTIFIER ::= { unisClusterObject 22 }

    unishgmpClusterProtocolMac OBJECT-TYPE
        SYNTAX      MacAddress
        MAX-ACCESS  read-write
        STATUS      current
        DESCRIPTION
            "Protocol MAC of HGMP protocol family. All multicast packets of this
            protocol family use this MAC as destination MAC."
        DEFVAL { '0180C200000A'H }
        ::= { unishgmpProtocolMac 1 }

--
-- unishgmp topology management
--

    unishgmpTopologyManagement OBJECT IDENTIFIER ::= { unisClusterObject 23 }

--
-- TABLE: Whitelist Table
--

    unishgmpWhitelistTable OBJECT-TYPE
        SYNTAX      SEQUENCE OF UnisHgmpWhitelistEntry
        MAX-ACCESS  not-accessible
        STATUS      current
        DESCRIPTION
            "Cluster switches white list table. White list topology is the
            topology which has been affirmed by network administrator in a
            cluster, and all devices in white list topology are recorded in this
            table. Against to white list table, black list table records the
            devices which are denied to join in cluster. Adding a black list
            device to white list table will cause a failure."
        ::= { unishgmpTopologyManagement 1 }

    unishgmpWhitelistEntry OBJECT-TYPE
        SYNTAX      UnisHgmpWhitelistEntry
        MAX-ACCESS  not-accessible
        STATUS      current
        DESCRIPTION
            "Entry items"
        INDEX
            {
                unishgmpWhitelistDeviceId
            }
        ::= { unishgmpWhitelistTable 1 }

    UnisHgmpWhitelistEntry ::=
        SEQUENCE
            {
                unishgmpWhitelistDeviceId     OCTET STRING,
                unishgmpWhitelistSerial       Integer32,
                unishgmpWhitelistRowStatus    RowStatus
            }

    unishgmpWhitelistDeviceId OBJECT-TYPE
        SYNTAX      OCTET STRING(SIZE(10))
        MAX-ACCESS  not-accessible
        STATUS      current
        DESCRIPTION
            "Unique identifier indicating a white list switch. Value format of the
            this object is 'XXXXYYYYYY', in which 'XXXX' is reserved as 4 bytes of
            0x0, 'YYYYYY' is a MAC address.
            For example, if the MAC is 000f-e459-000a, the value of this object is
            an octet string: '00' '00' '00' '00' '00' '0f' 'e4' '59' '00' '0a'."
        ::= { unishgmpWhitelistEntry  1 }

    unishgmpWhitelistSerial OBJECT-TYPE
        SYNTAX      Integer32(0..2047 | 65535)
        MAX-ACCESS  read-only
        STATUS      current
        DESCRIPTION
            "When adding member switch to the cluster, the administrator switch
            will assign an unique integer to identify it. 0xffff means invalid
            value for this object."
        ::= { unishgmpWhitelistEntry  2 }

    unishgmpWhitelistRowStatus OBJECT-TYPE
        SYNTAX      RowStatus
        MAX-ACCESS  read-create
        STATUS      current
        DESCRIPTION
            "The row status of this table."
        ::= { unishgmpWhitelistEntry 3 }

--
-- TABLE: Whitelist neighbor table
--

    unishgmpWhitelistNbTable OBJECT-TYPE
        SYNTAX      SEQUENCE OF UnisHgmpWhitelistNbEntry
        MAX-ACCESS  not-accessible
        STATUS      current
        DESCRIPTION
            "Cluster switches white list neighboring information table. White
            list neighbor table records all neighbor devices for every white
            list device. In fact, white list neighbor table displays the whole
            white list topology."
        ::= { unishgmpTopologyManagement 2 }

    unishgmpWhitelistNbEntry OBJECT-TYPE
        SYNTAX      UnisHgmpWhitelistNbEntry
        MAX-ACCESS  not-accessible
        STATUS      current
        DESCRIPTION
            "Entry items"
        INDEX
            {
                unishgmpWhitelistDeviceId,
                unishgmpWhitelistNbIndex
            }
        ::= { unishgmpWhitelistNbTable 1 }

    UnisHgmpWhitelistNbEntry ::=
        SEQUENCE
            {
                unishgmpWhitelistNbIndex       Integer32,
                unishgmpWhitelistNbDeviceId    OCTET STRING,
                unishgmpWhitelistPortName      OCTET STRING,
                unishgmpWhitelistNbPortName    OCTET STRING
            }

    unishgmpWhitelistNbIndex OBJECT-TYPE
        SYNTAX      Integer32(1..65535)
        MAX-ACCESS  not-accessible
        STATUS      current
        DESCRIPTION
            "Index of a switch which is the neighbor of a white list switch
            identified by 'hgmpWhitelistDeviceId'."
        ::= { unishgmpWhitelistNbEntry  1 }

    unishgmpWhitelistNbDeviceId OBJECT-TYPE
        SYNTAX      OCTET STRING(SIZE(10))
        MAX-ACCESS  read-only
        STATUS      current
        DESCRIPTION
            "Unique identifier indicating a neighbor switch of a white list
            switch. Value format of the this object is 'XXXXYYYYYY', in which
            'XXXX' is reserved as 4 bytes of 0x0, 'YYYYYY' is a MAC address.
            For example, if the MAC is 000f-e459-000a, the value of this object
            is an octet string: '00' '00' '00' '00' '00' '0f' 'e4' '59' '00' '0a'."
        ::= { unishgmpWhitelistNbEntry  2 }

    unishgmpWhitelistPortName OBJECT-TYPE
        SYNTAX      OCTET STRING(SIZE(0..47))
        MAX-ACCESS  read-only
        STATUS      current
        DESCRIPTION
            "The name of the port which a white list switch connects to the
            neighbor specified by 'hgmpWhitelistNbIndex'."
        ::= { unishgmpWhitelistNbEntry  3 }

    unishgmpWhitelistNbPortName OBJECT-TYPE
        SYNTAX      OCTET STRING(SIZE(0..47))
        MAX-ACCESS  read-only
        STATUS      current
        DESCRIPTION
            "The name of the port which a neighbor device connects to the white
            list switch specified by 'hgmpWhitelistDeviceId'."
        ::= { unishgmpWhitelistNbEntry  4 }

--
-- TABLE: Blacklist table
--

    unishgmpBlacklistTable OBJECT-TYPE
        SYNTAX      SEQUENCE OF UnisHgmpBlacklistEntry
        MAX-ACCESS  not-accessible
        STATUS      current
        DESCRIPTION
            "Cluster switches black list table. The black list table records all
            black list devices, and a device in black list is not permitted to
            join in any cluster."
        ::= { unishgmpTopologyManagement 3 }

    unishgmpBlacklistEntry OBJECT-TYPE
        SYNTAX      UnisHgmpBlacklistEntry
        MAX-ACCESS  not-accessible
        STATUS      current
        DESCRIPTION
            "Entry items"
        INDEX
            {
                unishgmpBlacklistDeviceId
            }
        ::= { unishgmpBlacklistTable 1 }

    UnisHgmpBlacklistEntry ::=
        SEQUENCE
            {
                unishgmpBlacklistDeviceId         OCTET STRING,
                unishgmpBlacklistAccessDeviceId   OCTET STRING,
                unishgmpBlacklistAccessPortName   OCTET STRING,
                unishgmpBlacklistRowStatus        RowStatus
            }

    unishgmpBlacklistDeviceId OBJECT-TYPE
        SYNTAX      OCTET STRING(SIZE(10))
        MAX-ACCESS  not-accessible
        STATUS      current
        DESCRIPTION
            "Unique identifier indicating a black list switch. Value format of the
            this object is 'XXXXYYYYYY', in which 'XXXX' is reserved as 4 bytes
            of 0x0, 'YYYYYY' is a MAC address.
            For example, if the MAC is 000f-e459-000a, the value of this object is
            an octet string: '00' '00' '00' '00' '00' '0f' 'e4' '59' '00' '0a'."
        ::= { unishgmpBlacklistEntry  1 }

    unishgmpBlacklistAccessDeviceId OBJECT-TYPE
        SYNTAX      OCTET STRING(SIZE(10))
        MAX-ACCESS  read-only
        STATUS      current
        DESCRIPTION
            "Unique identifier indicating the access device of a black list switch.
            Tracing from a black list device to the cluster commander switch, the
            device which the black list switch directly connects to is the access
            device.
            Value format of the this object is 'XXXXYYYYYY', in which 'XXXX' is
            reserved as 4 bytes of 0x0, 'YYYYYY' is a MAC address. 10 bytes of 0xff
            means invalid value for this object.
            For example, if the MAC is 000f-e459-000a, the value of this object is
            an octet string: '00' '00' '00' '00' '00' '0f' 'e4' '59' '00' '0a'."
        ::= { unishgmpBlacklistEntry  2 }

    unishgmpBlacklistAccessPortName OBJECT-TYPE
        SYNTAX      OCTET STRING(SIZE(0..47))
        MAX-ACCESS  read-only
        STATUS      current
        DESCRIPTION
            "The port which the access device connecting to the black list switch
            is named access port, the object returns the access port name.
            An empty string means invalid value for this object."
        ::= { unishgmpBlacklistEntry  3 }

    unishgmpBlacklistRowStatus OBJECT-TYPE
        SYNTAX      RowStatus
        MAX-ACCESS  read-create
        STATUS      current
        DESCRIPTION
            "The row status of this table."
        ::= { unishgmpBlacklistEntry 4 }

--
-- TABLE: Member private port number table
--

    unishgmpMemberPriPortTable OBJECT-TYPE
        SYNTAX      SEQUENCE OF UnisHgmpMemberPriPortEntry
        MAX-ACCESS  not-accessible
        STATUS      current
        DESCRIPTION
            "This table contains port number for different network protocols
            on each member switch. The port number can be used to access
            a specified member switch with specified protocol and private
            IP address."
        ::= { unisClusterObject 24 }

    unishgmpMemberPriPortEntry OBJECT-TYPE
        SYNTAX      UnisHgmpMemberPriPortEntry
        MAX-ACCESS  not-accessible
        STATUS      current
        DESCRIPTION
            "Information about a specified member private port entry. The
            indexes of the entry are unishgmpGrpMemberDevId and
            unishgmpMemberPriPortProto, which indicate entries in the table."
        INDEX
            {
                unishgmpMemberDevId,
                unishgmpMemberPriPortProto
            }
        ::= { unishgmpMemberPriPortTable 1 }

    UnisHgmpMemberPriPortEntry ::=
        SEQUENCE
            {
                unishgmpMemberDevId                OCTET STRING,
                unishgmpMemberPriPortProto         Unsigned32,
                unishgmpMemberPriPortProtoDescr    DisplayString,
                unishgmpMemberPriPortNum           Unsigned32
            }

    unishgmpMemberDevId OBJECT-TYPE
        SYNTAX      OCTET STRING(SIZE(0..10))
        MAX-ACCESS  read-only
        STATUS      current
        DESCRIPTION
            "Unique identifier indicating the switch in cluster.
            Value format of the this object is 'XXXXYYYYYY', in which 'XXXX' is 
            is reserved as 4 bytes of 0x0, 'YYYYYY' is a MAC address."
        ::= { unishgmpMemberPriPortEntry 1 }

    unishgmpMemberPriPortProto OBJECT-TYPE
        SYNTAX      Unsigned32
        MAX-ACCESS  not-accessible
        STATUS      current
        DESCRIPTION
            "The index of this table. Each instance value of this object
            corresponds to a different protocol."
        ::= { unishgmpMemberPriPortEntry 2 }

    unishgmpMemberPriPortProtoDescr OBJECT-TYPE
        SYNTAX      DisplayString
        MAX-ACCESS  read-only
        STATUS      current
        DESCRIPTION
            "It describes the unishgmpMemberPriPortProtocol object value.
            For example, it is 'SNMP' when unishgmpMemberPriPortProtocol value
            is 1."
        ::= { unishgmpMemberPriPortEntry 3 }

    unishgmpMemberPriPortNum OBJECT-TYPE
        SYNTAX      Unsigned32
        MAX-ACCESS  read-only
        STATUS      current
        DESCRIPTION
            "The private port number of member switch, used by specified
            unishgmpMemberPriPortProto. By using the private IP address,
            specified protocol and port number, other devices outside
            cluster can access member switch. The private IP address
            can be acquired by reading unishgmpGrpMemberIpAddr."
        ::= { unishgmpMemberPriPortEntry 4 }

--
-- stack definitions
--

    unisStackObject OBJECT-IDENTITY
        STATUS      current
        DESCRIPTION
            "This MIB contains objects to manage the stack operations, which is
            used on lanswitch products."
        ::= { unisHgmp 2 }

    unishgmpStackMemberTableChange OBJECT-TYPE
        SYNTAX      Integer32(0..65535)
        MAX-ACCESS  read-only
        STATUS      current
        DESCRIPTION
            "Change identifier of the stack member table."
        DEFVAL { 0 }
        ::= { unisStackObject 1 }

    unishgmpStackMemberDisconRate OBJECT-TYPE
        SYNTAX      Integer32
        MAX-ACCESS  read-only
        STATUS      current
        DESCRIPTION
            "Disconnection rate of the stack member switches."
        DEFVAL { 0 }
        ::= { unisStackObject 2 }

    unishgmpMainLanswitchFlag OBJECT-TYPE
        SYNTAX      INTEGER
            {
                false(0),
                true(1)
            }
        MAX-ACCESS  read-write
        STATUS      current
        DESCRIPTION
            "The status of the local switch in the stack."
        DEFVAL { false }
        ::= { unisStackObject 3 }

    unishgmpStackIpPoolStartIP OBJECT-TYPE
        SYNTAX      IpAddress
        MAX-ACCESS  read-write
        STATUS      current
        DESCRIPTION
            "The first address of the management IP network segment assigned by
            the master switch, which cannot be modified in the case that there
            is IP address assignment."
        ::= { unisStackObject 4 }

    unishgmpStackIpPoolLength OBJECT-TYPE
        SYNTAX      INTEGER(1..200)
        MAX-ACCESS  read-write
        STATUS      current
        DESCRIPTION
            "The length of the management IP segment assigned by the master
            switch, which cannot be modified in the case that there is IP
            address assignment."
        ::= { unisStackObject 5 }

    unishgmpStackIpPoolMask OBJECT-TYPE
        SYNTAX      IpAddress
        MAX-ACCESS  read-write
        STATUS      current
        DESCRIPTION
            "The mask of the management IP segment assigned by the master switch,
            which cannot be modified in the case that there is IP address assignment."
        DEFVAL { 'FFFF0000'H }
        ::= { unisStackObject 10 }

--
-- TABLE: Stack member table
--

    unishgmpStackMemberTable OBJECT-TYPE
        SYNTAX      SEQUENCE OF UnisHgmpStackMemberEntry
        MAX-ACCESS  not-accessible
        STATUS      current
        DESCRIPTION
            "Stack member table."
        ::= { unisStackObject 6 }

    unishgmpStackMemberEntry OBJECT-TYPE
        SYNTAX      UnisHgmpStackMemberEntry
        MAX-ACCESS  not-accessible
        STATUS      current
        DESCRIPTION
            ""
        INDEX
            {
                unishgmpStackMemberDeviceId
            }
        ::= { unishgmpStackMemberTable 1 }

    UnisHgmpStackMemberEntry ::=
        SEQUENCE
        {
            unishgmpStackMemberDeviceId       OCTET STRING,
            unishgmpStackMemberSerial         Integer32,
            unishgmpStackMemberIpAddr         IpAddress,
            unishgmpStackMemberName           OCTET STRING,
            unishgmpStackMemberPassword       OCTET STRING,
            unishgmpStackMemberPlatform       OCTET STRING,
            unishgmpStackMemberStatus         INTEGER,
            unishgmpStackMemberDisconCount    Integer32,
            unishgmpStackMemberEnrollTime     Integer32
        }

    unishgmpStackMemberDeviceId OBJECT-TYPE
        SYNTAX      OCTET STRING(SIZE(0..10))
        MAX-ACCESS  read-only
        STATUS      current
        DESCRIPTION
            "2 bytes address type of the switch + 2 bytes zero + MAC address,
            expressed as a hexadecimal number string."
        ::= { unishgmpStackMemberEntry 1 }

    unishgmpStackMemberSerial OBJECT-TYPE
        SYNTAX      Integer32(0..2047)
        MAX-ACCESS  read-only
        STATUS      current
        DESCRIPTION
            "When adding a member switch to the stack, the master switch will
            assign an unique integer to identify it."
        ::= { unishgmpStackMemberEntry 2 }

    unishgmpStackMemberIpAddr OBJECT-TYPE
        SYNTAX      IpAddress
        MAX-ACCESS  read-only
        STATUS      current
        DESCRIPTION
            "The private member IP address for the communication inside the stack."
        ::= { unishgmpStackMemberEntry 3 }

    unishgmpStackMemberName OBJECT-TYPE
        SYNTAX      OCTET STRING
        MAX-ACCESS  read-only
        STATUS      current
        DESCRIPTION
            "Hostname of the member switch."
        ::= { unishgmpStackMemberEntry 4 }

    unishgmpStackMemberPassword OBJECT-TYPE
        SYNTAX      OCTET STRING
        MAX-ACCESS  read-only
        STATUS      current
        DESCRIPTION
            "Member password for joining a stack."
        ::= { unishgmpStackMemberEntry 5 }

    unishgmpStackMemberPlatform OBJECT-TYPE
        SYNTAX      OCTET STRING
        MAX-ACCESS  read-only
        STATUS      current
        DESCRIPTION
            "Set the hardware platform. A null string indicates the information
            does not exist in the device adjacency table."
        ::= { unishgmpStackMemberEntry 6 }

    unishgmpStackMemberStatus OBJECT-TYPE
        SYNTAX      INTEGER
            {
                normal(0),
                fault(1)
            }
        MAX-ACCESS  read-only
        STATUS      current
        DESCRIPTION
            "Member status on the master switch, use for displaying the network
            management status."
        DEFVAL { fault }
        ::= { unishgmpStackMemberEntry 7 }

    unishgmpStackMemberDisconCount OBJECT-TYPE
        SYNTAX      Integer32
        MAX-ACCESS  read-only
        STATUS      current
        DESCRIPTION
            "Count of inside communication disconnection between the member switch
            and the master switch."
        ::= { unishgmpStackMemberEntry 8 }

    unishgmpStackMemberEnrollTime OBJECT-TYPE
        SYNTAX      Integer32
        MAX-ACCESS  read-only
        STATUS      current
        DESCRIPTION
            "Enrollment time of the member, measured in seconds."
        ::= { unishgmpStackMemberEntry 9 }

    unishgmpStackRole OBJECT-TYPE
        SYNTAX      INTEGER
            {
                roleCMDSW(1),
                roleMEMBERSW(2),
                roleBAKSW(3),
                roleCASW(16),
                roleUNISW(17)
            }
        MAX-ACCESS  read-only
        STATUS      current
        DESCRIPTION
            "This switch's role status in stack."
        DEFVAL { roleUNISW }
        ::= { unisStackObject 7 }

    unishgmpStackMaxPoolNum OBJECT-TYPE
        SYNTAX      INTEGER
        MAX-ACCESS  read-only
        STATUS      current
        DESCRIPTION
            "Max switch members in one stack that the switch support (include
            main switch)."
        ::= { unisStackObject 8 }

    unishgmpStackMainSwMac OBJECT-TYPE
        SYNTAX      OCTET STRING(SIZE(0..6))
        MAX-ACCESS  read-only
        STATUS      current
        DESCRIPTION
            "The MAC address of main switch. It will be 00.00.00 when not be a
            member of stack."
        ::= { unisStackObject 9 }

--
-- Neighbor protocol objects
--

    unisNDPObject OBJECT-IDENTITY
        STATUS      current
        DESCRIPTION
            "This MIB contains objects to manage the ndp operations, which are
            used on lanswitch products."
        ::= { unisHgmp 5 }

    unisNDPStatus OBJECT-TYPE
        SYNTAX      INTEGER
            {
                disable(0),
                enable(1)
            }
        MAX-ACCESS  read-write
        STATUS      current
        DESCRIPTION
            "NDP protocol module enable flag"
        DEFVAL { enable }
        ::= { unisNDPObject 1 }

    unisNDPHelloTimer OBJECT-TYPE
        SYNTAX      Integer32 (5..254)
        MAX-ACCESS  read-write
        STATUS      current
        DESCRIPTION
            "NDP packet transmission interval, measured in seconds."
        DEFVAL { 60 }
        ::= { unisNDPObject 2 }

    unisNDPAgingTime OBJECT-TYPE
        SYNTAX      Integer32(5..255)
        MAX-ACCESS  read-write
        STATUS      current
        DESCRIPTION
            "How long the NDP information of the local switch can be hold in
            the adjacent switch, measured in seconds."
        DEFVAL { 180 }
        ::= { unisNDPObject 3 }

    unisNDPChange OBJECT-TYPE
        SYNTAX      Counter32
        MAX-ACCESS  read-only
        STATUS      current
        DESCRIPTION
            "Change identifier of the Neighbor table"
        DEFVAL { 0 }
        ::= { unisNDPObject 4 }

    unisNDPPortTable OBJECT-TYPE
        SYNTAX      SEQUENCE OF UnisNDPPortEntry
        MAX-ACCESS  not-accessible
        STATUS      current
        DESCRIPTION
            "Configure to enable/disable the interface NDP of the switch."
        ::= { unisNDPObject 5 }

    unisNDPPortEntry OBJECT-TYPE
        SYNTAX      UnisNDPPortEntry
        MAX-ACCESS  not-accessible
        STATUS      current
        DESCRIPTION
            ""
        INDEX
            {
                unisNDPIfIndex
            }
        ::= { unisNDPPortTable 1 }

    UnisNDPPortEntry ::=
        SEQUENCE
            {
                unisNDPIfIndex       Integer32,
                unisNDPPortStatus    INTEGER
            }

    unisNDPIfIndex OBJECT-TYPE
        SYNTAX      Integer32
        MAX-ACCESS  read-only
        STATUS      current
        DESCRIPTION
            "Unique identifier of an interface of the device."
        ::= { unisNDPPortEntry 1 }

    unisNDPPortStatus OBJECT-TYPE
        SYNTAX      INTEGER
            {
                disable(0),
                enable(1)
            }
        MAX-ACCESS  read-write
        STATUS      current
        DESCRIPTION
            "If it is enable, the device will send and receive the NDP
            packets via the interface. To disable the NDP function on the
            interface, set the entry as false."
        DEFVAL { enable }
        ::= { unisNDPPortEntry 2 }

    unisNDPPortNbTable OBJECT-TYPE
        SYNTAX      SEQUENCE OF UnisNDPPortNbEntry
        MAX-ACCESS  not-accessible
        STATUS      current
        DESCRIPTION
            "NDP neighbor information on the switch."
        ::= { unisNDPObject 6 }

    unisNDPPortNbEntry OBJECT-TYPE
        SYNTAX      UnisNDPPortNbEntry
        MAX-ACCESS  not-accessible
        STATUS      current
        DESCRIPTION
            ""
        INDEX
            {
                unisNDPIfIndex,
                unisNDPPortNbDeviceId,
                unisNDPPortNbPortName
            }
        ::= { unisNDPPortNbTable 1 }

    UnisNDPPortNbEntry ::=
        SEQUENCE
            {
                unisNDPPortNbDeviceId      OCTET STRING,
                unisNDPPortNbPortName      OCTET STRING,
                unisNDPPortNbDeviceName    OCTET STRING,
                unisNDPPortNbPortMode      INTEGER,
                unisNDPPortNbProductVer    OCTET STRING,
                unisNDPPortNbHardVer       OCTET STRING,
                unisNDPPortNbBootromVer    OCTET STRING,
                unisNDPPortNbSoftVer       OCTET STRING,
                unisNDPPortNbAgingtime     Integer32
            }

    unisNDPPortNbDeviceId OBJECT-TYPE
        SYNTAX      OCTET STRING(SIZE(0..10))
        MAX-ACCESS  read-only
        STATUS      current
        DESCRIPTION
            "2 bytes address type of the member switch + 2 bytes zero + MAC
            address, expressed as a character string of the hexadecimal
            number."
        ::= { unisNDPPortNbEntry 1 }

    unisNDPPortNbPortName OBJECT-TYPE
        SYNTAX      OCTET STRING(SIZE(0..47))
        MAX-ACCESS  read-only
        STATUS      current
        DESCRIPTION
            "Unique identifier of a port. A null string indicates that the
            field was not included in in the latest NDP packet. Interface
            type + card number / slot number / sequence number."
        ::= { unisNDPPortNbEntry 2 }

    unisNDPPortNbDeviceName OBJECT-TYPE
        SYNTAX      OCTET STRING
        MAX-ACCESS  read-only
        STATUS      current
        DESCRIPTION
            "Device name. A null string indicates that the field was not
            included in the latest NDP packet."
        ::= { unisNDPPortNbEntry 3 }

    unisNDPPortNbPortMode OBJECT-TYPE
        SYNTAX      INTEGER
            {
                full(1),
                half(2),
                auto(3)
            }
        MAX-ACCESS  read-only
        STATUS      current
        DESCRIPTION
            "The neighbor port duplex mode."
        ::= { unisNDPPortNbEntry 4 }

    unisNDPPortNbProductVer OBJECT-TYPE
        SYNTAX      OCTET STRING
        MAX-ACCESS  read-only
        STATUS      current
        DESCRIPTION
            "Product version. A null string indicates that the field was
            not included in the latest NDP packet."
        ::= { unisNDPPortNbEntry 5 }

    unisNDPPortNbHardVer OBJECT-TYPE
        SYNTAX      OCTET STRING
        MAX-ACCESS  read-only
        STATUS      current
        DESCRIPTION
            "Hardware version. A null string indicates that the field was
            not included in the latest NDP packet."
        ::= { unisNDPPortNbEntry 6 }

    unisNDPPortNbBootromVer OBJECT-TYPE
        SYNTAX      OCTET STRING
        MAX-ACCESS  read-only
        STATUS      current
        DESCRIPTION
            "Bootrom version. A null string indicates that the field was
            not included in the latest NDP packet."
        ::= { unisNDPPortNbEntry 7 }

    unisNDPPortNbSoftVer OBJECT-TYPE
        SYNTAX      OCTET STRING
        MAX-ACCESS  read-only
        STATUS      current
        DESCRIPTION
            "Software version. A null string indicates that the field was
            not included in the latest NDP packet."
        ::= { unisNDPPortNbEntry 8 }

    unisNDPPortNbAgingtime OBJECT-TYPE
        SYNTAX      Integer32 (5..255)
        MAX-ACCESS  read-only
        STATUS      current
        DESCRIPTION
            "How long the NDP information of the local switch can be hold
            in the adjacent switch, measured in seconds."
        ::= { unisNDPPortNbEntry 9 }

--
-- NTDP management objects
--

    unisNTDPObject OBJECT-IDENTITY
        STATUS      current
        DESCRIPTION
            "This MIB contains objects to manage the ntdp operations, which
            are used on lanswitch products."
        ::= { unisHgmp 4 }

    unishgmpNTDPCollectTopTime OBJECT-TYPE
        SYNTAX      Integer32 (0..65535)
        MAX-ACCESS  read-write
        STATUS      current
        DESCRIPTION
            "Topology collection interval of the administrator switch of
            the cluster, measured in minutes."
        DEFVAL { 0 }
        ::= { unisNTDPObject 1 }

    unishgmpNTDPHopRange OBJECT-TYPE
        SYNTAX      Integer32 (1..16)
        MAX-ACCESS  read-write
        STATUS      current
        DESCRIPTION
            "Range of the topology collection of the administrator switch"
        DEFVAL { 3 }
        ::= { unisNTDPObject 2 }

    unishgmpNTDPRun OBJECT-TYPE
        SYNTAX      INTEGER
            {
                false(0),
                true(1)
            }
        MAX-ACCESS  read-write
        STATUS      current
        DESCRIPTION
            "Enable/Disable the NTDP function on the switch."
        DEFVAL { true }
        ::= { unisNTDPObject 3 }

    unishgmpNTDPPortDelay OBJECT-TYPE
        SYNTAX      Integer32 (1..100)
        MAX-ACCESS  read-write
        STATUS      current
        DESCRIPTION
            "Set the delay to forward the topology request via the ports,
            measured in milliseconds."
        DEFVAL { 20 }
        ::= { unisNTDPObject 4 }

    unishgmpNTDPHopDelay OBJECT-TYPE
        SYNTAX      Integer32 (1..1000)
        MAX-ACCESS  read-write
        STATUS      current
        DESCRIPTION
            "Set the delay to forward the topology request from every hop,
            measured in milliseconds."
        DEFVAL { 200 }
        ::= { unisNTDPObject 5 }

    unishgmpNTDPLastTopCollectDuration OBJECT-TYPE
        SYNTAX      Integer32
        MAX-ACCESS  read-only
        STATUS      current
        DESCRIPTION
            "Duration of the latest overall topology collection, a
            performance count measured in seconds."
        DEFVAL { 0 }
        ::= { unisNTDPObject 6 }

    unishgmpNTDPCacheChange OBJECT-TYPE
        SYNTAX      Integer32 (0..65535)
        MAX-ACCESS  read-only
        STATUS      current
        DESCRIPTION
            "Add 1 when the device table changes. The network administrator
            will check if it has changed before accessing the table. If it
            has not changed, he will not access again."
        DEFVAL { 0 }
        ::= { unisNTDPObject 7 }

    unishgmpNTDPTOPTableChange OBJECT-TYPE
        SYNTAX      Integer32 (0..65535)
        MAX-ACCESS  read-only
        STATUS      current
        DESCRIPTION
            "Add 1 when the topology table changes. The network
            administrator will check if it has changed before accessing
            the table. If it has not changed, he will not access again."
        DEFVAL { 0 }
        ::= { unisNTDPObject 8 }

    unishgmpNTDPInterfaceTable OBJECT-TYPE
        SYNTAX      SEQUENCE OF UnisHgmpNTDPInterfaceEntry
        MAX-ACCESS  not-accessible
        STATUS      current
        DESCRIPTION
            "Enable/Disable the NTDP on the switch port."
        ::= { unisNTDPObject 9 }

    unishgmpNTDPInterfaceEntry OBJECT-TYPE
        SYNTAX      UnisHgmpNTDPInterfaceEntry
        MAX-ACCESS  not-accessible
        STATUS      current
        DESCRIPTION
            ""
        INDEX
            {
                unishgmpNTDPInterfaceIfIndex
            }
        ::= { unishgmpNTDPInterfaceTable 1 }

    UnisHgmpNTDPInterfaceEntry ::=
        SEQUENCE
            {
                unishgmpNTDPInterfaceIfIndex    Integer32,
                unishgmpNTDPInterfaceEnable     INTEGER
            }

    unishgmpNTDPInterfaceIfIndex OBJECT-TYPE
        SYNTAX      Integer32
        MAX-ACCESS  read-only
        STATUS      current
        DESCRIPTION
            "Unique identifier an interface of the device."
        ::= { unishgmpNTDPInterfaceEntry 1 }

    unishgmpNTDPInterfaceEnable OBJECT-TYPE
        SYNTAX      INTEGER
            {
                false(0),
                true(1)
            }
        MAX-ACCESS  read-write
        STATUS      current
        DESCRIPTION
            "If it is true, the device will send and receive the NTDP
            packets via the interface. To disable the NTDP function on the
            interface, set the entry as false."
        DEFVAL { true }
        ::= { unishgmpNTDPInterfaceEntry 2 }

    unishgmpNTDPCacheTable OBJECT-TYPE
        SYNTAX      SEQUENCE OF UnisHgmpNTDPCacheEntry
        MAX-ACCESS  not-accessible
        STATUS      current
        DESCRIPTION
            "Access the information about the switch from the topology table."
        ::= { unisNTDPObject 10 }

    unishgmpNTDPCacheEntry OBJECT-TYPE
        SYNTAX      UnisHgmpNTDPCacheEntry
        MAX-ACCESS  not-accessible
        STATUS      current
        DESCRIPTION
            ""
        INDEX
            {
                unishgmpNTDPCacheHashIndex,
                unishgmpNTDPCacheDeviceID
            }
        ::= { unishgmpNTDPCacheTable 1 }

    UnisHgmpNTDPCacheEntry ::=
        SEQUENCE
            {
                unishgmpNTDPCacheHashIndex       Integer32,
                unishgmpNTDPCacheDeviceID        OCTET STRING,
                unishgmpNTDPCacheClusterName     OCTET STRING,
                unishgmpNTDPCacheClusterRole     INTEGER,
                unishgmpNTDPCacheCapabilities    INTEGER,
                unishgmpNTDPCacheVersion         OCTET STRING,
                unishgmpNTDPCachePlatform        OCTET STRING,
                unishgmpNTDPCacheMngVLAN         INTEGER,
                unishgmpNTDPCacheHop             INTEGER
            }

    unishgmpNTDPCacheHashIndex OBJECT-TYPE
        SYNTAX      Integer32 (0..255)
        MAX-ACCESS  read-only
        STATUS      current
        DESCRIPTION
            "Our NTDP information is saved in the HASH table on the
            administrator switch. Using DeviceID as index will lead to the
            comparison of a large amount of character strings, which puts
            too many burdens on the administrator switch. A HAHSIndex is
            added to reduce the character string comparison to the
            least range."
        ::= { unishgmpNTDPCacheEntry 1 }

    unishgmpNTDPCacheDeviceID OBJECT-TYPE
        SYNTAX      OCTET STRING(SIZE(0..10))
        MAX-ACCESS  read-only
        STATUS      current
        DESCRIPTION
            "2 bytes address type of the member switch + 2 bytes zero + MAC
            address, expressed as a character string of the
            hexadecimal number."
        ::= { unishgmpNTDPCacheEntry 2 }

    unishgmpNTDPCacheClusterName OBJECT-TYPE
        SYNTAX      OCTET STRING
        MAX-ACCESS  read-only
        STATUS      current
        DESCRIPTION
            "Name of the cluster including the device."
        ::= { unishgmpNTDPCacheEntry 3 }

    unishgmpNTDPCacheClusterRole OBJECT-TYPE
        SYNTAX      INTEGER
            {
                roleCOSW(1),
                roleMSW(2),
                roleBKSW(3),
                roleCASW(16),
                roleUNISW(17)
            }
        MAX-ACCESS  read-only
        STATUS      current
        DESCRIPTION
            "Cluster role of the current device, which can be a
            administrator switch (0x01), member switch(0x02), backup
            switch(0x03), candidate switch(0x10) or an independent
            switch (incapable of cluster member) (0x11)."
        DEFVAL { 17 }
        ::= { unishgmpNTDPCacheEntry 4 }

    unishgmpNTDPCacheCapabilities OBJECT-TYPE
        SYNTAX      INTEGER
        MAX-ACCESS  read-only
        STATUS      current
        DESCRIPTION
            "The capabilities of the device. FF indicates that the field
            was not included in in the latest NTDP packet."
        DEFVAL { 255 }
        ::= { unishgmpNTDPCacheEntry 5 }

    unishgmpNTDPCacheVersion OBJECT-TYPE
        SYNTAX      OCTET STRING
        MAX-ACCESS  read-only
        STATUS      current
        DESCRIPTION
            "The version information of the corresponding device. A null
            string indicates that the field was not included in in the
            latest NTDP packet."
        ::= { unishgmpNTDPCacheEntry 6 }

    unishgmpNTDPCachePlatform OBJECT-TYPE
        SYNTAX      OCTET STRING
        MAX-ACCESS  read-only
        STATUS      current
        DESCRIPTION
            "Hardware platform. A null string indicates that the field
            was not included in the latest NTDP packet."
        ::= { unishgmpNTDPCacheEntry 7 }

    unishgmpNTDPCacheMngVLAN OBJECT-TYPE
        SYNTAX      INTEGER
        MAX-ACCESS  read-only
        STATUS      current
        DESCRIPTION
            "The management VLAN ID of the device."
        DEFVAL { 1 }
        ::= { unishgmpNTDPCacheEntry 8 }

    unishgmpNTDPCacheHop OBJECT-TYPE
        SYNTAX      INTEGER
        MAX-ACCESS  read-only
        STATUS      current
        DESCRIPTION
            "Hops to this switch."
        ::= { unishgmpNTDPCacheEntry 9 }

    unishgmpNTDPTopTable OBJECT-TYPE
        SYNTAX      SEQUENCE OF UnisHgmpNTDPTopEntry
        MAX-ACCESS  not-accessible
        STATUS      current
        DESCRIPTION
            "Access the topology structure collected by the NTDP."
        ::= { unisNTDPObject 11 }

    unishgmpNTDPTopEntry OBJECT-TYPE
        SYNTAX      UnisHgmpNTDPTopEntry
        MAX-ACCESS  not-accessible
        STATUS      current
        DESCRIPTION
            ""
        INDEX
            {
                unishgmpNTDPTopHashIndex,
                unishgmpNTDPTopEdgeStartDevID,
                unishgmpNTDPTopEdgeIndex
            }
        ::= { unishgmpNTDPTopTable 1 }

    UnisHgmpNTDPTopEntry ::=
        SEQUENCE
            {
                unishgmpNTDPTopHashIndex                  Integer32,
                unishgmpNTDPTopEdgeStartDevID             OCTET STRING,
                unishgmpNTDPTopEdgeIndex                  Integer32,
                unishgmpNTDPTopEdgeEndDevID               OCTET STRING,
                unishgmpNTDPTopEdgeStartPort              OCTET STRING,
                unishgmpNTDPTopEdgeStartPortFullDuplex    INTEGER,
                unishgmpNTDPTopEdgeStartPortSpeed         Integer32,
                unishgmpNTDPTopEdgeEndPort                OCTET STRING,
                unishgmpNTDPTopLinkStatus                 INTEGER
            }

    unishgmpNTDPTopHashIndex OBJECT-TYPE
        SYNTAX      Integer32 (0..255)
        MAX-ACCESS  read-only
        STATUS      current
        DESCRIPTION
            "Our NTDP information is saved in the HASH table on the
            administrator switch. Using DeviceID as index will lead to the
            comparison of a large amount of character strings, which puts
            too many burdens on the administrator switch. A HAHSIndex is
            added to reduce the character string comparison to the
            least range."
        ::= { unishgmpNTDPTopEntry 1 }

    unishgmpNTDPTopEdgeStartDevID OBJECT-TYPE
        SYNTAX      OCTET STRING(SIZE(0..10))
        MAX-ACCESS  read-only
        STATUS      current
        DESCRIPTION
            "2 bytes address type of the member switch + 2 bytes zero + MAC
            address, expressed as a character string of the hexadecimal number."
        ::= { unishgmpNTDPTopEntry 2 }

    unishgmpNTDPTopEdgeIndex OBJECT-TYPE
        SYNTAX      Integer32 (0..65535)
        MAX-ACCESS  read-only
        STATUS      current
        DESCRIPTION
            "Edge index of this entry in the data structure."
        ::= { unishgmpNTDPTopEntry 3 }

    unishgmpNTDPTopEdgeEndDevID OBJECT-TYPE
        SYNTAX      OCTET STRING(SIZE(0..10))
        MAX-ACCESS  read-only
        STATUS      current
        DESCRIPTION
            "2 bytes address type of the member switch + 2 bytes zero + MAC
            address, expressed as a character string of the hexadecimal number."
        ::= { unishgmpNTDPTopEntry 4 }

    unishgmpNTDPTopEdgeStartPort OBJECT-TYPE
        SYNTAX      OCTET STRING(SIZE(0..47))
        MAX-ACCESS  read-only
        STATUS      current
        DESCRIPTION
            "The number of the first port of a topology edge. Interface
            type + card number / slot number / sequence number."
        ::= { unishgmpNTDPTopEntry 5 }

    unishgmpNTDPTopEdgeStartPortFullDuplex OBJECT-TYPE
        SYNTAX      INTEGER
            {
                half(0),
                full(1)
            }
        MAX-ACCESS  read-only
        STATUS      current
        DESCRIPTION
            "The full-duplex status of the first port on a topology edge."
        DEFVAL { half }
        ::= { unishgmpNTDPTopEntry 6 }

    unishgmpNTDPTopEdgeStartPortSpeed OBJECT-TYPE
        SYNTAX      Integer32
        MAX-ACCESS  read-only
        STATUS      current
        DESCRIPTION
            "The speed of the first port on a topology edge."
        DEFVAL { 0 }
        ::= { unishgmpNTDPTopEntry 7 }

    unishgmpNTDPTopEdgeEndPort OBJECT-TYPE
        SYNTAX      OCTET STRING(SIZE(0..47))
        MAX-ACCESS  read-only
        STATUS      current
        DESCRIPTION
            "The number of the last port of a topology edge. Interface
            type + card number / slot number / sequence number."
        ::= { unishgmpNTDPTopEntry 8 }

    unishgmpNTDPTopLinkStatus OBJECT-TYPE
        SYNTAX      INTEGER
            {
                forwarding(1),
                blocking(2)
            }
        MAX-ACCESS  read-only
        STATUS      current
        DESCRIPTION
            "In STP or RSTP, it describes link status according to port STP
            steady status. In MSTP it describes STP steady status of the
            instance which management VLAN belongs to. Either
            'hgmpNTDPTopEdgeStartPort' or 'hgmpNTDPTopEdgeEndPort' STP
            steady status is 'blocking', this object is 'blocking',
            otherwise is 'forwarding'.
            If STP or MSTP is disabled, this object is 'forwarding'."
        ::= { unishgmpNTDPTopEntry 11 }

    unishgmpStackEventsV2 OBJECT-IDENTITY
        STATUS      current
        DESCRIPTION
            "Definition point for Stack notifications."
        ::= { unisStackObject 0 }

    unishgmpStackMemberfailure NOTIFICATION-TYPE
        OBJECTS
            {
                unishgmpStackMemberDeviceId
            }
        STATUS      current
        DESCRIPTION
            "When a stack member failure, send a snmp trap to the network
            management."
        ::= { unishgmpStackEventsV2 1 }

    unishgmpStackMemberRecover NOTIFICATION-TYPE
        OBJECTS
            {
                unishgmpStackMemberDeviceId
            }
        STATUS      current
        DESCRIPTION
            "When a stack member Recover, send a snmp trap to the network
            management."
        ::= { unishgmpStackEventsV2 2 }

    unishgmpStackMemberStatusChange NOTIFICATION-TYPE
        OBJECTS
            {
                unishgmpStackMemberDeviceId,
                unishgmpNTDPCacheClusterRole
            }
        STATUS      current
        DESCRIPTION
            "When a stack member status change, send a snmp trap to the network
            management."
        ::= { unishgmpStackEventsV2 3 }
END
