-- ============================================================================
-- Copyright (c) 2020 Unisyue Technologies Co., Ltd.  All rights reserved.
--
-- Description: The purpose of this MIB file is to provide the definition of
--              the MAC Information general configuration.
-- Reference:
-- Version: V1.2
-- History:
-- V1.0 2007-12-28
--   Initial version, created by gejianzhuang
-- V1.1 2009-08-13
--   Add 'unisMACInformationTrapObjectsExt' by gejianzhuang
-- V1.2 2013-05-02
--   Add 'unisMACInformationMovedTrap' by yangjie
-- ============================================================================
UNIS-MAC-INFORMATION-MIB DEFINITIONS ::= BEGIN

IMPORTS
        unisCommon
    FROM UNIS-OID-MIB
        Unsigned32, Counter32, OBJECT-TYPE, MODULE-IDENTITY, NOTIFICATION-TYPE, Integer32
    FROM SNMPv2-SMI
        TEXTUAL-CONVENTION, MacAddress
    FROM SNMPv2-TC
        ifIndex
    FROM IF-MIB;

-- Node definitions
unisMACInformation MODULE-IDENTITY
    LAST-UPDATED "200712281912Z"        -- DEC 28, 2007 at 19:12 GMT
    ORGANIZATION
        "Unisyue Technologies Co., Ltd."
    CONTACT-INFO
        ""
    DESCRIPTION
        "This MIB file is to provide the definition of the MAC Information
        general configuration.  MAC Information feature is used to
        make that the changed MAC information in the monitored device is
        knowable in remote monitoring device."
    REVISION "200712281912Z"
    DESCRIPTION
        "The initial version of this MIB file."
    ::= { unisCommon 87 }

UnisMACInfoWorkMode ::=  TEXTUAL-CONVENTION
    STATUS      current
    DESCRIPTION
        "The working mode of the MAC Information feature."
    SYNTAX      INTEGER
        {
            trap(1),
            syslog(2)
        }

unisMACInformationObjects OBJECT IDENTIFIER ::= { unisMACInformation 1 }

unisMACInformationMibGlobal OBJECT IDENTIFIER  ::= { unisMACInformationObjects 1 }

unisMACInformationMIBTableTroop OBJECT IDENTIFIER  ::= { unisMACInformationObjects 2 }

unisMACInformationMibTrap OBJECT IDENTIFIER  ::= { unisMACInformationObjects 3 }

unisMACInformationMibTrapExt OBJECT IDENTIFIER  ::= { unisMACInformationObjects 4 }


unisMACInformationEnabled OBJECT-TYPE
    SYNTAX      INTEGER
        {
            enabled(1),
            disabled(2)
        }
    MAX-ACCESS  read-write
    STATUS      current
    DESCRIPTION
        "The value is a global setting.  The feature will not work until the
        value is set to enabled(1).  If the value is set to disabled(2),
        the feature will stop working even there are interfaces that have
        been enabled the feature."
    DEFVAL { disabled }
    ::= { unisMACInformationMibGlobal 1 }

unisMACInformationcSendInterval OBJECT-TYPE
    SYNTAX      Unsigned32(1..20000)
    MAX-ACCESS  read-write
    STATUS      current
    DESCRIPTION
        "The maximum interval that the device generate syslogs or traps.
        The unit is second."
    DEFVAL { 1 }
    ::= { unisMACInformationMibGlobal 2 }


unisMACInformationLearntMACNum OBJECT-TYPE
    SYNTAX      Counter32
    MAX-ACCESS  read-only
    STATUS      current
    DESCRIPTION
        "The number of MAC addresses that learnt by the device since the
        unisMACInformationEnabled is set to enabled(1) and unisMACLearntEnable
        is set to enabled(1) at least on one interface. If the unisMACInformationEnabled
        is set to disabled(2), the object will always return 0."
    ::= { unisMACInformationMibGlobal 3 }

unisMACInformationRemovedMACNum OBJECT-TYPE
    SYNTAX      Counter32
    MAX-ACCESS  read-only
    STATUS      current
    DESCRIPTION
        "The number of MAC addresses that removed by the device since the
        unisMACInformationEnabled is set to enabled(1) and unisMACRemovedEnable
        is set to enabled(1) at least on one interface. If the unisMACInformationEnabled
        is set to disabled(2), the object will always return 0."
    ::= { unisMACInformationMibGlobal 4 }

unisMACInformationTrapSendNum OBJECT-TYPE
    SYNTAX      Counter32
    MAX-ACCESS  read-only
    STATUS      current
    DESCRIPTION
        "The number of traps that have been generated. This object is valid
        only when the unisMACInfomationWorkMode is set to trap(1). If the
        unisMACInfomationWorkMode is set to syslog(2), the object will always return 0."
    ::= { unisMACInformationMibGlobal 5 }


unisMACInformationSyslogSendNum OBJECT-TYPE
    SYNTAX      Counter32
    MAX-ACCESS  read-only
    STATUS      current
    DESCRIPTION
        "The number of syslogs that have been generated. This object is valid only
        when the unisMACInfomationWorkMode is set to syslog(2). If the
        unisMACInfomationWorkMode is set to trap(1), the object will always return 0."
    ::= { unisMACInformationMibGlobal 6 }


unisMACInformationCacheLen OBJECT-TYPE
    SYNTAX      Unsigned32(0..1000)
    MAX-ACCESS  read-write
    STATUS      current
    DESCRIPTION
        "The maximum queue lenth used to cache the changed MAC addresses information
        in the monitored device. If the value is set to 0, syslog or trap will generate
        as soon as there is a MAC address learnt or removed."
    DEFVAL { 50 }
    ::= { unisMACInformationMibGlobal 7 }

unisMACInfomationWorkMode OBJECT-TYPE
    SYNTAX      UnisMACInfoWorkMode
    MAX-ACCESS  read-write
    STATUS      current
    DESCRIPTION
        "The working mode of MAC Information feature.  If the object is
        set to trap(1), the device will use trap mode to notify the MAC
        address information and all properties of trap interrelated is
        valid.  If the object is set to syslog(2), the device will use
        syslog mode to notify the MAC address information and all
        properties of trap interrelated is invalid."
    ::= { unisMACInformationMibGlobal 8}


--unisMACInfomationIfTable

unisMACInfomationIfTable OBJECT-TYPE
    SYNTAX      SEQUENCE OF UnisMACInfomationIfEntry
    MAX-ACCESS  not-accessible
    STATUS      current
    DESCRIPTION
        "The table is used to enable or disable the MAC Information feature
        on interfaces."
    ::= { unisMACInformationMIBTableTroop 1 }

unisMACInfomationIfEntry OBJECT-TYPE
    SYNTAX      UnisMACInfomationIfEntry
    MAX-ACCESS  not-accessible
    STATUS      current
    DESCRIPTION
        "The entry of unisMACInfomationIfTable."
    INDEX
        {
            ifIndex
        }
    ::= { unisMACInfomationIfTable 1 }

UnisMACInfomationIfEntry ::= SEQUENCE
    {
        unisMACLearntEnable     INTEGER,
        unisMACRemovedEnable    INTEGER
    }

unisMACLearntEnable OBJECT-TYPE
    SYNTAX      INTEGER
        {
            enabled(1),
            disabled(2)
        }
    MAX-ACCESS  read-write
    STATUS      current
    DESCRIPTION
        "If the object is set to enabled(1) on interface, the device
        will cache the MAC address information that learnt on the interface."
    DEFVAL { disabled }
    ::= { unisMACInfomationIfEntry 1 }

unisMACRemovedEnable OBJECT-TYPE
    SYNTAX      INTEGER
        {
            enabled(1),
            disabled(2)
        }
    MAX-ACCESS  read-write
    STATUS      current
    DESCRIPTION
        "If the object is set to enable(1) on interface, the device
        will cache the MAC address information that removed on the interface."
    DEFVAL { disabled }
    ::= { unisMACInfomationIfEntry 2 }


-- unisMACNotificationTrap

unisMACInformationTraps OBJECT IDENTIFIER ::= { unisMACInformationMibTrap 0 }

unisMACInformationChangedTrap NOTIFICATION-TYPE
    OBJECTS
        {
            unisMACInfoTrapIndex,
            unisMACInfoTrapCount,
            unisMACInfoTrapMsg
        }
    STATUS      current
    DESCRIPTION
        "When the cached number of MAC address information is reached the
        value specified by unisMACInformationCacheLen, trap is generated
        and is sent to the remote monitoring device.  The trap is also
        generated when the amount of time elapsed since the previous
        notification is greater than the interval value specified by
        unisMACInformationcSendInterval and there is at least one cached
        MAC address information learnt or removed. The object is valid
        only when unisMACInfomationWorkMode is set to trap(1).  When the
        unisMACInfomationWorkMode is set to syslog(2), No trap will be
        generated even unisMACInformationEnabled is set to enabled(1) and
        the feature is enabled on interface."
    ::= { unisMACInformationTraps 1 }

unisMACInformationTrapObjects OBJECT IDENTIFIER  ::= { unisMACInformationMibTrap 2 }

unisMACInfoTrapIndex OBJECT-TYPE
    SYNTAX      Unsigned32(1..4294967295)
    MAX-ACCESS  accessible-for-notify
    STATUS      current
    DESCRIPTION
        "The sequence number of trap information. When it reaches the
        maximum value, it should be set to 1."
    ::= { unisMACInformationTrapObjects 1 }

unisMACInfoTrapCount OBJECT-TYPE
    SYNTAX      Unsigned32
    MAX-ACCESS  accessible-for-notify
    STATUS      current
    DESCRIPTION
        "The cell number of the current trap information.  The trap
        message may consists of more than one MAC address information.
        Each of the one MAC address information in one trap is called cell."
    ::= { unisMACInformationTrapObjects 2 }

unisMACInfoTrapMsg OBJECT-TYPE
    SYNTAX      OCTET STRING(SIZE(1..254))
    MAX-ACCESS  accessible-for-notify
    STATUS      current
    DESCRIPTION
        "This object is the MAC information that learnt or removed
        in the monitored device. It can consists of more than
        one MAC information in the object.
        This object is in the format of '<cell1><cell2>...'. Each
        cell consists of 12 octets in the format of
        '<operationType><VLAN><MAC><MACtype><ifIndex>'.

        <operationType> is the reason type of MAC address changed and have
        size of 1 octet. It only supports the following values.
        1 - MAC learnt.
        2 - MAC removed.

        <VLAN> is the vlan number that correspond to the MAC address in
        MAC address table and has size of 2 octet.

        <MAC> is the MAC address and has size of 6 octets.

        <MACtype> is the MAC address type and has size of 1 octet. It only
        supports the following values.
        0 - Unknown
        1 - Learnt
        2 - Config dynamic
        3 - Config static
        4 - Blackhole
        5 - Security
        6 - 802.1x
        7 - MAC authentication
        8 - Voice VLAN
        9 - Reserved

        <ifIndex> is the index of the interface where the MAC
        address is learnt or removed and has size of 2 octets."
    ::= { unisMACInformationTrapObjects 3 }

-- unisMACNotificationTrapExt

unisMACInformationTrapsExt OBJECT IDENTIFIER ::= { unisMACInformationMibTrapExt 0 }

unisMACInformationChangedTrapExt NOTIFICATION-TYPE
    OBJECTS
        {
            unisMACInfoTrapVerExt,
            unisMACInfoTrapIndexExt,
            unisMACInfoTrapCountExt,
            unisMACInfoTrapMsgExt
        }
    STATUS      current
    DESCRIPTION
        "When the cached number of MAC address information is reached the
        value specified by unisMACInformationCacheLen, trap is generated
        and is sent to the remote monitoring device.  The trap is also
        generated when the amount of time elapsed since the previous
        notification is greater than the interval value specified by
        unisMACInformationcSendInterval and there is at least one cached
        MAC address information learnt or removed.  The object is valid
        only when unisMACInfomationWorkMode is set to trap(1).  When the
        unisMACInfomationWorkMode is set to syslog(2), No trap will be
        generated even unisMACInformationEnabled is set to enabled(1) and
        the feature is enabled on interface."
    ::= { unisMACInformationTrapsExt 1 }

unisMACInformationMovedTrap NOTIFICATION-TYPE
    OBJECTS
        {
            unisMACInfoTrapMsgMovedAddress,
            unisMACInfoTrapMsgMovedVlan,
            unisMACInfoTrapMsgMovedFromIf,
            unisMACInfoTrapMsgMovedToIf,
            unisMACInfoTrapMsgMovedCount
        }
    STATUS      current
    DESCRIPTION
        "When the MAC address has been moved to another interface, trap
        is generated and is sent to the remote monitoring device."
    ::= { unisMACInformationTrapsExt 2 }

unisMACInformationTrapObjectsExt OBJECT IDENTIFIER  ::= { unisMACInformationMibTrapExt 2 }

unisMACInfoTrapVerExt OBJECT-TYPE
    SYNTAX      Unsigned32
    MAX-ACCESS  accessible-for-notify
    STATUS      current
    DESCRIPTION
        "The version of trap information."
    ::= { unisMACInformationTrapObjectsExt 1 }

unisMACInfoTrapIndexExt OBJECT-TYPE
    SYNTAX      Unsigned32(1..4294967295)
    MAX-ACCESS  accessible-for-notify
    STATUS      current
    DESCRIPTION
        "The sequence number of trap information.  When it reaches the
        maximum value, it should be set to 1."
    ::= { unisMACInformationTrapObjectsExt 2 }

unisMACInfoTrapCountExt OBJECT-TYPE
    SYNTAX      Unsigned32
    MAX-ACCESS  accessible-for-notify
    STATUS      current
    DESCRIPTION
        "The cell number of the current trap information.  The trap
        message may consists of more than one MAC address information.
        Each of the one MAC address information in one trap is called cell."
    ::= { unisMACInformationTrapObjectsExt 3 }

unisMACInfoTrapMsgExt OBJECT-TYPE
    SYNTAX      OCTET STRING(SIZE(1..254))
    MAX-ACCESS  accessible-for-notify
    STATUS      current
    DESCRIPTION
        "This object is the MAC information that learnt or removed
        in the monitored device.  It can consists of more than
        one MAC information in the object.
        This object is in the format of '<cell1><cell2>...'.  Each
        cell consists of 14 octets in the format of
        '<operationType><VLAN><MAC><MACtype><ifIndex>'.

        <operationType> is the reason type of MAC address changed and have
        size of 1 octet.  It only supports the following values.
        1 - MAC learnt.
        2 - MAC removed.

        <VLAN> is the vlan number that correspond to the MAC address in
        MAC address table and has size of 2 octet.

        <MAC> is the MAC address and has size of 6 octets.

        <MACtype> is the MAC address type and has size of 1 octet.  It only
        supports the following values.
        0 - Unknown
        1 - Learnt
        2 - Config dynamic
        3 - Config static
        4 - Blackhole
        5 - Security
        6 - 802.1x
        7 - MAC authentication
        8 - Voice VLAN
        9 - Reserved

        <ifIndex> is the index of the interface where the MAC
        address is learnt or removed and has size of 4 octets."
    ::= { unisMACInformationTrapObjectsExt 4 }

unisMACInfoTrapMsgMovedAddress   OBJECT-TYPE
    SYNTAX  MacAddress
    MAX-ACCESS  accessible-for-notify
    STATUS  current
    DESCRIPTION
        "The MAC address that is moved between interfaces."
        ::= { unisMACInformationTrapObjectsExt  5 }

unisMACInfoTrapMsgMovedVlan OBJECT-TYPE
    SYNTAX      Integer32 (1..4094)
    MAX-ACCESS  accessible-for-notify
    STATUS      current
    DESCRIPTION
        "The VLAN number in which the MAC address is moved."
        ::= { unisMACInformationTrapObjectsExt  6}

unisMACInfoTrapMsgMovedFromIf OBJECT-TYPE
    SYNTAX      Integer32 (1..2147483647)
    MAX-ACCESS  accessible-for-notify
    STATUS      current
    DESCRIPTION
        "The index of the interface from which the MAC address is moved."
        ::= { unisMACInformationTrapObjectsExt  7 }

unisMACInfoTrapMsgMovedToIf OBJECT-TYPE
    SYNTAX      Integer32 (1..2147483647)
    MAX-ACCESS  accessible-for-notify
    STATUS      current
    DESCRIPTION
        "The index of the interface to which the MAC address is moved."
        ::= { unisMACInformationTrapObjectsExt  8 }

unisMACInfoTrapMsgMovedCount OBJECT-TYPE
    SYNTAX      Counter32
    MAX-ACCESS  accessible-for-notify
    STATUS      current
    DESCRIPTION
        "The times for which the MAC address has been moved between the
        interfaces."
        ::= { unisMACInformationTrapObjectsExt  9 }

END
