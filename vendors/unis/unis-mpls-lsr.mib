-- =========================================================================
-- Copyright (c) 2020 Unisyue Technologies Co., Ltd.  All rights reserved.
--
-- Description:This file describes the MIB implementation of mpls lsr.
-- Reference:
-- Version: V1.0
-- History:
-- 	    V1.0 6th Mar 2004
--		Initial version
-- =========================================================================
UNIS-MPLS-LSR-MIB DEFINITIONS ::= BEGIN

IMPORTS
   MODULE-IDENTITY, OBJECT-TYPE, NOTIFICATION-TYPE,
   Integer32, Counter32, Unsigned32,
   Counter64, Gauge32
      FROM SNMPv2-SMI
      
   MODULE-COMPLIANCE, OBJECT-GROUP, NOTIFICATION-GROUP
      FROM SNMPv2-CONF
      
   TEXTUAL-CONVENTION, TruthValue, RowStatus, StorageType,
   RowPointer, TimeStamp
      FROM SNMPv2-TC
      
   InterfaceIndex, InterfaceIndexOrZero
      FROM IF-MIB

   unisMpls
      FROM UNIS-OID-MIB

   AddressFamilyNumbers
      FROM IANA-ADDRESS-FAMILY-NUMBERS-MIB
      
   InetAddressIPv4, InetAddressIPv6, InetAddressType
      FROM INET-ADDRESS-MIB;

unisMplsLsr MODULE-IDENTITY
   LAST-UPDATED "200007121200Z"  -- 12 July 2000 12:00:00 EST
   ORGANIZATION
       "Unisyue Technologies Co., Ltd."
   CONTACT-INFO
       ""
   DESCRIPTION
       "This MIB contains managed object definitions for the
        Multiprotocol Label Switching (MPLS) Router as
        defined in: Rosen, E., Viswanathan, A., and R.
        Callon, Multiprotocol Label Switching Architecture,
        Internet Draft <draft-ietf-mpls-arch-06.txt>,
        August 1999."
   
   -- Revision history.
   REVISION
       "200007121200Z"  -- 12 July 2000 12:00:00 EST
   DESCRIPTION
       "Seventh draft version. Fix minor compilation errors."
   REVISION
       "200007071200Z"  -- 07 July 2000 12:00:00 EST
   DESCRIPTION
       "Sixth draft version. Made minor typographical corrections 
        noted from WG mailing list during second working group last
        call."
   REVISION
       "200004261200Z"  -- 26 April 2000 12:00:00 EST
   DESCRIPTION
       "Fifth draft version. Made minor typographical corrections 
        noted from WG mailing list."
   REVISION
       "200004211200Z"  -- 21 April 2000 12:00:00 EST
   DESCRIPTION
       "Fourth draft version.  Made corrections from WG Last 
        Call comments."
   REVISION
       "200003061200Z"  -- 6 March 2000 12:00:00 EST
   DESCRIPTION
       "Third draft version."
   REVISION
       "200002161200Z"  -- 16 February 2000 12:00:00 EST
   DESCRIPTION
       "Second draft version."
   REVISION
       "199906161200Z"  -- 16 June 1999 12:00:00 EST
   DESCRIPTION
      "Initial draft version."
   ::= { unisMpls 1 }


-- Textual Conventions.

UnisMplsLSPID ::= TEXTUAL-CONVENTION
   STATUS        current
   DESCRIPTION
       "An identifier that is assigned to each LSP and is
        used to uniquely identify it.  This is assigned at
        the head end of the LSP and can be used by all LSRs
        to identify this LSP.  This value is piggybacked by
        the signaling protocol when this LSP is signaled
        within the network.  This identifier can then be
        used at each LSR to identify which labels are being
        swapped to other labels for this LSP.  For IPv4
        addresses this results in a 6-octet long cookie."
   SYNTAX        OCTET STRING (SIZE (0..31))

-- An MPLS label.
UnisMplsLabel ::= TEXTUAL-CONVENTION
   STATUS        current
   DESCRIPTION
       "This value represents an MPLS label.  Note that the
        contents of a label field are interpreted in an
        interface-type specific fashion.  For example, the
        20-bit wide label carried in the MPLS shim header is
        contained in bits 0-19 and bits 20-31 must be zero.
        The frame relay label can be either 10 or 23 bits
        wide depending on the size of the DLCI field and
        bits 10-31, or 23-31 must be zero, respectively.
        For an ATM interface, bits 0-15 must be interpreted
        as the VCI, bits 16-23 as the VPI and bits 24-31
        must be zero.  Note that the permissible label
        values are also a function of the interface type.
        For example, the value 3 has special semantics in
        the control plane for an MPLS shim header label and
        is not a valid label value in the data path."
   REFERENCE
       "1. MPLS Label Stack Encoding, Rosen et al, draft-
          ietf-mpls-label-encaps-07.txt, March 2000.
        2. Use of Label Switching on Frame Relay Networks,
          Conta et al, draft-ietf-mpls-fr-03.txt, Nov.
          1998.
        3. MPLS using LDP and ATM VC switching, Davie et al,
          draft-ietf-mpls-atm-02.txt, April 1999."
   SYNTAX  Unsigned32 (0..4294967295)

UnisMplsBitRate ::= TEXTUAL-CONVENTION
   DISPLAY-HINT "d"
   STATUS      current
   DESCRIPTION
       "An estimate of bandwidth in units of 1,000 bits per
        second.  If this object reports a value of 'n' then
        the rate of the object is somewhere in the range of
        'n-500' to 'n+499'. For objects which do not vary in
        bitrate, or for those where no accurate estimation
        can be made, this object should contain the nominal
        bitrate."
   SYNTAX  Integer32 (1..2147483647)

UnisMplsBurstSize ::= TEXTUAL-CONVENTION
   DISPLAY-HINT "d"
   STATUS      current
   DESCRIPTION
       "The number of octets of MPLS data that the stream
        may send back-to-back without concern for policing."
   SYNTAX  Integer32 (1..2147483647)

UnisMplsObjectOwner ::= TEXTUAL-CONVENTION
   STATUS      current
   DESCRIPTION
           "The entity which owns the object in question."
   SYNTAX   INTEGER {
                other(1),
                snmp(2),
                ldp(3),
                rsvp(4),
                crldp(5),
                policyAgent(6),
                unknown (7)
             }

-- Top level components of this MIB.

-- Tables, Scalars
unismplsLsrObjects       OBJECT IDENTIFIER ::= { unisMplsLsr 1 }
-- traps
unismplsLsrNotifications OBJECT IDENTIFIER ::= { unisMplsLsr 2 }
unismplsLsrNotifyPrefix OBJECT IDENTIFIER ::= { unismplsLsrNotifications 0 }
-- conformance
unismplsLsrConformance   OBJECT IDENTIFIER ::= { unisMplsLsr 3 }


-- MPLS Interface Configuration Table.

unismplsInterfaceConfTable  OBJECT-TYPE
   SYNTAX        SEQUENCE OF UnisMplsInterfaceConfEntry
   MAX-ACCESS    not-accessible
   STATUS        current
   DESCRIPTION
       "This table specifies per-interface MPLS capability
        and associated information."
   ::= { unismplsLsrObjects 1 }

unismplsInterfaceConfEntry OBJECT-TYPE
   SYNTAX        UnisMplsInterfaceConfEntry
   MAX-ACCESS    not-accessible
   STATUS        current
   DESCRIPTION
       "An entry in this table is created by an LSR for
        every interface capable of supporting MPLS. The
        entry with index 0 represents the per-platform label
        space and contains parameters that apply to all
        interfaces that participate in the per-platform
        label space. Other entries defined in this table
        represent additional MPLS interfaces that may
        participate in either the per-platform or per-
        interface label spaces, or both. Additional
        information about label space participation of an
        interface is provided in the description clause of
        unismplsInterfaceLabelParticipationType."
   INDEX       { unismplsInterfaceConfIndex }
      ::= { unismplsInterfaceConfTable 1 }

UnisMplsInterfaceConfEntry ::= SEQUENCE {
  unismplsInterfaceConfIndex              InterfaceIndexOrZero,
  unismplsInterfaceLabelMinIn             UnisMplsLabel,
  unismplsInterfaceLabelMaxIn             UnisMplsLabel,
  unismplsInterfaceLabelMinOut            UnisMplsLabel,
  unismplsInterfaceLabelMaxOut            UnisMplsLabel,
  unismplsInterfaceTotalBandwidth         UnisMplsBitRate,
  unismplsInterfaceAvailableBandwidth     UnisMplsBitRate,
  unismplsInterfaceLabelParticipationType BITS,
  unismplsInterfaceConfStorageType        StorageType
}

unismplsInterfaceConfIndex OBJECT-TYPE
   SYNTAX        InterfaceIndexOrZero
   MAX-ACCESS    not-accessible
   STATUS        current
   DESCRIPTION
       "This is a unique index for an entry in the
        unismplsInterfaceConfTable.  A non-zero index for an
        entry indicates the ifIndex for the corresponding
        interface entry in of the MPLS-layer in the ifTable.
        Note that the per-platform label space may apply to
        several interfaces, and therefore the configuration
        of the per-platform label space interface parameters
        will apply to all of the interfaces that are
        participating in the per-platform label space."
   REFERENCE
       "RFC 2233 - The Interfaces Group MIB using SMIv2,
        McCloghrie, K., and F. Kastenholtz, Nov. 1997"
   ::= { unismplsInterfaceConfEntry 1 }

unismplsInterfaceLabelMinIn OBJECT-TYPE
   SYNTAX        UnisMplsLabel
   MAX-ACCESS    read-only
   STATUS        current
   DESCRIPTION
       "This is the minimum value of an MPLS label that this
        LSR is willing to receive on this interface."
   ::= { unismplsInterfaceConfEntry 2 }

unismplsInterfaceLabelMaxIn OBJECT-TYPE
   SYNTAX        UnisMplsLabel
   MAX-ACCESS    read-only
   STATUS        current
   DESCRIPTION
       "This is the maximum value of an MPLS label that this
        LSR is willing to receive on this interface."
   ::= { unismplsInterfaceConfEntry 3 }

unismplsInterfaceLabelMinOut OBJECT-TYPE
   SYNTAX        UnisMplsLabel
   MAX-ACCESS    read-only
   STATUS        current
   DESCRIPTION
       "This is the minimum value of an MPLS label that this
        LSR is willing to send on this interface."
   ::= { unismplsInterfaceConfEntry 4 }

unismplsInterfaceLabelMaxOut OBJECT-TYPE
   SYNTAX        UnisMplsLabel
   MAX-ACCESS    read-only
   STATUS        current
   DESCRIPTION
       "This is the maximum value of an MPLS label that this
        LSR is willing to send on this interface."
   ::= { unismplsInterfaceConfEntry 5 }

unismplsInterfaceTotalBandwidth        OBJECT-TYPE
   SYNTAX        UnisMplsBitRate
   MAX-ACCESS    read-only
   STATUS        current
   DESCRIPTION
       "This value indicates the total amount of usable
        bandwidth on this interface and is specified in
        kilobits per second (Kbps).  This variable is
        not applicable when applied to the interface with
        index 0."
::= { unismplsInterfaceConfEntry 6 }

unismplsInterfaceAvailableBandwidth       OBJECT-TYPE
   SYNTAX        UnisMplsBitRate
   MAX-ACCESS    read-only
   STATUS        current
   DESCRIPTION
       "This value indicates the total amount of available
        bandwidth available on this interface and is
        specified in kilobits per second (Kbps).  This
        value is calculated as the difference between the
        amount of bandwidth currently in use and that
        specified in unismplsInterfaceTotalBandwidth.  This
        variable is not applicable when applied to the
        interface with index 0."
::= { unismplsInterfaceConfEntry 7 }

unismplsInterfaceLabelParticipationType OBJECT-TYPE
   SYNTAX  BITS {
                perPlatform (0),
                perInterface (1)
              }
   MAX-ACCESS    read-only
   STATUS        current
   DESCRIPTION
       "Either the perPlatform(0) or perInterface(1) bit
        MUST be set. If the value of the
        unismplsInterfaceConfIndex for this entry is zero, then
        only the perPlatform(0) bit MUST be set and the
        perInterface(1) bit is meaningless. If the
        perInterface(1) bit is set then the value of
        unismplsInterfaceLabelMinIn, unismplsInterfaceLabelMaxIn,
        unismplsInterfaceLabelMinOut, and
        unismplsInterfaceLabelMaxOut for this entry reflect the
        label ranges for this interface.  If only the
        perPlatform(0) bit is set, then the value of
        unismplsInterfaceLabelMinIn, unismplsInterfaceLabelMaxIn,
        unismplsInterfaceLabelMinOut, and
        unismplsInterfaceLabelMaxOut for this entry must be
        identical to the instance of these objects with
        index 0."
   REFERENCE
      "Multiprotocol Label Switching, Rosen et al, draft-ietf-mpls-
       arch-06.txt, August 1999."
::= { unismplsInterfaceConfEntry 8 }

unismplsInterfaceConfStorageType  OBJECT-TYPE
   SYNTAX      StorageType
   MAX-ACCESS  read-create
   STATUS      current
   DESCRIPTION
       "The storage type for this entry."
   ::= { unismplsInterfaceConfEntry 9 }

-- End of unismplsInterfaceConfTable


-- MPLS Interface Performance Table.
unismplsInterfacePerfTable  OBJECT-TYPE
   SYNTAX        SEQUENCE OF UnisMplsInterfacePerfEntry
   MAX-ACCESS    not-accessible
   STATUS        current
   DESCRIPTION
       "This table provides MPLS performance information on
        a per-interface basis."
   ::= { unismplsLsrObjects 2 }

unismplsInterfacePerfEntry OBJECT-TYPE
   SYNTAX        UnisMplsInterfacePerfEntry
   MAX-ACCESS    not-accessible
   STATUS        current
   DESCRIPTION
       "An entry in this table is created by the LSR for
        every interface capable of supporting MPLS.  Its is
        an extension to the unismplsInterfaceConfEntry table."
   AUGMENTS      { unismplsInterfaceConfEntry }
      ::= { unismplsInterfacePerfTable 1 }

UnisMplsInterfacePerfEntry ::= SEQUENCE {
      -- incoming direction
      unismplsInterfaceInLabelsUsed          Gauge32,
      unismplsInterfaceFailedLabelLookup     Counter32,
      
      -- outgoing direction
      unismplsInterfaceOutLabelsUsed         Gauge32,
      unismplsInterfaceOutFragments          Counter32
   }

unismplsInterfaceInLabelsUsed OBJECT-TYPE
   SYNTAX        Gauge32
   MAX-ACCESS    read-only
   STATUS        current
   DESCRIPTION
       "This object counts the number of labels
        that are in use at this point in time on this
        interface in the incoming direction. If the interface
        participates in the per-platform label space only,
        then this instance of this object MUST be identical
        with the instance with index 0. If the interface
        participates in the per-interface label space, then this
        this instance of this object MUST represent the number of
        of per-interface labels that are in use at this point in
        time on this interface."
   ::= { unismplsInterfacePerfEntry 1 }

unismplsInterfaceFailedLabelLookup OBJECT-TYPE
   SYNTAX        Counter32
   MAX-ACCESS    read-only
   STATUS        current
   DESCRIPTION
       "This object counts the number of labeled packets
        that have been received on this interface and were
        discarded because there was no matching cross-connect
        entry. This object MUST count on a per-interface basis
        regardless of which label space the interface participates
        in."
   ::= { unismplsInterfacePerfEntry 2 }

unismplsInterfaceOutLabelsUsed OBJECT-TYPE
   SYNTAX        Gauge32
   MAX-ACCESS    read-only
   STATUS        current
   DESCRIPTION
       "This object counts the number of top-most labels in the
        outgoing label stacks that are in use at this point
        in time on this interface. This object
        MUST count on a per-interface basis regardless of
        which label space the interface participates in."
   ::= { unismplsInterfacePerfEntry 3 }

unismplsInterfaceOutFragments OBJECT-TYPE
   SYNTAX        Counter32
   MAX-ACCESS    read-only
   STATUS        current
   DESCRIPTION
       "This object counts the number of outgoing MPLS
        packets that required fragmentation before
        transmission on this interface. This object
        transmission on this interface. This object
        MUST count on a per-interface basis regardless of 
        which label space the interface participates in."
::= { unismplsInterfacePerfEntry 4 }

-- In-segment table.

unismplsInSegmentTable  OBJECT-TYPE
   SYNTAX        SEQUENCE OF UnisMplsInSegmentEntry
   MAX-ACCESS    not-accessible
   STATUS        current
   DESCRIPTION
       "This table contains a collection of incoming
        segments to an LSR."
   ::= { unismplsLsrObjects 3 }

unismplsInSegmentEntry  OBJECT-TYPE
   SYNTAX        UnisMplsInSegmentEntry
   MAX-ACCESS    not-accessible
   STATUS        current
   DESCRIPTION
       "An entry in this table represents one incoming
        segment.  An entry can be created by a network
        administrator or an SNMP agent, or an MPLS signaling
        protocol.  The creator of the entry is denoted by
        unismplsInSegmentOwner.  An entry in this table is
        indexed by the ifIndex of the incoming interface and
        the (top) label."
   INDEX         { unismplsInSegmentIfIndex, unismplsInSegmentLabel }
   ::= { unismplsInSegmentTable 1 }

UnisMplsInSegmentEntry ::= SEQUENCE {
  unismplsInSegmentIfIndex              InterfaceIndexOrZero,
  unismplsInSegmentLabel                UnisMplsLabel,
  unismplsInSegmentNPop                 Integer32,
  unismplsInSegmentAddrFamily           AddressFamilyNumbers,
  unismplsInSegmentXCIndex              Integer32,
  unismplsInSegmentOwner                UnisMplsObjectOwner,
  unismplsInSegmentTrafficParamPtr      RowPointer,
  unismplsInSegmentRowStatus            RowStatus,
  unismplsInSegmentStorageType          StorageType
}

unismplsInSegmentIfIndex OBJECT-TYPE
   SYNTAX        InterfaceIndexOrZero
   MAX-ACCESS    accessible-for-notify
   STATUS        current
   DESCRIPTION
       "This is a unique index for an entry in the
        unismplsInSegmentTable.  This value represents the
        interface index for the incoming MPLS interface.  A
        value of zero represents an incoming label from the
        per-platform label space.  In this case, the
        unismplsInSegmentLabel is interpreted to be an MPLS-type
        label."
   ::= { unismplsInSegmentEntry 1 }

unismplsInSegmentLabel OBJECT-TYPE
   SYNTAX        UnisMplsLabel
   MAX-ACCESS    accessible-for-notify
   STATUS        current
   DESCRIPTION
       "The incoming label for this segment."
   ::= { unismplsInSegmentEntry 2 }

unismplsInSegmentNPop OBJECT-TYPE
   SYNTAX        Integer32 (1..2147483647)
   MAX-ACCESS    read-create
   STATUS        current
   DESCRIPTION
       "The number of labels to pop from the incoming
        packet.  Normally only the top label is popped from
        the packet and used for all switching decisions for
        that packet.  Note that technologies which do not
        support label popping should set this value to its
        default value of 1."
   DEFVAL        { 1 }
   ::= { unismplsInSegmentEntry 3 }

unismplsInSegmentAddrFamily OBJECT-TYPE
   SYNTAX        AddressFamilyNumbers
   MAX-ACCESS    read-create
   STATUS        current
   DESCRIPTION
       "The IANA address family [IANAFamily] of the incoming
        packet.  A value of other(0) indicates that the
        family type is either unknown or undefined."
   DEFVAL        { other }
   ::= { unismplsInSegmentEntry 4 }

unismplsInSegmentXCIndex OBJECT-TYPE
SYNTAX        Integer32 (0..2147483647)
   MAX-ACCESS    read-only
   STATUS        current
   DESCRIPTION
       "Index into unismplsXCTable which identifies which cross-
        connect entry this segment is part of.  A value of
        zero indicates that this entry is not referred to by
        any cross-connect entry.  When a cross-connect entry
        is created which this in-segment is a part of, this
        object is automatically updated to reflect the value
        of unismplsXCIndex of that cross-connect entry."
   DEFVAL        { 0 }
   ::= { unismplsInSegmentEntry 5 }
   
unismplsInSegmentOwner OBJECT-TYPE
   SYNTAX        UnisMplsObjectOwner
   MAX-ACCESS    read-create
   STATUS        current
   DESCRIPTION
       "Denotes the entity that created and is responsible
        for managing this segment."
   DEFVAL { unknown }
   ::= { unismplsInSegmentEntry 6 }

unismplsInSegmentTrafficParamPtr OBJECT-TYPE
   SYNTAX            RowPointer
   MAX-ACCESS        read-create
   STATUS            current
   DESCRIPTION
     "This variable represents a pointer to the traffic
     parameter specification for this in-segment.  This
     value may point at an entry in the
     unismplsTrafficParamTable to indicate which
     unismplsTrafficParamEntry is to be assigned to this
     segment.  This value may optionally point at an
     externally defined traffic parameter specification
     table.  A value of zero-dot-zero indicates best-effort
     treatment.  By having the same value of this object,
     two or more segments can indicate resource sharing."
   ::= { unismplsInSegmentEntry 7 }

unismplsInSegmentRowStatus OBJECT-TYPE
   SYNTAX        RowStatus
   MAX-ACCESS    read-create
   STATUS        current
   DESCRIPTION
       "This variable is used to create, modify, and/or
        delete a row in this table."
   ::= { unismplsInSegmentEntry 8 }
   
unismplsInSegmentStorageType OBJECT-TYPE
   SYNTAX        StorageType
   MAX-ACCESS    read-create
   STATUS        current
   DESCRIPTION
       "This variable indicates the storage type for this
        object."
   ::= { unismplsInSegmentEntry 9 }

-- End of unismplsInSegmentTable

-- In-segment performance table.

unismplsInSegmentPerfTable  OBJECT-TYPE
   SYNTAX        SEQUENCE OF UnisMplsInSegmentPerfEntry
   MAX-ACCESS    not-accessible
   STATUS        current
   DESCRIPTION
       "This table contains statistical information for
        incoming MPLS segments to an LSR."
   ::= { unismplsLsrObjects 4 }

unismplsInSegmentPerfEntry  OBJECT-TYPE
   SYNTAX        UnisMplsInSegmentPerfEntry
   MAX-ACCESS    not-accessible
   STATUS        current
   DESCRIPTION
       "An entry in this table contains statistical
        information about one incoming segment which was
        configured in the unismplsInSegmentTable. The counters
        in this entry should behave in a manner similar to
        that of the interface."
   AUGMENTS      { unismplsInSegmentEntry }
   ::= { unismplsInSegmentPerfTable 1 }

UnisMplsInSegmentPerfEntry ::= SEQUENCE {
    unismplsInSegmentOctets                 Counter32,
    unismplsInSegmentPackets                Counter32,
    unismplsInSegmentErrors                 Counter32,
    unismplsInSegmentDiscards               Counter32,
    
    -- high capacity counter
    unismplsInSegmentHCOctets               Counter64,
    
    unismplsInSegmentPerfDiscontinuityTime  TimeStamp
   }
unismplsInSegmentOctets OBJECT-TYPE
   SYNTAX        Counter32
   MAX-ACCESS    read-only
   STATUS        current
   DESCRIPTION
       "This value represents the total number of octets
        received by this segment."
   ::= { unismplsInSegmentPerfEntry 1 }

unismplsInSegmentPackets OBJECT-TYPE
   SYNTAX        Counter32
   MAX-ACCESS    read-only
   STATUS        current
   DESCRIPTION
       "Total number of packets received by this segment."
   ::= { unismplsInSegmentPerfEntry 2 }

unismplsInSegmentErrors OBJECT-TYPE
   SYNTAX        Counter32
   MAX-ACCESS    read-only
   STATUS        current
   DESCRIPTION
       "The number of errored packets received on this
        segment."
   ::= { unismplsInSegmentPerfEntry 3 }

unismplsInSegmentDiscards OBJECT-TYPE
   SYNTAX        Counter32
   MAX-ACCESS    read-only
   STATUS        current
   DESCRIPTION
       "The number of labeled packets received on this in-
        segment, which were chosen to be discarded even
        though no errors had been detected to prevent their
        being transmitted.  One possible reason for
        discarding such a labeled packet could be to free up
        buffer space."
   ::= { unismplsInSegmentPerfEntry 4 }

unismplsInSegmentHCOctets OBJECT-TYPE
   SYNTAX        Counter64
   MAX-ACCESS    read-only
   STATUS        current
   DESCRIPTION
       "The total number of octets received.  This is the 64
        bit version of unismplsInSegmentOctets."
   ::= { unismplsInSegmentPerfEntry 5 }
   
unismplsInSegmentPerfDiscontinuityTime OBJECT-TYPE

       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { unismplsInSegmentPerfEntry 6 }
   

-- End of unismplsInSegmentPerfTable.

-- Out-segment table.

unismplsOutSegmentIndexNext OBJECT-TYPE
   SYNTAX        Integer32 (0..2147483647)
   MAX-ACCESS    read-only
   STATUS        current
   DESCRIPTION
       "This object contains the next appropriate value to
        be used for unismplsOutSegmentIndex when creating
        entries in the unismplsOutSegmentTable.  If the number
        of unassigned entries is exhausted, this object will
        take on the value of 0.  To obtain the
        unismplsOutSegmentIndex value for a new entry, the
        manager must first issue a management protocol
        retrieval operation to obtain the current value of
        this object.  The agent should modify the value to
        reflect the next unassigned index after each
        retrieval operation.  After a manager retrieves a
        value the agent will determine through its local
        policy when this index value will be made available
        for reuse."
   ::= { unismplsLsrObjects 5 }


unismplsOutSegmentTable  OBJECT-TYPE
   SYNTAX        SEQUENCE OF UnisMplsOutSegmentEntry
   MAX-ACCESS    not-accessible
   STATUS        current
   DESCRIPTION
       "This table contains a representation of the outgoing
        segments from an LSR."
   ::= { unismplsLsrObjects 6 }

unismplsOutSegmentEntry  OBJECT-TYPE
   SYNTAX        UnisMplsOutSegmentEntry
   MAX-ACCESS    not-accessible
   STATUS        current
   DESCRIPTION
       "An entry in this table represents one outgoing
        segment.  An entry can be created by a network
        administrator or an SNMP agent, or an MPLS signaling
        protocol.  The object unismplsOutSegmentOwner indicates
        the creator of this entry."
   INDEX         { unismplsOutSegmentIndex }
   ::= { unismplsOutSegmentTable 1 }

UnisMplsOutSegmentEntry ::= SEQUENCE {
  unismplsOutSegmentIndex                Integer32,
  unismplsOutSegmentIfIndex              InterfaceIndex,
  unismplsOutSegmentPushTopLabel         TruthValue,
  unismplsOutSegmentTopLabel             UnisMplsLabel,
  unismplsOutSegmentNextHopIpAddrType    InetAddressType,
  unismplsOutSegmentNextHopIpv4Addr      InetAddressIPv4,
  unismplsOutSegmentNextHopIpv6Addr      InetAddressIPv6,
  unismplsOutSegmentXCIndex              Integer32,
  unismplsOutSegmentOwner                UnisMplsObjectOwner,
  unismplsOutSegmentTrafficParamPtr      RowPointer,
  unismplsOutSegmentRowStatus            RowStatus,
  unismplsOutSegmentStorageType          StorageType
}

unismplsOutSegmentIndex OBJECT-TYPE
   SYNTAX        Integer32(0..2147483647)
   MAX-ACCESS    accessible-for-notify
   STATUS        current
   DESCRIPTION
       "This value contains a unique index for this row.
        While a value of 0 is not valid as an index for this
        row it can be supplied as a valid value to index
        unismplsXCTable to access entries for which no out-
        segment has been configured."
   ::= { unismplsOutSegmentEntry 1 }

unismplsOutSegmentIfIndex OBJECT-TYPE
   SYNTAX        InterfaceIndex
   MAX-ACCESS    read-create
   STATUS        current
   DESCRIPTION
       "This value contains the interface index of the
        outgoing interface."
   ::= { unismplsOutSegmentEntry 2 }

unismplsOutSegmentPushTopLabel OBJECT-TYPE
   SYNTAX        TruthValue
   MAX-ACCESS    read-create
   STATUS        current
   DESCRIPTION
       "This value indicates whether or not a top label
        should be pushed onto the outgoing packet's label
        stack.  The value of this variable must be set to
        true if the outgoing interface does not support pop-
        and-go (for example an ATM interface) or if it is a
        tunnel origination.  Note that it is considered an
        error in the case that unismplsOutSegmentPushTopLabel is
        set to false, but the cross-connect entry which
        refers to this out-segment has a non-zero
        unismplsLabelStackIndex.  The LSR MUST ensure that this
        situation does not happen "
   ::= { unismplsOutSegmentEntry 3 }

unismplsOutSegmentTopLabel OBJECT-TYPE
   SYNTAX        UnisMplsLabel
   MAX-ACCESS    read-create
   STATUS        current
   DESCRIPTION
       "If unismplsOutSegmentPushTopLabel is true then this
        represents the label that should be pushed onto the
        top of the outgoing packet's label stack."
   ::= { unismplsOutSegmentEntry 4 }

unismplsOutSegmentNextHopIpAddrType OBJECT-TYPE
   SYNTAX        InetAddressType
   MAX-ACCESS    read-create
   STATUS        current
   DESCRIPTION
       "Indicates whether the next hop address is IPv4 or
        IPv6.  Note that a value of unknown (0) is valid
        only when the outgoing interface is of type point-to-
        point."
   DEFVAL        { unknown }
   ::= { unismplsOutSegmentEntry 5 }

unismplsOutSegmentNextHopIpv4Addr OBJECT-TYPE
   SYNTAX        InetAddressIPv4
   MAX-ACCESS    read-create
   STATUS        current
   DESCRIPTION
       "IPv4 Address of the next hop.  Its value is
        significant only when
        unismplsOutSegmentNextHopIpAddrType is ipV4 (1),
        otherwise it should return a value of 0."
   ::= { unismplsOutSegmentEntry 6 }

unismplsOutSegmentNextHopIpv6Addr OBJECT-TYPE
   SYNTAX        InetAddressIPv6
   MAX-ACCESS    read-create
   STATUS        current
   DESCRIPTION
       "IPv6 address of the next hop.  Its value is
        significant only when
        unismplsOutSegmentNextHopIpAddrType is ipV6 (2),
        otherwise it should return a value of 0."
   ::= { unismplsOutSegmentEntry 7 }

unismplsOutSegmentXCIndex OBJECT-TYPE
   SYNTAX        Integer32 (0..2147483647)
   MAX-ACCESS    read-only
   STATUS        current
   DESCRIPTION
       "Index into unismplsXCTable which identifies which cross-
        connect entry this segment is part of.  A value of
        zero indicates that this entry is not referred to by
        any cross-connect entry.  When a cross-connect entry
        is created which this out-segment is a part of, this
        object is automatically updated to reflect the value
        of unismplsXCIndex of that cross-connect entry."
   DEFVAL        { 0 }
   ::= { unismplsOutSegmentEntry 8 }

unismplsOutSegmentOwner OBJECT-TYPE
   SYNTAX        UnisMplsObjectOwner
   MAX-ACCESS    read-create
   STATUS        current
   DESCRIPTION
       "Denotes the entity which created and is responsible
        for managing this segment."
   DEFVAL { unknown }
   ::= { unismplsOutSegmentEntry 9 }

unismplsOutSegmentTrafficParamPtr OBJECT-TYPE
   SYNTAX        RowPointer
   MAX-ACCESS    read-create
   STATUS        current
   DESCRIPTION
     "This variable represents a pointer to the traffic
      parameter specification for this out-segment.  This
      value may point at an entry in the
      unismplsTrafficParamTable to indicate which
      unismplsTrafficParamEntry is to be assigned to this
      segment.  This value may optionally point at an
      externally defined traffic parameter specification
      table.  A value of zero-dot-zero indicates best-
      effort treatment.  By having the same value of this
      object, two or more segments can indicate resource
      sharing."
   ::= { unismplsOutSegmentEntry 10 }

unismplsOutSegmentRowStatus OBJECT-TYPE
   SYNTAX        RowStatus
   MAX-ACCESS    read-create
   STATUS        current
   DESCRIPTION
       "For creating, modifying, and deleting this row."
   ::= { unismplsOutSegmentEntry 11 }

unismplsOutSegmentStorageType OBJECT-TYPE
   SYNTAX        StorageType
   MAX-ACCESS    read-create
   STATUS        current
   DESCRIPTION
       "This variable indicates the storage type for this
        object."
   ::= { unismplsOutSegmentEntry 12 }

-- End of unismplsOutSegmentTable


-- Out-segment performance table.

unismplsOutSegmentPerfTable  OBJECT-TYPE
   SYNTAX        SEQUENCE OF UnisMplsOutSegmentPerfEntry
   MAX-ACCESS    not-accessible
   STATUS        current
   DESCRIPTION
       "This table contains statistical information about
        outgoing segments from an LSR. The counters in this
        entry should behave in a manner similar to that of
        the interface."
   ::= { unismplsLsrObjects 7 }

unismplsOutSegmentPerfEntry  OBJECT-TYPE
   SYNTAX        UnisMplsOutSegmentPerfEntry
   MAX-ACCESS    not-accessible
   STATUS        current
   DESCRIPTION
       "An entry in this table contains statistical
        information about one outgoing segment configured in
        unismplsOutSegmentTable."
   AUGMENTS      { unismplsOutSegmentEntry }
      ::= { unismplsOutSegmentPerfTable 1 }

UnisMplsOutSegmentPerfEntry ::= SEQUENCE {
      unismplsOutSegmentOctets                Counter32,
      unismplsOutSegmentPackets               Counter32,
      unismplsOutSegmentErrors                Counter32,
      unismplsOutSegmentDiscards              Counter32,
      
      -- HC counter
      unismplsOutSegmentHCOctets              Counter64,
      
      unismplsOutSegmentPerfDiscontinuityTime  TimeStamp
   }

unismplsOutSegmentOctets OBJECT-TYPE
   SYNTAX        Counter32
   MAX-ACCESS    read-only
   STATUS        current
   DESCRIPTION
       "This value contains the total number of octets sent
        on this segment."
   ::= { unismplsOutSegmentPerfEntry 1 }

unismplsOutSegmentPackets OBJECT-TYPE
   SYNTAX        Counter32
   MAX-ACCESS    read-only
   STATUS        current
   DESCRIPTION
       "This value contains the total number of packets sent
        on this segment."
   ::= { unismplsOutSegmentPerfEntry 2 }

unismplsOutSegmentErrors OBJECT-TYPE
   SYNTAX        Counter32
   MAX-ACCESS    read-only
   STATUS        current
   DESCRIPTION
       "Number of packets that could not be sent due to
        errors on this segment."
   ::= { unismplsOutSegmentPerfEntry 3 }

unismplsOutSegmentDiscards OBJECT-TYPE
   SYNTAX        Counter32
   MAX-ACCESS    read-only
   STATUS        current
   DESCRIPTION
       "The number of labeled packets received on this out-
        segment, which were chosen to be discarded even
        though no errors had been detected to prevent their
        being transmitted.  One possible reason for
        discarding such a labeled packet could be to free up
        buffer space."
   ::= { unismplsOutSegmentPerfEntry 4 }

unismplsOutSegmentHCOctets OBJECT-TYPE
   SYNTAX        Counter64
   MAX-ACCESS    read-only
   STATUS        current
   DESCRIPTION
       "Total number of octets sent.  This is the 64 bit
        version of unismplsOutSegmentOctets."
   ::= { unismplsOutSegmentPerfEntry 5 }
   
unismplsOutSegmentPerfDiscontinuityTime OBJECT-TYPE
       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { unismplsOutSegmentPerfEntry 6 }
   

-- End of unismplsOutSegmentPerfTable.

-- Cross-connect table.

unismplsXCIndexNext OBJECT-TYPE
   SYNTAX        Integer32 (0..2147483647)
   MAX-ACCESS    read-only
   STATUS        current
   DESCRIPTION
       "This object contains an appropriate value to be used
        for unismplsXCIndex when creating entries in the
        unismplsXCTable.  The value 0 indicates that no
        unassigned entries are available.  To obtain the
        value of unismplsXCIndex for a new entry in the
        unismplsXCTable, the manager issues a management
        protocol retrieval operation to obtain the current
        value of unismplsXCIndex.  After each retrieval
        operation, the agent should modify the value to
        reflect the next unassigned index.  After a manager
        retrieves a value the agent will determine through
        its local policy when this index value will be made
        available for reuse."
   ::= { unismplsLsrObjects 8 }

unismplsXCTable  OBJECT-TYPE
   SYNTAX        SEQUENCE OF UnisMplsXCEntry
   MAX-ACCESS    not-accessible
   STATUS        current
   DESCRIPTION

       "This table specifies information for switching
        between LSP segments.  It supports point-to-point,
        point-to-multipoint and multipoint-to-point
        connections.  unismplsLabelStackTable specifies the
        label stack information for a cross-connect LSR and
        is referred to from unismplsXCTable."
   ::= { unismplsLsrObjects 9 }

unismplsXCEntry  OBJECT-TYPE
   SYNTAX        UnisMplsXCEntry
   MAX-ACCESS    not-accessible
   STATUS        current
   DESCRIPTION
       "A row in this table represents one cross-connect
        entry.  The following objects index it:
       
        - cross-connect index unismplsXCIndex that uniquely
          identifies a group of cross-connect entries
        - interface index of the in-segment,
          unismplsInSegmentIfIndex
        - incoming label(s), unismplsInSegmentLabel
        - out-segment index, unismplsOutSegmentIndex
       
       Originating LSPs:
        These are represented by using the special
        combination of values unismplsInSegmentIfIndex=0 and
        unismplsInSegmentLabel=0 as indexes.  In this case the
        unismplsOutSegmentIndex MUST be non-zero.
       
       Terminating LSPs:
       These are represented by using the special value
        unismplsOutSegmentIndex=0 as index.

       Special labels:
        Entries indexed by reserved MPLS label values 0
        through 15 imply terminating LSPs and MUST have
        unismplsOutSegmentIfIndex = 0.  Note that situations
        where LSPs are terminated with incoming label equal
        to 0, should have unismplsInSegmentIfIndex = 0 as well,
        but can be distinguished from originating LSPs
        because the unismplsOutSegmentIfIndex = 0.  The
        unismplsOutSegmentIfIndex MUST only be set to 0 in
        cases of terminating LSPs.
       
        An entry can be created by a network administrator
        or by an SNMP agent as instructed by an MPLS
        signaling protocol."
   INDEX  { unismplsXCIndex, unismplsInSegmentIfIndex,
            unismplsInSegmentLabel,
            unismplsOutSegmentIndex }

      ::= { unismplsXCTable 1 }

UnisMplsXCEntry ::= SEQUENCE {
      unismplsXCIndex                 Integer32,
      unismplsXCLspId                 UnisMplsLSPID,
      unismplsXCLabelStackIndex       Integer32,
      unismplsXCIsPersistent          TruthValue,
      unismplsXCOwner                 UnisMplsObjectOwner,
      unismplsXCRowStatus             RowStatus,
      unismplsXCStorageType           StorageType,
      unismplsXCAdminStatus           INTEGER,
      unismplsXCOperStatus            INTEGER
   }

unismplsXCIndex OBJECT-TYPE
   SYNTAX        Integer32 (1..2147483647)
   MAX-ACCESS    accessible-for-notify
   STATUS        current
   DESCRIPTION
       "Primary index for the conceptual row identifying 
        a group of cross-connect segments."
   ::= { unismplsXCEntry 1 }

unismplsXCLspId OBJECT-TYPE
   SYNTAX        UnisMplsLSPID
   MAX-ACCESS    read-create
   STATUS        current
   DESCRIPTION
       "This value identifies the label switched path that
        this cross-connect entry belongs to."
   ::= { unismplsXCEntry 2 }

unismplsXCLabelStackIndex OBJECT-TYPE
   SYNTAX        Integer32 (0..2147483647)
   MAX-ACCESS    read-create
   STATUS        current
   DESCRIPTION
       "Primary index into unismplsLabelStackTable identifying a
        stack of labels to be pushed beneath the top label.
        Note that the top label identified by the out-
        segment ensures that all the components of a
        multipoint-to-point connection have the same
        outgoing label.  A value of 0 indicates that no
        labels are to be stacked beneath the top label."
   ::= { unismplsXCEntry 3 }

unismplsXCIsPersistent OBJECT-TYPE
   SYNTAX        TruthValue
   MAX-ACCESS    read-create
   STATUS        current
   DESCRIPTION
       "Denotes whether or not this cross-connect entry and
        associated in- and out-segments should be restored
        automatically after failures.  This value MUST be
        set to false in cases where this cross-connect entry
        was created by a signaling protocol."
   DEFVAL        { false }
   ::= { unismplsXCEntry 4 }
   
unismplsXCOwner OBJECT-TYPE
   SYNTAX    UnisMplsObjectOwner
   MAX-ACCESS    read-create
   STATUS        current
   DESCRIPTION
       "Denotes the entity that created and is responsible
        for managing this cross-connect."
   ::= { unismplsXCEntry 5 }

unismplsXCRowStatus OBJECT-TYPE
   SYNTAX        RowStatus
   MAX-ACCESS    read-create
   STATUS        current
   DESCRIPTION
       "For creating, modifying, and deleting this row."
   ::= { unismplsXCEntry 6 }
   
unismplsXCStorageType OBJECT-TYPE
   SYNTAX        StorageType
   MAX-ACCESS    read-create
   STATUS        current
   DESCRIPTION
       "Defines the storage type for this object."
   ::= { unismplsXCEntry 7 }

unismplsXCAdminStatus OBJECT-TYPE
   SYNTAX   INTEGER {
                up(1),     -- ready to pass packets
                down(2),
                testing(3) -- in some test mode
                }
   MAX-ACCESS    read-create
   STATUS        current
   DESCRIPTION
       "The desired operational status of this segment."
   ::= { unismplsXCEntry 8 }

unismplsXCOperStatus OBJECT-TYPE
   SYNTAX   INTEGER {
         up(1),            -- ready to pass packets
         down(2),
         testing(3),       -- in some test mode
         unknown(4),       -- status cannot be determined
                           -- for some reason.
         dormant(5),
         notPresent(6),    -- some component is missing
         lowerLayerDown(7) -- down due to the state of
                           -- lower layer interfaces
      }
   MAX-ACCESS    read-only
   STATUS        current
   DESCRIPTION
       "The actual operational status of this cross-
        connect."
   ::= { unismplsXCEntry 9 }

-- End of unismplsXCTable


-- Label stack table.
unismplsMaxLabelStackDepth  OBJECT-TYPE
   SYNTAX        Integer32 (1..2147483647)
   MAX-ACCESS    read-only
   STATUS        current
   DESCRIPTION
       "The maximum stack depth supported by this LSR."
::= { unismplsLsrObjects 10 }

unismplsLabelStackIndexNext  OBJECT-TYPE
   SYNTAX        Integer32 (0..2147483647)
   MAX-ACCESS    read-only
   STATUS        current
   DESCRIPTION
       "This object contains an appropriate value to be used
        for unismplsLabelStackIndex when creating entries in the
        unismplsLabelStackTable.  The value 0 indicates that no
        unassigned entries are available.  To obtain an
        unismplsLabelStackIndex value for a new entry, the
        manager issues a management protocol retrieval
        operation to obtain the current value of this
        object.  After each retrieval operation, the agent
        should modify the value to reflect the next
        unassigned index.  After a manager retrieves a value
        the agent will determine through its local policy
        when this index value will be made available for
        reuse."
::= { unismplsLsrObjects 11 }

unismplsLabelStackTable OBJECT-TYPE
   SYNTAX        SEQUENCE OF UnisMplsLabelStackEntry
   MAX-ACCESS    not-accessible
   STATUS        current
   DESCRIPTION
       "This table specifies the label stack to be pushed
        onto a packet, beneath the top label.  Entries into
        this table are referred to from unismplsXCTable."
   ::= { unismplsLsrObjects 12 }

unismplsLabelStackEntry OBJECT-TYPE
   SYNTAX        UnisMplsLabelStackEntry
   MAX-ACCESS    not-accessible
   STATUS        current
   DESCRIPTION
       "An entry in this table represents one label which is
        to be pushed onto an outgoing packet, beneath the
        top label.  An entry can be created by a network
        administrator or by an SNMP agent as instructed by
        an MPLS signaling protocol."
   INDEX         { unismplsLabelStackIndex, unismplsLabelStackLabelIndex }
      ::= { unismplsLabelStackTable 1 }

UnisMplsLabelStackEntry ::= SEQUENCE {
      unismplsLabelStackIndex             Integer32,
      unismplsLabelStackLabelIndex        Integer32,
      unismplsLabelStackLabel             UnisMplsLabel,
      unismplsLabelStackRowStatus         RowStatus,
      unismplsLabelStackStorageType       StorageType
   }

unismplsLabelStackIndex OBJECT-TYPE
   SYNTAX        Integer32 (1..2147483647)
   MAX-ACCESS    not-accessible
   STATUS        current
   DESCRIPTION
       "Primary index for this row identifying a stack of
        labels to be pushed on an outgoing packet, beneath
        the top label."
   ::= { unismplsLabelStackEntry 1 }

unismplsLabelStackLabelIndex OBJECT-TYPE
   SYNTAX        Integer32 (1..2147483647)
   MAX-ACCESS    not-accessible
   STATUS        current
   DESCRIPTION
       "Secondary index for this row identifying one label
        of the stack.  Note that an entry with a smaller
        unismplsLabelStackLabelIndex would refer to a label
        higher up the label stack and would be popped at a
        downstream LSR before a label represented by a
        higher unismplsLabelStackLabelIndex at a downstream
        LSR."

   ::= { unismplsLabelStackEntry 2 }

unismplsLabelStackLabel OBJECT-TYPE
   SYNTAX        UnisMplsLabel
   MAX-ACCESS    read-create
   STATUS        current
   DESCRIPTION
       "The label to pushed."
   ::= { unismplsLabelStackEntry 3 }

unismplsLabelStackRowStatus OBJECT-TYPE
   SYNTAX        RowStatus
   MAX-ACCESS    read-create
   STATUS        current
   DESCRIPTION
       "For creating, modifying, and deleting this row."
   ::= { unismplsLabelStackEntry 4 }
   
unismplsLabelStackStorageType OBJECT-TYPE
   SYNTAX        StorageType
   MAX-ACCESS    read-create
   STATUS        current
   DESCRIPTION
       "Defines the storage type for this object."
   ::= { unismplsLabelStackEntry 5 }

-- End of unismplsLabelStackTable

-- Traffic Parameter table.

unismplsTrafficParamIndexNext OBJECT-TYPE
   SYNTAX        Integer32 (0..2147483647)
   MAX-ACCESS    read-only
   STATUS        current
   DESCRIPTION
       "This object contains an appropriate value which will
        be used for unismplsTrafficParamIndex when creating
        entries in the unismplsTrafficParamTable.  The value 0
        indicates that no unassigned entries are available.
        To obtain the unismplsTrafficParamIndex value for a new
        entry, the manager issues a management protocol
        retrieval operation to obtain the current value of
        this object.  After each retrieval operation, the
        agent should modify the value to reflect the next
        unassigned index.  After a manager retrieves a value
        the agent will determine through its local policy
        when this index value will be made available for
        reuse."
   ::= { unismplsLsrObjects 13 }


unismplsTrafficParamTable OBJECT-TYPE
   SYNTAX        SEQUENCE OF UnisMplsTrafficParamEntry
   MAX-ACCESS    not-accessible
   STATUS        current
   DESCRIPTION
       "This table specifies the Traffic Parameter objects
        for in and out-segments."
   ::= { unismplsLsrObjects 14 }

unismplsTrafficParamEntry OBJECT-TYPE
   SYNTAX        UnisMplsTrafficParamEntry
   MAX-ACCESS    not-accessible
   STATUS        current
   DESCRIPTION
       "An entry in this table represents the TrafficParam
        objects for one or more in or out segments.  A
        single entry can be pointed to by multiple segments
        indicating resource sharing."
   INDEX         { unismplsTrafficParamIndex }
      ::= { unismplsTrafficParamTable 1 }

UnisMplsTrafficParamEntry ::= SEQUENCE {
      unismplsTrafficParamIndex           Integer32,
      unismplsTrafficParamMaxRate         UnisMplsBitRate,
      unismplsTrafficParamMeanRate        UnisMplsBitRate,
      unismplsTrafficParamMaxBurstSize    UnisMplsBurstSize,
      unismplsTrafficParamRowStatus       RowStatus,
      unismplsTrafficParamStorageType     StorageType
   }

unismplsTrafficParamIndex OBJECT-TYPE
   SYNTAX        Integer32 (1..2147483647)
   MAX-ACCESS    not-accessible
   STATUS        current
   DESCRIPTION
       "Uniquely identifies this row of the table.  Note
        that zero represents an invalid index."
   ::= { unismplsTrafficParamEntry 1 }

unismplsTrafficParamMaxRate OBJECT-TYPE
   SYNTAX        UnisMplsBitRate
   UNITS         "kilobits per second"
   MAX-ACCESS    read-create
   STATUS        current
   DESCRIPTION
       "Maximum rate in kilobits/second."
   ::= { unismplsTrafficParamEntry 2 }

unismplsTrafficParamMeanRate OBJECT-TYPE
   SYNTAX        UnisMplsBitRate
   UNITS         "kilobits per second"
   MAX-ACCESS    read-create
   STATUS        current
   DESCRIPTION
       "Mean rate in kilobits/second."
   ::= { unismplsTrafficParamEntry 3 }

unismplsTrafficParamMaxBurstSize OBJECT-TYPE
   SYNTAX        UnisMplsBurstSize
   UNITS         "bytes"
   MAX-ACCESS    read-create
   STATUS        current
   DESCRIPTION
       "Maximum burst size in bytes."
   ::= { unismplsTrafficParamEntry 4 }

unismplsTrafficParamRowStatus OBJECT-TYPE
   SYNTAX        RowStatus
   MAX-ACCESS    read-create
   STATUS        current
   DESCRIPTION
       "For creating, modifying, and deleting this row."
   ::= { unismplsTrafficParamEntry 5 }
   
unismplsTrafficParamStorageType OBJECT-TYPE
   SYNTAX        StorageType
   MAX-ACCESS    read-create
   STATUS        current
   DESCRIPTION
       "The storage type for this object."
   ::= { unismplsTrafficParamEntry 6 }

-- End of unismplsTrafficParamTable

-- Notification Configuration

unismplsXCTrapEnable OBJECT-TYPE
   SYNTAX        TruthValue
   MAX-ACCESS    read-write
   STATUS        current
   DESCRIPTION
       "If this object is true, then it enables the
        generation of unismplsXCUp and unismplsXCDown traps,
        otherwise these traps are not emitted."
   DEFVAL { false }
   ::= { unismplsLsrObjects 15 }

-- Cross-connect.

unismplsXCUp NOTIFICATION-TYPE
   OBJECTS     { unismplsXCIndex,
                  unismplsInSegmentIfIndex,
                  unismplsInSegmentLabel,
                  unismplsOutSegmentIndex,
                  unismplsXCAdminStatus,
                  unismplsXCOperStatus }
   STATUS      current
   DESCRIPTION
       "This notification is generated when a
        unismplsXCOperStatus object for one of the configured
        cross-connect entries is about to leave the down
        state and transition into some other state (but not
        into the notPresent state).  This other state is
        indicated by the included value of
        unismplsXCOperStatus."
   ::= { unismplsLsrNotifyPrefix 1 }

unismplsXCDown NOTIFICATION-TYPE
   OBJECTS     { unismplsXCIndex,
                 unismplsInSegmentIfIndex,
                 unismplsInSegmentLabel,
                 unismplsOutSegmentIndex,
                 unismplsXCAdminStatus,
                 unismplsXCOperStatus }
   STATUS      current
   DESCRIPTION
       "This notification is generated when a
        unismplsXCOperStatus object for one of the configured
        cross-connect entries is about to enter the down
        state from some other state (but not from the
        notPresent state).  This other state is indicated by
        the included value of unismplsXCOperStatus."
   ::= { unismplsLsrNotifyPrefix 2 }

-- End of notifications.


-- Module compliance.

unismplsLsrGroups
   OBJECT IDENTIFIER ::= { unismplsLsrConformance 1 }

unismplsLsrCompliances
   OBJECT IDENTIFIER ::= { unismplsLsrConformance 2 }

unismplsLsrModuleCompliance MODULE-COMPLIANCE
   STATUS current
   DESCRIPTION
       "Compliance statement for agents that support the
        MPLS LSR MIB."
   MODULE -- this module

      -- The mandatory groups have to be implemented
      -- by all LSRs.  However, they may all be supported
      -- as read-only objects in the case where manual
      -- configuration is unsupported.

      MANDATORY-GROUPS    { unismplsInSegmentGroup,
                            unismplsOutSegmentGroup,
                            unismplsXCGroup,
                            unismplsInterfaceGroup,
                            unismplsPerfGroup,
                            unismplsSegmentDiscontinuityGroup }

      GROUP unismplsHCInSegmentPerfGroup
      DESCRIPTION
          "This group is mandatory for those in-segment
           entries for which the object
           unismplsInSegmentOutOctets wraps around too
           quickly."

      GROUP unismplsHCOutSegmentPerfGroup
      DESCRIPTION
          "This group is mandatory for those out-segment
           entries for which the object
           unismplsOutSegmentOctets wraps around too quickly."
          
      GROUP unismplsTrafficParamGroup
      DESCRIPTION
          "This group is mandatory for those LSRs that
           support QoS resource reservation."

      -- Depending on whether the device implements
      -- persistent cross-connects or not one of the
      -- following two groups is mandatory.

      GROUP unismplsXCIsPersistentGroup
      DESCRIPTION
          "This group is mandatory for devices which
           support persistent cross-connects.  The
           following constraints apply: unismplsXCIsPersistent
           must at least be read-only returning true(2)."

      GROUP unismplsXCIsNotPersistentGroup
      DESCRIPTION
          "This group is mandatory for devices which
           support non-persistent cross-connects.  The
           following constraints apply: unismplsXCIsPersistent
           must at least be read-only returning false(1)."

      -- unismplsInterfaceConfTable

      OBJECT      unismplsInterfaceConfStorageType
      SYNTAX      INTEGER { other(1) }
      MIN-ACCESS  read-only
      DESCRIPTION
          "Only other(1) needs to be supported."
      
      -- unismplsInSegmentTable
          
      OBJECT     unismplsInSegmentXCIndex
      DESCRIPTION
          "Write access is not required."

      OBJECT      unismplsInSegmentNPop
      MIN-ACCESS  read-only
      DESCRIPTION
          "Write access if not required.  This object
           should be set to 1 if it is read-only."

      OBJECT      unismplsInSegmentAddrFamily
      DESCRIPTION
          "Write access is not required.  A <value of
           other(0) should be supported because there may
           be cases where the agent may not know about or
           support any address types."

      OBJECT      unismplsInSegmentStorageType
      SYNTAX      INTEGER { other(1) }
      MIN-ACCESS  read-only

      DESCRIPTION
          "Only other(1) needs to be supported."

      -- unismplsOutSegmentTable

      OBJECT      unismplsOutSegmentIfIndex
      MIN-ACCESS  read-only
      DESCRIPTION
          "Write access is not required."
      
      OBJECT      unismplsOutSegmentPushTopLabel
      MIN-ACCESS  read-only
      DESCRIPTION
          "Write access is not required."

      OBJECT      unismplsOutSegmentTopLabel
      MIN-ACCESS  read-only
      DESCRIPTION
          "Write access is not required."

      OBJECT      unismplsOutSegmentNextHopIpAddrType
      MIN-ACCESS  read-only
      DESCRIPTION
          "ipV6(3) need not be supported."

      OBJECT      unismplsOutSegmentNextHopIpv4Addr
      MIN-ACCESS  read-only
      DESCRIPTION
          "Write access is not required."

      OBJECT      unismplsOutSegmentNextHopIpv6Addr
      MIN-ACCESS  read-only
      DESCRIPTION
          "Write access is not required."

      OBJECT      unismplsOutSegmentRowStatus
      SYNTAX      INTEGER { active(1), notInService(2),
                            createAndGo(4), destroy(6) }
      MIN-ACCESS  read-only
      DESCRIPTION
          "The notReady(3) and createAndWait(5) states need
           not be supported."
      OBJECT      unismplsOutSegmentStorageType
      SYNTAX      INTEGER { other(1) }
      MIN-ACCESS  read-only
      DESCRIPTION
          "Only other(1) needs to be supported."

      -- unismplsXCTable

      OBJECT      unismplsXCLabelStackIndex
      MIN-ACCESS  read-only
      DESCRIPTION
          "Write access is not required."

      OBJECT      unismplsXCIsPersistent
      MIN-ACCESS  read-only
      DESCRIPTION
          "Write access is not required."

      OBJECT      unismplsXCAdminStatus
      SYNTAX      INTEGER { up(1), down(2) }
      MIN-ACCESS  read-only
      DESCRIPTION
          "A value of testing(3) need not be supported."

      OBJECT      unismplsXCOperStatus
      SYNTAX      INTEGER { up(1), down(2) }
      DESCRIPTION
          "Only up(1) and down(2) need to be supported."
      
      OBJECT      unismplsXCRowStatus
      SYNTAX      INTEGER { active(1),
                             notInService(2),
                             createAndGo(4),
                             destroy(6) }
      MIN-ACCESS  read-only
      DESCRIPTION
          "The notReady(3) and createAndWait(5) states need
           not be supported."
      
      OBJECT      unismplsXCStorageType
      SYNTAX      INTEGER { other(1) }
      MIN-ACCESS  read-only
      DESCRIPTION
          "Only other(1) needs to be supported."

   ::= { unismplsLsrCompliances 1 }

-- Units of conformance.

unismplsInterfaceGroup OBJECT-GROUP
   OBJECTS { unismplsInterfaceLabelMinIn,
             unismplsInterfaceLabelMaxIn,
             unismplsInterfaceLabelMinOut,
             unismplsInterfaceLabelMaxOut,
             unismplsInterfaceTotalBandwidth,
             unismplsInterfaceAvailableBandwidth,
             unismplsInterfaceLabelParticipationType,
             unismplsInterfaceConfStorageType
          }
             
   STATUS  current
   DESCRIPTION
          "Collection of objects needed for MPLS interface
           configuration and performance information."
   ::= { unismplsLsrGroups 1 }

unismplsInSegmentGroup  OBJECT-GROUP
             OBJECTS { unismplsInSegmentNPop,
             unismplsInSegmentAddrFamily,
             unismplsInSegmentXCIndex,
             unismplsInSegmentOctets,
             unismplsInSegmentDiscards,
             unismplsInSegmentOwner,
             unismplsInSegmentRowStatus,
             unismplsInSegmentStorageType,
             unismplsInSegmentTrafficParamPtr
          }
   STATUS  current
   DESCRIPTION
          "Collection of objects needed to implement an in-
           segment."
   ::= { unismplsLsrGroups 2 }

unismplsOutSegmentGroup  OBJECT-GROUP
   OBJECTS { unismplsOutSegmentIndexNext,
             unismplsOutSegmentIfIndex,
             unismplsOutSegmentPushTopLabel,
             unismplsOutSegmentTopLabel,
             unismplsOutSegmentNextHopIpAddrType,
             unismplsOutSegmentNextHopIpv4Addr,
             unismplsOutSegmentNextHopIpv6Addr,
             unismplsOutSegmentXCIndex,
             unismplsOutSegmentOwner,
             unismplsOutSegmentOctets,
             unismplsOutSegmentDiscards,
             unismplsOutSegmentErrors,
             unismplsOutSegmentRowStatus,
             unismplsOutSegmentStorageType,
             unismplsOutSegmentTrafficParamPtr
          }
   STATUS  current
   DESCRIPTION
          "Collection of objects needed to implement an out-
           segment."
   ::= { unismplsLsrGroups 3 }

unismplsXCGroup  OBJECT-GROUP
   OBJECTS { unismplsXCIndexNext,
             unismplsXCLabelStackIndex,
             unismplsXCOwner,
             unismplsXCAdminStatus,
             unismplsXCOperStatus,
             unismplsXCRowStatus,
             unismplsXCTrapEnable,
             unismplsXCStorageType
          }
   STATUS  current
   DESCRIPTION
          "Collection of objects needed to implement a
           cross-connect entry."
   ::= { unismplsLsrGroups 4 }

unismplsXCOptionalGroup  OBJECT-GROUP
   OBJECTS { unismplsXCLspId }
   STATUS  current
   DESCRIPTION
          "Collection of optional objects for implementing 
           a cross-connect entry."
   ::= { unismplsLsrGroups 5 }

unismplsPerfGroup OBJECT-GROUP
   OBJECTS { unismplsInSegmentOctets,
             unismplsInSegmentPackets,
             unismplsInSegmentErrors,
             unismplsInSegmentDiscards,
             unismplsOutSegmentOctets,
             unismplsOutSegmentPackets,
             unismplsOutSegmentDiscards,
             unismplsInterfaceInLabelsUsed,
             unismplsInterfaceFailedLabelLookup,
             unismplsInterfaceOutFragments,
             unismplsInterfaceOutLabelsUsed
          }
   
   STATUS  current
   DESCRIPTION
          "Collection of objects providing performance
           information
        about an LSR."
   ::= { unismplsLsrGroups 6 }

unismplsHCInSegmentPerfGroup OBJECT-GROUP
   OBJECTS { unismplsInSegmentHCOctets }
   STATUS  current
   DESCRIPTION
          "Object(s) providing performance information
           specific to out-segments for which the object
           unismplsInterfaceInOctets wraps around too quickly."
   ::= { unismplsLsrGroups 7 }

unismplsHCOutSegmentPerfGroup OBJECT-GROUP
   OBJECTS { unismplsOutSegmentHCOctets }
   STATUS  current
   DESCRIPTION
          "Object(s) providing performance information
           specific to out-segments for which the object
           unismplsInterfaceOutOctets wraps around too
           quickly."
   ::= { unismplsLsrGroups 8 }
   
unismplsTrafficParamGroup OBJECT-GROUP
   OBJECTS { unismplsTrafficParamIndexNext,
             unismplsTrafficParamMaxRate,
             unismplsTrafficParamMeanRate,
             unismplsTrafficParamMaxBurstSize,
             unismplsTrafficParamRowStatus,
             unismplsTrafficParamStorageType
          }
   STATUS  current
   DESCRIPTION
          "Object(s) required for supporting QoS resource
           reservation."
   ::= { unismplsLsrGroups 9 }

unismplsXCIsPersistentGroup OBJECT-GROUP
   OBJECTS { unismplsXCIsPersistent }
   STATUS  current
   DESCRIPTION
          "Objects needed to support persistent cross-
           connects."
   ::= { unismplsLsrGroups 10 }

unismplsXCIsNotPersistentGroup OBJECT-GROUP
   OBJECTS { unismplsXCIsPersistent }
   STATUS  current
   DESCRIPTION
          "Objects needed to support non-persistent cross-
           connects."
   ::= { unismplsLsrGroups 11 }
   
unismplsLabelStackGroup OBJECT-GROUP
   OBJECTS { unismplsLabelStackLabel,
             unismplsLabelStackRowStatus,
             unismplsLabelStackStorageType,
             unismplsMaxLabelStackDepth,
             unismplsLabelStackIndexNext }
   STATUS current
   DESCRIPTION
          "Objects needed to support label stacking."
      ::= { unismplsLsrGroups 12 }
      
unismplsSegmentDiscontinuityGroup OBJECT-GROUP
   OBJECTS { unismplsInSegmentPerfDiscontinuityTime,
             unismplsOutSegmentPerfDiscontinuityTime
          }
   
   STATUS  current
   DESCRIPTION
       " A collection of objects providing information
        specific to segment discontinuities.."
   ::= { unismplsLsrGroups 13 }
      

unismplsLsrNotificationGroup NOTIFICATION-GROUP
   NOTIFICATIONS { unismplsXCUp,
                   unismplsXCDown }
   STATUS  current
   DESCRIPTION
          "Set of notifications implemented in this module.
           None is mandatory."
   ::= { unismplsLsrGroups 14 }

-- End of MPLS-LSR-MIB
END
