-- ============================================================================
-- Copyright (c) 2020 Unisyue Technologies Co., Ltd.  All rights reserved.
--
-- Description: 802.1 QinQv2 MIB Version 1
-- Reference:
-- Version: V1.0
-- History:
-- V1.0 Initial version Created by XiaoRen Yang, 2013.3.8
-- ==================================================================
UNIS-QINQV2-MIB DEFINITIONS ::= BEGIN
IMPORTS
    unisCommon
        FROM UNIS-OID-MIB
    TruthValue
        FROM SNMPv2-TC
    MODULE-IDENTITY, OBJECT-TYPE, Integer32
        FROM SNMPv2-SMI
    ifIndex
        FROM IF-MIB;

-- ==================================================================
--
-- module identity part
--
-- ==================================================================
unisQinQv2 MODULE-IDENTITY
    LAST-UPDATED
        "201303080000Z"
    ORGANIZATION
        "Unisyue Technologies Co., Ltd."
    CONTACT-INFO
        ""
    DESCRIPTION
        "802.1 QinQv2 MIB Version 1"
    REVISION
        "201303080000Z"
    DESCRIPTION
        "The initial version of this MIB module."
    ::= { unisCommon 137 }

-- ==================================================================
--
-- =====================object definition begin======================
--
-- ==================================================================
unisQinQv2MibObject OBJECT IDENTIFIER ::= { unisQinQv2 1 }

unisQinQv2ScalarObjects OBJECT IDENTIFIER ::= { unisQinQv2MibObject 1 }

unisQinQv2ServiceTPID  OBJECT-TYPE
    SYNTAX      Integer32 (1..65535)
    MAX-ACCESS  read-write
    STATUS      current
    DESCRIPTION
        "TPID globally configured for service VLAN tags.  The global TPID value
        for service VLAN tags does not take effect on interfaces where
        unisQinQIfServiceTPID is configured.
        By default, the global TPID for service VLAN tags is 0x8100."
    ::= { unisQinQv2ScalarObjects 1 }

unisQinQv2CustomerTPID  OBJECT-TYPE
    SYNTAX      Integer32 (1..65535)
    MAX-ACCESS  read-write
    STATUS      current
    DESCRIPTION
        "TPID globally configured for customer VLAN tags.  The global TPID value
        for customer VLAN tags does not take effect on interfaces where
        unisQinQIfCustomerTPID is configured.
        By default, the global TPID for customer VLAN tags is 0x8100."
    ::= { unisQinQv2ScalarObjects 2 }

unisQinQv2IfCfgTable  OBJECT-TYPE
    SYNTAX      SEQUENCE OF UnisQinQv2IfCfgEntry
    MAX-ACCESS  not-accessible
    STATUS      current
    DESCRIPTION
        "802.1 QinQ configuration table."
    ::= { unisQinQv2MibObject 2 }

unisQinQv2IfCfgEntry OBJECT-TYPE
    SYNTAX      UnisQinQv2IfCfgEntry
    MAX-ACCESS  not-accessible
    STATUS      current
    DESCRIPTION
        "802.1 QinQ configuration entries."
    INDEX { ifIndex }
    ::= { unisQinQv2IfCfgTable 1 }

UnisQinQv2IfCfgEntry ::=
    SEQUENCE
    {
        unisQinQv2IfState           TruthValue,
        unisQinQv2IfServiceTPID     Integer32,
        unisQinQv2IfCustomerTPID    Integer32,
        unisQinQv2IfTransVlanList   OCTET STRING
    }

unisQinQv2IfState OBJECT-TYPE
    SYNTAX      TruthValue
    MAX-ACCESS  read-write
    STATUS      current
    DESCRIPTION
        "802.1 QinQ functions on the port.
         The value is false by default."
    DEFVAL { false }
    ::= { unisQinQv2IfCfgEntry 1 }

unisQinQv2IfServiceTPID    OBJECT-TYPE
    SYNTAX      Integer32 (1..65535)
    MAX-ACCESS  read-write
    STATUS      current
    DESCRIPTION
        "Service TPID value on the port."
    ::= { unisQinQv2IfCfgEntry 2 }

unisQinQv2IfCustomerTPID    OBJECT-TYPE
    SYNTAX      Integer32 (1..65535)
    MAX-ACCESS  read-write
    STATUS      current
    DESCRIPTION
        "Customer TPID value on the port."
    ::= { unisQinQv2IfCfgEntry 3 }

unisQinQv2IfTransVlanList    OBJECT-TYPE
    SYNTAX      OCTET STRING (SIZE(512))
    MAX-ACCESS  read-write
    STATUS      current
    DESCRIPTION
        "Transparent VLANs described as a bitmap.  Each octet within this value
        specifies a set of eight VLANs.  The first octet specifies VLANs 1
        through 8.  The second octet specifies VLANs 9 through 16, and so on.
        Within each octet, the most significant bit represents the highest
        numbered VLAN, and the least significant bit represents the lowest
        numbered VLAN."
    ::= { unisQinQv2IfCfgEntry 4 }

END
