-- =================================================================
-- Copyright (c) 2020 Unisyue Technologies Co., Ltd.  All rights reserved.
--
-- Description: The definition of Entity Vendortype OID
-- Reference:
-- Version: V4.82
-- History:
-- V1.0 2004.05.13  Created by lvzhenfeng, modified by gaolong.
-- V1.1 2004.05.22  Adjusted by gaolong and lvzhenfeng.
--   1. Adjust module name to unisEntityVendorTypeOID and its location is set to { unis 3 }.
--   2. Rename module name prefix from unisevtModule to unisevtModuleRt_
--   and unisevtModuleSw_ for routers and switches seperately.
--   3. Add unisevtSubModuleRouter and unisevtSubModuleSwitch under unisevtModule.
--   4. Split port type into two groups, one for routers, another for switches.
-- V1.11 2004-06-17 add unisevtHotSwapFan node by limeng for garibaldi
-- V1.12 2004-07-19 add unisevtModuleSwitchType {117-138}
-- V1.13 2004-07-29 add unisevtPortSwitchType {50-58}
-- V1.14 2004-08-12 add unisevtModuleSw_LSA1FP8U(unisevtModuleSwitchType 139)
-- V1.15 2004-08-25 change enumeration name
--                     from unisevtModuleSw_LS81SFCA(120) to unisevtModuleSw_LS81SRPG0(120),
--                     from unisevtModuleSw_LS81SFCB(121) to unisevtModuleSw_LS81SRPG1(121),
--                     from unisevtModuleSw_LS81SFCC(122) to unisevtModuleSw_LS81SRPG2(122),
--                     from unisevtModuleSw_LS81SFCD(123) to unisevtModuleSw_LS81SRPG3(123).
--                  modify comments for these enumerations as well.
-- V1.2  2004-08-26 add sub identifier of unisevtPortSwitchType from 59 to 71.
-- V1.21 2004-09-08 add sub identifier of unisevtModuleSwitchType from 140 to 148.
-- V1.3  2004-09-14 add subidentifier under unisevtModuleSwitchType from 149 to 157 by wangyahui
--                  add subidentifier under unisevtModuleSwitchType from 158 to 159 by kangyinan
--                  add subidentifier under unisevtModuleSwitchType from 72 to 93 by wangyahui
--                  add subidentifier under unisevtModuleSwitchType from 94 to 96 by kangyinan
--                  add type description for unisevtModuleSw_SP4, unisevtModuleSw_UP1, unisevtModuleSw_XP4 by kangyinan
-- V2.0  2004-10-12 updated by gaolong
--                  Change all underscore('_') characters to hyphen characters('-') because underscore character is not allowed in MIB module.
--                  Remove some adjacent hyphens
-- V2.1  2004-10-19 add subidentifier under unisevtModuleSwitchType from 160 to 162 by kangyinan
--                  add subidentifier under unisevtPortSwitchType 97 by kangyinan
-- V2.2  2004-09-18 add sub identifier for unisevtModuleRouterType from 111 to 117 by taotao
-- V2.3  2004-11-18 add sub identifier 2 under unisevtFan by liyutao
-- V2.4  2004-11-23 add subidentifier under unisevtModuleSwitchType from 163 to 166 by zhangchengmei
-- V2.5  2004-12-04 add subidentifier 118 under unisevtModuleRouterType by lizhiyong
-- V2.6  2004-12-23 add sub identifier 4 to 7 under unisevtPowerSupply by Zhangjianfeng
--                  add sub identifier 167 to 169 under unisevtModuleSwitchType by Zhangjianfeng
-- V2.7  2004-12-26 add subidentifier 170 under unisevtModuleSwitchType by wangyahui
-- v2.8  2004-12-23 add subidentifier under unisevtModuleSwitchType from 171 to 172 and
--                  add sub identifier 98 to 99 under unisevtPortSwitchType by liyue
-- V2.9  2004-12-26 add sub identifier 173 under unisevtModuleSwitchType by Zhangjianfeng
--                  add sub identifier 100 for 24G cascade port under unisevtPort by Zhangjianfeng
-- V3.0  2004-01-07 add subidentifier 174 and 175 under unisevtModuleSwitchType by wangyahui
-- V3.1  2005-01-31 add subidentifier 176 under unisevtModuleSwitchType by wangyahui
-- V3.2  2005-02-26 add subidentifier 177 under unisevtModuleSwitchType by zhangchengmei
--                  add subidentifier 101 to 137 under unisevtPortSwitchType by zhangchengmei
--                  add subidentifier 178 under unisevtModuleSwitchType by zhouqiang
--                  add subidentifier 138 under unisevtPortSwitchType by zhouqiang
--                  add subidentifier 179 to 180 under unisevtModuleSwitchType by wangyahui
--                  remove trailing spaces
-- V3.3  2005-03-22 add subidentifier 181 to 187 under unisevtModuleSwitchType by zhangchengmei
-- V3.4  2004-12-29 add subidentifier 119 to 120 under unisevtModuleRouterType by lizhiyong
-- V3.5  2005-04-12 add subidentifier 141 to 144 under unisevtModuleRouterType by yinxiaoyu
--                  add subidentifier 30 to 33 under unisevtPortRouterType by yinxiaoyu
-- V3.6  2005-04-07 add subidentifier 121 to 140 under unisevtModuleRouterType by taotao
--                  change the name of subidentifier 118 under unisevtModuleRouterType by taotao
--                  adjust file format
-- V3.7  2005-05-10 add subidentifier 188 to 216 under unisevtModuleSwitchType by zhangchengmei
-- V3.8  2005-06-12 add subidentifier 145 to 149 under unisevtModuleRouterType,
--                  add subidentifier 34 under unisevtPortRouterType by wanghanlin
-- V3.9  2005-06-22 add subidentifier 150 under unisevtModuleRouterType by yinxiaoyu
-- V4.0  2005-07-18 add subidentifier 217 to 219 under unisevtModuleSwitchType by yangliming
--                  add subidentifier 139 to 142 under unisevtPortSwitchType by wangyahui
-- V4.01 2005-07-29 add subidentifier 220 to 225 under unisevtModuleSwitchType by wangyahui
-- V4.02 2005-07-21 change the name of subidentifier 183 under unisevtModuleSwitchType,
--                  add subidentifier 226 to 227 under unisevtModuleSwitchType by zhangchengmei
--       2005-08-29 add subidentifier 143 under unisevtPortSwitchType by qianxiaoyu
--                  add subidentifier 151 to 161 under unisevtModuleRouterType by taotao
--                  add subidentifier 35 to 41 under unisevtPortRouterType by taotao
-- V4.03 2005-09-07 add unisevtCPU and unisevtGeneralCPU by taotao
--                  add subidentifier 162 to 163 under unisevtModuleRouterType by taotao
--                  adjust file format by gaolong
-- V4.04 2005-09-13 add subidentifier 228 to 253 under unisevtModuleSwitchType by zhangchengmei
--       2005-09-13 add subidentifier 257 to 268 under unisevtModuleSwitchType by zhangchengmei
-- V4.05 2005-11-04 add subidentifier 144 to 149 under unisevtPortSwitchType by zhangchengmei
--                  add subidentifier 150 under unisevtPortSwitchType by huangyuetao
--                  add subidentifier 269 to 271 under unisevtModuleSwitchType by yangxiaopeng
--                  add subidentifier 272 under unisevtModuleSwitchType by qianxiaoyu
--                  add subidentifier 164 to 165 under unisevtModuleRouterType by xuejiayong
-- V4.06 2005-11-24 add subidentifier 500 to 501 under unisevtModuleSwitchType by wangyahui
-- V4.07 2005-11-28 add subidentifier 300 to 316 under unisevtModuleSwitchType by zhangchengmei
-- V4.08 2005-12-09 add subidentifier 220 to 223 under unisevtModuleRouterType by taotao
-- V4.09 2005-12-30 add subidentifier 151 to 170 under unisevtPortSwitchType by zhangchengmei
-- V4.10 2006-01-04 add subidentifier 701 under unisevtModuleSwitchType by qianxiaoyu
-- V4.11 2006-02-12 add subidentifier 200 to 219 under unisevtModuleRouterType by liutinghai
--                  add subidentifier 702 under unisevtModuleSwitchType by chenxiaohui
--                  add subidentifier 600 under unisevtModuleRouterType by qujin
--                  add subidentifier 317 under unisevtModuleSwitchType by zhangchengmei
-- V4.12 2006-02-24 add subidentifier 703 under unisevtModuleSwitchType by chijuntao
--                  add subidentifier 224 to 228 under unisevtModuleRouterType by taotao
-- V4.13 2006-02-27 add subidentifier 171 to 174 under unisevtPortSwitchType by wangshunli
--                  add subidentifier 318 to 336 under unisevtModuleSwitchType by zhaiyingying
-- V4.14 2006-03-14 add subidentifier 175 under unisevtPortSwitchType by wangyahui
--                  add subidentifier 502 to 504 under unisevtModuleSwitchType by wangyahui
-- V4.15 2006-04-03 add subidentifier 176 under unisevtPortSwitchType by wangyahui
-- V4.16 2006-04-26 add subidentifier 229 to 233 under unisevtModuleRouterType by taotao
-- V4.17 2006-04-21 add subidentifier 337 to 340 under unisevtModuleSwitchType by zhaiyingying
-- V4.18 2006-06-05 add subidentifier 704 to 705 under unisevtModuleSwitchType by zhangxianguo
--                  add subidentifier 505 to 506 under unisevtModuleSwitchType by zhangjianfeng
--                  add subidentifier 341 to 349 under unisevtModuleSwitchType by zhaiyingying
--                  add subidentifier 177 to 178 under unisevtPortSwitchType by zhangjianfeng
--                  add subidentifier 179 to 180 under unisevtPortSwitchType by zhangxianguo
-- V4.19 2006-08-23 add subidentifier 507 to 509 under unisevtModuleSwitchType by wangyahui
--                  modify object name of subidentifier 502 and 503 under unisevtModuleSwitchType by wangyahui
--                  add subidentifier 234 to 235 under unisevtModuleRouterType by liutinghai
--                  add subidentifier 350 to 357 under unisevtModuleSwitchType by zhaiyingying
-- V4.20 2006-09-26 add subidentifier 510 to 514 under unisevtModuleSwitchType by wangyahui
--                  add subidentifier 601 to 603 under unisevtModuleRouterType by zhoujianming
--                  add subidentifier 236 to 239 under unisevtModuleRouterType by qikai
--                  add subidentifier 240 to 241 under unisevtModuleRouterType by liutinghai
--                  add subidentifier 800 to 801 under unisevtModuleSwitchType by luoguixing
-- V4.21 2006-10-26 add subidentifier 358 to 370 under unisevtModuleSwitchType by zhaiyingying
--                  add subidentifier 183 under unisevtPortSwitchType by zhaiyingying
--                  add subidentifier 515 to 526 under unisevtModuleSwitchType by wangyahui
--                  add subidentifier 181 to 182 under unisevtPortSwitchType by wangyahui
-- V4.22 2006-11-02 add subidentifier 527 to 536 under unisevtModuleSwitchType by wangyahui
--                  modify description of 511 to 513 under unisevtModuleSwitchType by wangyahui
--       2006-11-10 add subidentifier 371 to 378 under unisevtModuleSwitchType by shuxiongtao
--       2006-11-08 add subidentifier 184 to 185 under unisevtPortSwitchType by zhaiyingying
-- V4.23 2006-12-04 add subidentifier 242 to 243 under unisevtModuleRouterType by liutinghai
-- V4.24 2006-01-24 add subidentifier 244 to 245 under unisevtModuleRouterType by liutinghai
-- V4.25 2007-03-19 add subidentifier 537 under unisevtModuleSwitchType by wangyahui
-- V4.26 2007-04-12 add subidentifier 538 to 542 under unisevtModuleSwitchType by wangyahui
-- V4.27 2007-04-25 add subidentifier 706 under unisevtModuleSwitchType by zhangzongyi
--                  add subidentifier 379 to 380 under unisevtModuleSwitchType by zhaiyingying
--                  add subidentifier 246 to 250 under unisevtModuleRouterType by liutinghai
--                  add subidentifier 42 under unisevtPortRouterType by liutinghai
-- V4.28 2007-05-28 add subidentifier 707 under unisevtModuleSwitchType by ligaoxu
--                  add subidentifier 381 to 392 under unisevtModuleSwitchType by shuxiongtao
--                  modify name of subidentifier 371 and 374 under unisevtModuleSwitchType by shuxiongtao
--                  add subidentifier 251 to 253 under unisevtModuleRouterType by qikai
--                  add subidentifier 254 to 255 under unisevtModuleRouterType by liutinghai
--                  add subidentifier 186 under unisevtPortSwitchType by jinzhaoqiong
-- V4.29 2007-07-09 add subidentifier 543 to 551 under unisevtModuleSwitchType by zhangjianfeng
--                  add subidentifier 552 to 554 under unisevtModuleSwitchType by wangyahui
-- V4.30 2007-07-26 add subidentifier 400 under unisevtModuleRouterType by xuejiayong
--                  add subidentifier 708 under unisevtModuleSwitchType by xiuyihong
--                  add subidentifier 256 to 258 under unisevtModuleRouterType by qikai
--                  add subidentifier 259 to 263 under unisevtModuleRouterType by liutinghai
--                  add subidentifier 3 to 5 under unisevtOther by gaolong
-- V4.31 2007-08-27 add subidentifier 187 to 188 under unisevtPortSwitchType by ruanhan
--                  add subidentifier 802 to 804 under unisevtModuleSwitchType by luoguixing
--                  add subidentifier 393 to 397 under unisevtModuleSwitchType by shuxiongtao
-- V4.32 2007-09-25 add subidentifier 555 to 559 under unisevtModuleSwitchType by wangyahui
--                  add subidentifier 805 under unisevtModuleSwitchType by luoguixing
--                  add subidentifier 401 to 403 under unisevtModuleRouterType by tanwen
--                  add subidentifier 43 under unisevtPortRouterType by qikai
--                  add subidentifier 266 to 267 under unisevtModuleRouterType by qikai
--                  add subidentifier 398 to 399 under unisevtModuleSwitchType by hexuefei
-- V4.33 2007-10-22 add subidentifier 189 under unisevtPortSwitchType by liaoxin
--                  add subidentifier 268 under unisevtModuleRouterType by liutinghai
-- V4.34 2007-11-26 add subidentifier 269 to 273 under unisevtModuleRouterType by liutinghai
--                  add subidentifier 274 to 276 under unisevtModuleRouterType by qikai
--                  add subidentifier 404 to 406 under unisevtModuleRouterType by chaiyaqin
--                  add subidentifier 400 to 407 under unisevtModuleSwitchType by shuxiongtao
-- V4.35 2007-12-27 add subidentifier 277 to 278 under unisevtModuleRouterType by liutinghai
--                  add subidentifier 560 to 568 under unisevtModuleSwitchType by wangyahui
-- V4.36 2008-01-30 add subidentifier 408 under unisevtModuleSwitchType by hexuefei
--                  add subidentifier 569 to 572 under unisevtModuleSwitchType by wangyahui
--                  add subidentifier 279 to 280 under unisevtModuleRouterType by qikai
--                  add subidentifier 190 under unisevtPortSwitchType by liujingya
-- V4.37 2008-02-20 add subidentifier 720 to 724 under unisevtModuleSwitchType by chaiyaqin
--                  add subidentifier 573 to 574 under unisevtModuleSwitchType by zhangjianfeng
--                  modify name of subidentifier 546 and 550 under unisevtModuleSwitchType by zhangjianfeng
--                  add subidentifier 575 to 576 under unisevtModuleSwitchType by wangyahui
--                  add subidentifier 281 under unisevtModuleRouterType by liutinghai
-- V4.38 2008-03-31 add subidentifier 806 to 808 under unisevtModuleSwitchType by luoguixing
--                  add subidentifier 709 to 715 under unisevtModuleSwitchType by wangcong
--                  add subidentifier 191 to 196 under unisevtPortSwitchType by wangcong
--                  add subidentifier 44 under unisevtPortRouterType by liutinghai
--                  add subidentifier 409 to 431 under unisevtModuleSwitchType by zhaiyingying
--                  add subidentifier 432 under unisevtModuleSwitchType by shuxiongtao
-- V4.39 2008-04-29 add subidentifier 577 to 589 under unisevtModuleSwitchType by wangyahui
--                  add subidentifier 407 to 409 under unisevtModuleRouterType by tanwen
-- V4.40 2008-05-31 add subidentifier 410 to 413 under unisevtModuleRouterType by tanwen
--                  add subidentifier 282 to 284 under unisevtModuleRouterType by qikai
--                  add subidentifier 285 to 286 under unisevtModuleRouterType by liutinghai
-- V4.41 2008-07-28 add subidentifier 590 to 592 under unisevtModuleSwitchType by wangyahui
--                  add subidentifier 287 to 289 under unisevtModuleRouterType by qikai
--                  add subidentifier 290 to 291 under unisevtModuleRouterType by liutinghai
--                  add subidentifier 45 to 46 under unisevtPortRouterType by liutinghai
--                  add subidentifier 809 to 810 under unisevtModuleSwitchType by luoguixing
-- V4.42 2008-08-26 modify name of 379 and 399 under unisevtModuleSwitchType by wangwei
--                  modify description of 408 under unisevtModuleSwitchType by wangwei
--                  modify name and description of 804 under unisevtModuleSwitchType by wangwei
--                  add subidentifier 433 to 434 under unisevtModuleSwitchType by wangwei
--                  add subidentifier 593 to 595 under unisevtModuleSwitchType by wangyahui
--                  modify name and description of 256 and 288 under unisevtPortRouterType by qikai
--                  add subidentifier 292 to 293 under unisevtPortRouterType by qikai
-- V4.43 2008-10-13 add subidentifier 725 under unisevtModuleSwitchType by ruanhan
--                  add subidentifier 197 under unisevtPortSwitchType by ruanhan
--                  add subidentifier 811 under unisevtModuleSwitchType by luoguixing
--                  add subidentifier 596 to 601 under unisevtModuleSwitchType by wangyahui
-- V4.44 2008-11-04 add subidentifier 294 under unisevtPortRouterType by qikai
--                  add subidentifier 414 under unisevtModuleRouterType by tanwen
-- V4.45 2008-12-01 add subidentifier 602 to 619 under unisevtModuleSwitchType by wangyahui
--                  add subidentifier 435 to 442 under unisevtModuleSwitchType by zhaiyingying
--                  modify name of 546 under unisevtModuleSwitchType by zhangjianfeng
--                  add subidentifier 295 under unisevtPortRouterType by qikai
--                  add subidentifier 443 under unisevtModuleSwitchType by shuxiongtao
-- V4.46 2008-12-25 add subidentifier 620 to 622 under unisevtModuleSwitchType by wangyahui
--                  add subidentifier 716 to 718 under unisevtModuleSwitchType by zhangshilin
--                  add subidentifier 444 to 445 under unisevtModuleSwitchType by wangchang
-- V4.47 2009-03-02 add subidentifier 446 to 452 under unisevtModuleSwitchType by wangchang
--                  add subidentifier 719 under unisevtModuleSwitchType by zhangshilin
--                  add subidentifier 623 to 633 under unisevtModuleSwitchType by wangyahui
-- V4.48 2009-03-31 add subidentifier 415 under unisevtModuleRouterType by tanwen
--                  add subidentifier 296 under unisevtPortRouterType by qikai
--                  add subidentifier 297 to 298 under unisevtPortRouterType by qianjialin
--                  add subidentifier 453 to 464 under unisevtModuleSwitchType by huyinxing
-- V4.49 2009-07-02 add subidentifier 299 to 302 under unisevtModuleRouterType by qikai
--                  add subidentifier 303 under unisevtModuleRouterType by chenfeihu
--                  add subidentifier 304 to 307 under unisevtModuleRouterType by qianjialin
--                  add subidentifier 634 to 637 under unisevtModuleSwitchType by wangyahui
--                  add subidentifier 604 to 606 under unisevtModuleRouterType by chenjianhui
--                  add subidentifier 465 to 468 under unisevtModuleSwitchType by zhaiyingying
--                  add subidentifier 469 to 472 under unisevtModuleSwitchType by huyinxing
--                  add subidentifier 198 under unisevtPortSwitchType by huyinxing
--                  add subidentifier 199 under unisevtPortSwitchType by zhangjianfeng
-- V4.50 2009-08-28 add subidentifier 638 to 640 under unisevtModuleSwitchType by wangyahui
--                  add subidentifier 308 to 310 under unisevtModuleRouterType by qianjialin
-- V4.51 2009-11-09 add subidentifier 726 under unisevtModuleSwitchType by ruanhan
--                  add subidentifier 641 under unisevtModuleSwitchType by wangyahui
--                  add subidentifier 473 to 477 under unisevtModuleSwitchType by yudongyang
--                  add subidentifier 478 to 485 under unisevtModuleSwitchType by heweibin
-- V4.52 2009-12-31 add subidentifier 200 to 201 under unisevtPortSwitchType by zhanghaiyang
--                  add subidentifier 642 to 651 under unisevtModuleSwitchType by wangyahui
--                  add subidentifier 416 under unisevtModuleRouterType by lixiaomin
--                  add subidentifier 486 under unisevtModuleSwitchType by yudongyang
--                  add subidentifier 727 to 728 under unisevtModuleSwitchType by xiaobing
--                  add subidentifier 652 to 659 under unisevtModuleSwitchType by wangyahui
--                  add subidentifier 487 to 488 under unisevtModuleSwitchType by huyinxing
--                  add subidentifier 660 to 662 under unisevtModuleSwitchType by wangyahui
--                  add subidentifier 202 to 203 under unisevtPortSwitchType by yangdonghong
-- V4.53 2010-03-03 add subidentifier 812 under unisevtModuleSwitchType by mashuhang
--                  add subidentifier 489 to 497 under unisevtModuleSwitchType by liubuxiang
--                  add subidentifier 498 to 499 under unisevtModuleSwitchType by shikejun
--                  add subidentifier 900 under unisevtModuleSwitchType by yangqiulin
--                  add subidentifier 901 to 902 under unisevtModuleSwitchType by huyinxing
-- V4.54 2010-04-21 add subidentifier 903 to 904 under unisevtModuleSwitchType by huyinxing
--                  add subidentifier 905 to 907 under unisevtModuleSwitchType by shikejun
--                  add subidentifier 663 to 685 under unisevtModuleSwitchType by wangyahui
--                  add subidentifier 813 under unisevtModuleSwitchType by mashuhang
--                  add subidentifier 729 under unisevtModuleSwitchType by zhangshilin
--                  add subidentifier 908 to 913 under unisevtModuleSwitchType by yangbin
--                  add subidentifier 914 to 918 under unisevtModuleSwitchType by huyinxing
--                  add subidentifier 5000 to 5011 under unisevtModuleRouterType by qianjialin
--                  add subidentifier 919 to 927 under unisevtModuleSwitchType by langgaoyi
-- V4.55 2011-01-31 add subidentifier 417 under unisevtModuleRouterType by tanwen
--                  add subidentifier 311 to 314 under unisevtModuleRouterType by qianjialin
--                  add subidentifier 686 to 691 under unisevtModuleSwitchType by wangyahui
--                  add subidentifier 928 to 929 under unisevtModuleSwitchType by langgaoyi
-- V4.56 2011-04-22 add subidentifier 930 under unisevtModuleSwitchType by liuhui
--                  add subidentifier 814 to 815 under unisevtModuleSwitchType by mashuhang
--                  add subidentifier 692 to 694 under unisevtModuleSwitchType by wangyahui
--                  add subidentifier 204 under unisevtPortSwitchType by yangliming
-- V4.57 2011-06-30 add subidentifier 695, 1201 to 1211 under unisevtModuleSwitchType by wangyahui
--                  add subidentifier 205 to 207 under unisevtPortSwitchType by gaoruichang
-- V4.58 2011-08-31 add subidentifier 696 to 697 under unisevtModuleSwitchType by langgaoyi
--                  add subidentifier 208 under unisevtPortSwitchType by wangshunli
--                  add subidentifier 931 to 933 under unisevtModuleSwitchType by langgaoyi
--                  add subidentifier 934 under unisevtModuleSwitchType by zhaohonghai
-- V4.59 2012-04-20 add subidentifier 935 to 938, 942 under unisevtModuleSwitchType by wangjiangnan
--                  add subidentifier 1212 to 1218 under unisevtModuleSwitchType by wangyahui
--                  add subidentifier 939 to 941 under unisevtModuleSwitchType by herui
--                  modify name of 205 to 207 under unisevtPortSwitchType by xvman
--                  add subidentifier 350 to 360 under unisevtModuleRouterType by chenfeihu
--                  add subidentifier 943 to 945 under unisevtModuleSwitchType by langgaoyi
--                  add subidentifier 209, 211 under unisevtPortSwitchType by wangyahui
--                  add subidentifier 730 to 731 under unisevtModuleSwitchType by panxiyuan
--                  add subidentifier 210 under unisevtPortSwitchType by panxiyuan
--                  add subidentifier 315 to 349 under unisevtModuleRouterType by qianjialin
--                  add subidentifier 946 to 948 under unisevtModuleSwitchType by zhangheng
--                  add subidentifier 949 to 956 under unisevtModuleSwitchType by zhengjiang
--                  add subidentifier 957 under unisevtModuleSwitchType by zhaohonghai
--                  add subidentifier 361 to 372 under unisevtModuleRouterType by qianjialin
--                  add subidentifier 212 under unisevtPortSwitchType by wangyahui
--                  add subidentifier 732 under unisevtModuleSwitchType by houchengshuai
--                  add subidentifier 1219 to 1230 under unisevtModuleSwitchType by wangyahui
-- V4.60 2013-01-07 add subidentifier 733 under unisevtModuleSwitchType by shixuemei
--                  add subidentifier 958 to 959 under hunisevtModuleSwitchType by zhaohonghai
--                  add subidentifier 960 to 965, 996 under unisevtModuleSwitchType by zhangheng
--                  add subidentifier 966 to 988 under unisevtModuleSwitchType by yebiaoxiang
--                  add subidentifier 989 to 995 under unisevtModuleSwitchType by zhaohonghai
--                  add subidentifier 1231 to 1255 under unisevtModuleSwitchType by wangyahui
--                  add subidentifier 373 to 388 under unisevtModuleRouterType by qianjialin
--                  add subidentifier 1400 to 1410 under unisevtModuleSwitchType by qizhenglin
--                  add subidentifier 213 to 219 under unisevtPortSwitchType by yebiaoxiang
--                  add subidentifier 47 under unisevtPortRouterType by qianjialin
--                  add subidentifier 418 under unisevtModuleRouterType by tanwen
--                  modify name of 673, 1214, 1215 under unisevtModuleSwitchType by wangyahui
-- V4.61 2013-04-26 add subidentifier 1256 to 1269 under unisevtModuleSwitchType by wangyahui
--                  add subidentifier 607 to 610 under unisevtModuleRouterType by jiangwendong
--                  add subidentifier 220 to 222 under unisevtPortSwitchType by jiangyongjiang
--                  add subidentifier 389 to 392 under unisevtModuleRouterType by chenfeihu
--                  add subidentifier 393 to 398 under unisevtModuleRouterType by qianjialin
--                  modify name of 975 to 982 under unisevtModuleSwitchType by lihaijun
--                  add subidentifier 997 to 1015 under unisevtModuleSwitchType by chenke
--                  add subidentifier 1016 to 1018 under unisevtModuleSwitchType by jiangyongjiang
--                  add subidentifier 1270 to 1273 under unisevtModuleSwitchType by sunzhenxing
--                  add subidentifier 1 to 8 under unisevtModuleCommonCards by zhouxiaodong
-- V4.62 2013-10-10 add subidentifier 419 to 431 under unisevtModuleRouterType by tanwen
--                  add subidentifier 611 under unisevtModuleRouterType by jiangwendong
--                  add subidentifier 399, 800 to 804, 807 under unisevtModuleRouterType by qianjialin
--                  add subidentifier 805 to 806 under unisevtModuleRouterType by chenfeihu
--                  add subidentifier 1274 to 1279, 1293 to 1296 under unisevtModuleSwitchType by lihaijun
--                  add subidentifier 1019 to 1024 under unisevtModuleSwitchType by zhaohonghai
--                  add subidentifier 1280 to 1287, 1298 to 1306 under unisevtModuleSwitchType by sunzhenxing
--                  add subidentifier 1025, 1028, 1029, 1050 under unisevtModuleSwitchType by jiangyongjiang
--                  add subidentifier 1026 to 1027, 1030 to 1049 under unisevtModuleSwitchType by chenke
--                  add subidentifier 816 under unisevtModuleSwitchType by luoguixing
--                  add subidentifier 1288 to 1292, 1297 under unisevtModuleSwitchType by wujili
--                  modify name of 1234 to 1236 under unisevtModuleSwitchType by lihaijun
--                  add subidentifier 48 to 49 under unisevtPortRouterType by jiangwendong
--                  add subidentifier 223 to 224 under unisevtPortSwitchType by jiangyongjiang
-- V4.63 2014-01-26 add subidentifier 432 under unisevtModuleRouterType by zhaowenbin
--                  add subidentifier 808 to 809, 814 under unisevtModuleRouterType by qianjialin
--                  add subidentifier 810 to 813, 815 to 817 under unisevtModuleRouterType by chenfeihu
--                  add subidentifier 734 to 739 under unisevtModuleSwitchType by panxiyuan
--                  modify name of 1032 to 1041 under unisevtModuleSwitchType by chenke
--                  add subidentifier 1051 to 1055 under unisevtModuleSwitchType by zhaohonghai
--                  add subidentifier 1056 to 1058 under unisevtModuleSwitchType by chenke
--                  add subidentifier 1307 to 1313 under unisevtModuleSwitchType by wujili
--                  add subidentifier 1314 to 1316 under unisevtModuleSwitchType by lihaijun
--                  add subidentifier 1317 to 1319 under unisevtModuleSwitchType by sunzhenxing
--                  add subidentifier 1320 to 1326 under unisevtModuleSwitchType by jiangyongjiang
-- V4.64 2014-04-25 add subidentifier 1059 to 1069 under unisevtPortSwitchType by youhua
--                  add subidentifier 1070 to 1102 under unisevtModuleSwitchType by chenke
--                  add subidentifier 1103 to 1107 under unisevtModuleSwitchType by lihaijun
--                  add subidentifier 1108 under unisevtModuleSwitchType by zhaohonghai
--                  add subidentifier 1327 to 1328 under unisevtModuleSwitchType by sunzhenxing
--                  add subidentifier 1329 to 1331 under unisevtModuleSwitchType by lihaijun
--                  add subidentifier 1332 to 1371 under unisevtModuleSwitchType by jiangyongjiang
--                  add subidentifier 1372 to 1373 under unisevtModuleSwitchType by sunzhenxing
--                  modify name of 733 under unisevtModuleSwitchType by maoyun
--                  add subidentifier 740 to 743 unisevtModuleSwitchType by tanxiaopeng
--                  add subidentifier 433 under unisevtModuleRouterType by zhaowenbin
--                  add subidentifier 818 to 822, 824 to 825 under unisevtModuleRouterType by chenfeihu
--                  add subidentifier 823 under unisevtModuleRouterType by qianjialin
--                  add subidentifier 50 to 51 under unisevtPortRouterType by chenfeihu
--                  add subidentifier 225 to 232 under unisevtPortSwitchType by pantao
--                  modify name of 1400, remove 1401 to 1410 under unisevtModuleSwitchType by qizhenglin
-- V4.65 2014-09-18 add subidentifier 434 under unisevtModuleRouterType by zhaowenbin
--                  add subidentifier 612 to 615 under unisevtModuleRouterType by jiangwendong
--                  add subidentifier 826 to 833, 840 under unisevtModuleRouterType by qianjialin
--                  add subidentifier 834 to 839 under unisevtModuleRouterType by chenfeihu
--                  add subidentifier 52 under unisevtPortRouterType by jiangwendong
--                  add subidentifier 744 unisevtModuleSwitchType by tanxiaopeng
--                  add subidentifier 1109 to 1117 under unisevtModuleSwitchType by chenke
--                  add subidentifier 1118 to 1119, 1375 to 1376 under unisevtModuleSwitchType by lihaijun
--                  add subidentifier 1374, 1382 to 1385 under unisevtModuleSwitchType by jiangyongjiang
--                  add subidentifier 1377 to 1381, 1386 to 1389 under unisevtModuleSwitchType by sunzhenxing
--                  modify description of 1010 under unisevtModuleSwitchType by chenke
--                  modify name of 1320 to 1325, 1332 to 1371 under unisevtModuleSwitchType by jiangyongjiang
--                  add subidentifier 8 to 35 under unisevtPowerSupply, 3 to 23 under unisevtFan by jiangyongjiang
-- V4.66 2015-04-18 add subidentifier 435 under unisevtModuleRouterType by zhaowenbin
--                  add subidentifier 841 to 854 under unisevtModuleRouterType by qianjialin
--                  add subidentifier 855 to 858 under unisevtModuleRouterType by zhaohonghai
--                  add subidentifier 745 to 747 unisevtModuleSwitchType by tanxiaopeng
--                  add subidentifier 748 unisevtModuleSwitchType by wangshunli
--                  add subidentifier 1120 to 1125, 1127 to 1128, 1390 to 1397,
--                                    1647 to 1649, 1667 to 1673 under unisevtModuleSwitchType by lihaijun
--                  add subidentifier 1126 under unisevtModuleSwitchType by chenke
--                  add subidentifier 1129 to 1144 under unisevtPortSwitchType by youhua
--                  add subidentifier 1398, 1399, 1600 to 1605, 1623 to 1646,
--                                    1650 to 1652, 1660 to 1666, 1674 to 1685
--                                    under unisevtModuleSwitchType by jiangyongjiang
--                  add subidentifier 1606 to 1622 under unisevtModuleSwitchType by sunzhenxing
--                  add subidentifier 1653 to 1659 under unisevtModuleSwitchType by zhaiwanqing
--                  add subidentifier 233 to 237, 239 to 253 under unisevtPortSwitchType by pantao
--                  add subidentifier 238 under unisevtPortSwitchType by chenke
--                  modify name of 1315 and 1316 under unisevtModuleSwitchType by lihaijun
-- V4.67 2016-04-02 add subidentifier 436 to 437, 448 to 449 under unisevtModuleRouterType by zhaowenbin
--                  add subidentifier 438 to 439 and 616 to 618 under unisevtModuleRouterType by sunqingyan
--                  add subidentifier 440 under unisevtModuleRouterType by chengaishuang
--                  add subidentifier 441 to 446 under unisevtModuleRouterType by yaoshuo
--                  add subidentifier 447 under unisevtModuleRouterType by dongchanghai
--                  modify name of 856 to 858 under unisevtModuleSwitchType by zhaohonghai
--                  add subidentifier 859 to 862 under unisevtModuleRouterType by zhaohonghai
--                  add subidentifier 863 under unisevtModuleRouterType by qianjialin
--                  add subidentifier 864 to 878 under unisevtModuleRouterType by chenfeihu
--                  add subidentifier 879 to 884 under unisevtModuleRouterType by fujuan
--                  add subidentifier 749 under unisevtModuleSwitchType by wangshunli
--                  add subidentifier 750 under unisevtModuleSwitchType by yangjianlin
--                  add subidentifier 751 to 752 unisevtModuleSwitchType by mengfanhua
--                  add subidentifier 753 to 756 under unisevtModuleSwitchType by songkeke
--                  add subidentifier 1145, 1149 under unisevtPortSwitchType by youhua
--                  add subidentifier 1146 to 1148, 1150 to 1154 under unisevtPortSwitchType by chenke
--                  add subidentifier 1686 to 1694, 1710 to 1722, 1742 to 1760, 1767 to 1784, 1789 to 1793
--                                    under unisevtModuleSwitchType by jiangyongjiang
--                  add subidentifier 1695 to 1696 under unisevtModuleSwitchType by zhaiwanqing
--                  add subidentifier 1697 to 1709, 1723 to 1741, 1761 to 1766, 1785 to 1788, 1794 to 1805
--                                    under unisevtModuleSwitchType by lihaijun
--                  add subidentifier 53 to 54 under unisevtPortRouterType by chenfeihu
--                  add subidentifier 55 under unisevtPortRouterType by fujuan
--                  add subidentifier 56 under unisevtPortRouterType by qianjialin
--                  modify name of 1128 under unisevtModuleSwitchType by lihaijun
--                  modify description of 1673 under unisevtModuleSwitchType by lihaijun
--                  add subidentifier 254 to 262, 264 to 265 under unisevtPortSwitchType by guolei
--                  add subidentifier 263 under unisevtPortSwitchType by zhanghuimin
-- V4.68 2018-04-13 add subidentifier 1806 to 1829 under unisevtModuleSwitchType by jiangyongjiang
--                  add subidentifier 266 under unisevtPortSwitchType by guolei
--                  add subidentifier 1830 to 1841 under unisevtModuleSwitchType by lihaijun
--                  add subidentifier 757 to 758 under unisevtModuleSwitchType by wangshunli
--                  add subidentifier 1842 under unisevtModuleSwitchType by zhaoshihong
--                  add subidentifier 1843 to 1846 under unisevtModuleSwitchType by jiangyongjiang
--                  add subidentifier 759 under unisevtModuleSwitchType by mengfanhua
--                  add subidentifier 1847 under unisevtModuleSwitchType by jiangyongjiang
--                  add subidentifier 619 to 620 under unisevtModuleRouterType by songyanqing
--                  add subidentifier 1848 to 1849 under unisevtModuleSwitchType by lihaijun
--                  add subidentifier 885 to 886 under unisevtModuleRouterType by zhaohonghai
--                  add subidentifier 1850 to 1852 under unisevtModuleSwitchType by jiangyongjiang
--                  add subidentifier 1853 to 1857 under unisevtModuleSwitchType by lihaijun
--                  add subidentifier 1858 to 1862 under unisevtModuleSwitchType by lihaijun
--                  add subidentifier 1863 to 1893 under unisevtModuleSwitchType by jiangyongjiang
--                  add subidentifier 1155 to 1170 under unisevtModuleSwitchType by chenke
--                  add subidentifier 1894 to 1895 under unisevtModuleSwitchType by lihaijun
--                  add subidentifier 1896 under unisevtModuleSwitchType by jiangyongjiang
--                  add subidentifier 267 under unisevtPortSwitchType by guolei
--                  add subidentifier 887 to 889 under unisevtModuleRouterType by mazheng
--                  add subidentifier 1171 to 1176 under unisevtModuleSwitchType by chenke
--                  add subidentifier 1897 to 1904 under unisevtModuleSwitchType by jiangyongjiang
--                  add subidentifier 1905 unisevtModuleSwitchType by liuyanpeng
--                  add subidentifier 450 to 454 unisevtModuleRouterType by dongchanghai
--                  add subidentifier 1906 to 1907 unisevtModuleSwitchType by jiangyongjiang
--                  add subidentifier 1908 unisevtModuleSwitchType by liuyanpeng
--                  add subidentifier 1177 to 1181 under unisevtModuleSwitchType by chenke
--                  add subidentifier 760 to 762 unisevtModuleSwitchType by mengfanhua
--                  add subidentifier 890 to 894 under unisevtModuleRouterType by fujuan
--                  modify name of subidentifier 872 and 873 under unisevtModuleRouterType by fujuan
--                  add subidentifier 1909 to 1910 under unisevtModuleSwitchType by lihaijun
--                  add subidentifier 455 to 456 unisevtModuleRouterType by yaoshuo
--                  add subidentifier 1911 to 1935 under unisevtModuleSwitchType by jiangyongjiang
--                  add subidentifier 457 under unisevtModuleRouterType by lizhifeng
--                  add subidentifier 895 to 899 under unisevtModuleRouterType by zhaohonghai
--                  add subidentifier 1936 to 1938 under unisevtModuleSwitchType by zhangkun
--                  add subidentifier 1939 to 1941 under unisevtModuleSwitchType by jiangyongjiang
--                  add subidentifier 6 to 8 under unisevtOther by chenke
--                  add subidentifier 458 to 462 under unisevtModuleRouterType by wangchunlei
--                  add subidentifier 900 to 906 under unisevtModuleRouterType by fujuan
--                  add subidentifier 1182 under unisevtModuleSwitchType by youhua
--                  add subidentifier 1942 under unisevtModuleSwitchType by lihaijun
--                  add subidentifier 1943 to 1953 under unisevtModuleSwitchType by jiangyongjiang
--                  add subidentifier 463 to 468 under unisevtModuleRouterType by dongchanghai
--                  add subidentifier 1183 to 1196 under unisevtModuleSwitchType by chenke
--                  add subidentifier 907 to 921 under unisevtModuleRouterType by zhongchao
--                  add subidentifier 763 to 764 under unisevtModuleSwitchType by sunfang
--                  add subidentifier 1954 to 1957 under unisevtModuleSwitchType by lihaijun
--                  add subidentifier 1958 to 1972 under unisevtModuleSwitchType by jiangyongjiang
--                  add subidentifier 1973 to 1979 unisevtModuleSwitchType by lihaijun
--                  add subidentifier 1980 to 1981 unisevtModuleSwitchType by jiangyongjiang
--                  add subidentifier 274 to 279 under unisevtModuleSwitchType by guolei
--                  add subidentifier 469 under unisevtModuleRouterType by maxiaojie
--                  add subidentifier 470 to 473 under unisevtModuleSwitchType by fuzhanfeng
--                  add subidentifier 765 under unisevtModuleSwitchType by mengfanhua
--                  add subidentifier 1982 to 1985 unisevtModuleSwitchType by  lihaijun
--                  add subidentifier 1986 to 2003 unisevtModuleSwitchType by  jiangyongjiang
--                  add subidentifier 922 under unisevtModuleRouterType by mazheng
--                  add subidentifier 58 under unisevtPortRouterType by liuhua
--                  add subidentifier 474 to 477 under unisevtModuleSwitchType by tanyan
--                  add subidentifier 2004 to 2005 unisevtModuleSwitchType by  lihaijun
--                  add subidentifier 2006 to 2008 unisevtModuleSwitchType by  jiangyongjiang
--                  add subidentifier 2009 to 2015 unisevtModuleSwitchType by  lihaijun
--                  add subidentifier 1401 to 1450 under unisevtModuleSwitchType by chenke
--                  add subidentifier 923 under unisevtModuleRouterType by zhongchao
--                  add subidentifier 924 to 933 under unisevtModuleRouterType by fujuan
--                  add subidentifier 766 to 768 under unisevtModuleSwitchType by wangshunli
--                  add subidentifier 482 to 483 under unisevtModuleSwitchType by cuipeilei
--                  add subidentifier 35 to 37 under unisevtPowerSupply by wangchunlei
--                  add subidentifier 24 to 25 under  unisevtFan by wangchunlei
--                  add subidentifier 484 to 489 under unisevtModuleSwitchType by wangchunlei
--                  add subidentifier 938 under unisevtModuleRouterType by fujuan
--                  add subidentifier 491 to 492 under unisevtModuleSwitchType by fuzhanfeng
--                  add subidentifier 939 under unisevtModuleRouterType by zhongchao
--                  add subidentifier 769 under unisevtModuleSwitchType by yangjianlin
--                  add subidentifier 940 to 945 under unisevtModuleRouterType by fujuan
--                  add subidentifier 946 to 953 under unisevtModuleRouterType by zhaochao
--                  add subidentifier 493 under unisevtModuleSwitchType by liyujun
--                  add subidentifier 2016 to 2017 unisevtModuleSwitchType by  jiangyongjiang
--                  add subidentifier 769 to 770 under unisevtModuleSwitchType by yangjianlin
--                  add subidentifier 494 to 497 under unisevtModuleSwitchType by yangyuan
--                  add subidentifier 2018 to 2021 unisevtModuleSwitchType by  lihaijun
--                  add subidentifier 280 under unisevtPortSwitchType by yuanzhi
--                  add subidentifier 2022 to 2047 unisevtModuleSwitchType by  jiangyongjiang
--                  add subidentifier 281 to 283 under unisevtPortSw by wangshunli
--                  add subidentifier 954 to 958 under unisevtModuleRouterType by fujuan
--                  add subidentifier 959 to 960 under unisevtModuleRouterType by zhongchao
--                  add subidentifier 284 to 285 under unisevtPortSwitchType by guolei
--                  add subidentifier 771 to 775 under unisevtModuleSwitchType by wangshunli
--                  add subidentifier 961 to 962 under unisevtModuleRouterType by fujuan
--                  add subidentifier 963 to 968 under unisevtModuleRouterType by zhongchao
--                  modify name of 1822 and 1825 under unisevtModuleSwitchType by jiangyongjiang
--                  add subidentifier 499 to 508 under unisevtModuleSwitchType by tanyan
--                  add subidentifier 969 under unisevtModuleRouterType by fujuan
--                  add subidentifier 970 to 973 under unisevtModuleRouterType by zhongchao
--                  add subidentifier 2048 to 2049 unisevtModuleSwitchType by  lihaijun
--                  add subidentifier 2050 to 2055 unisevtModuleSwitchType by  jiangyongjiang
--                  add subidentifier 974 to 980 under unisevtModuleRouterType by zhaomeng
--                  add subidentifier 286 under unisevtPortSwitchType by zhaomeng
--                  add subidentifier 502 to 517 under unisevtModuleSwitchType by fuzhanfeng
--                  add subidentifier 287 under unisevtPortSwitchType by guolei
-- V4.69 2019-01-15 add subidentifier 518 to 519 under unisevtModuleSwitchType by tanyan
--                  add subidentifier 520 under unisevtModuleSwitchType by fuzhanfeng
--                  add subidentifier 287 under unisevtPortSwitchType by qinjuan
--                  add subidentifier 1451 to 1456 under unisevtModuleSwitchType by chenke
--                  add subidentifier 2056 to 2060 unisevtModuleSwitchType by  jiangyongjiang
-- V4.70 2019-01-21 add subidentifier 2061 to 2063 under unisevtModuleSwitchType by jiangyongjiang
--                  add subidentifier 1457 to 1459 under unisevtModuleSwitchType by  zhanglili
--       2019-02-12 add subidentifier 2064 to 2072 under unisevtModuleSwitchType by lihaijun
--                  add subidentifier 521 to 530 under unisevtModuleSwitchType by fuzhanfeng
--                  add subidentifier 621 to 625 under unisevtModuleRouterType by wangxinmeng
--                  add subidentifier 776 to 777 under unisevtModuleSwitchType by wangshunli
--                  modify name of 966 to 968, 970 to 971,980 under unisevtModuleSwitchType by zhaomeng
--                  add subidentifier 289 to 290 under unisevtModuleSwitchType by wangzilong
--                  add subidentifier 981 to 984 under unisevtModuleRouterType  by fujuan
--                  add subidentifier 985 to 986 under unisevtModuleRouterType wangxinmeng
--                  add subidentifier 987 to 989 under unisevtModuleRouterType  by fuzhanfeng
--                  add subidentifier 990  under unisevtModuleRouterType wangxinmeng
--                  add subidentifier 991 to 1004 under unisevtModuleRouterType  by fuzhanfeng
--                  add subidentifier 1005 under unisevtModuleRouterType  by zhaomeng
--                  add subidentifier 2076 under unisevtModuleSwitchType by maoyun
--                  add subidentifier 2077 under unisevtModuleSwitchType by jiangyongjiang
--                  add subidentifier 2078 to 2081 under unisevtModuleSwitchType by chenke
--                  add subidentifier 2082 to 2108 under unisevtModuleSwitchType by jiangyongjiang
--                  add subidentifier 2109 to 2111 under unisevtModuleSwitchType by maoyun
--                  add subidentifier 2112 under unisevtModuleSwitchType by chenke
--                  add subidentifier 291 to 292  under unisevtPortSwitchType wangzilong
--                  add subidentifier 2113 to 2116 under unisevtModuleSwitchType by lihaijun
--                  add subidentifier 2117 to 2118 under unisevtModuleSwitchType by chenke
--                  add subidentifier 2119 to 2129 under unisevtModuleSwitchType by jiangyongjian
--                  add subidentifier 2130 under unisevtModuleSwitchType by maoyun
--                  add subidentifier 1006 under unisevtModuleRouterType by fuzhanfeng
--                  add subidentifier 2131 to 2141 under unisevtModuleSwitchType by chenke
--                  add subidentifier 2142 to 2146 under unisevtModuleSwitchType by jiangyongjiang
--                  add subidentifier 2147 to 2148 under unisevtModuleSwitchType by maoyun
--                  add subidentifier 1007 to 1009 under unisevtModuleRouterType by zhaomeng
--                  add subidentifier 59 under unisevtPortRouterType  by fujuan
--                  add subidentifier 2149 to 2155 under unisevtModuleSwitchType by chenke
--                  add subidentifier 2156 to 2169 under unisevtModuleSwitchType by lihaijun
--                  add subidentifier 2170 to 2173 under unisevtModuleSwitchType by jiangyongjiang
--                  add subidentifier 2174 to 2175 under unisevtModuleSwitchType by lihaijun
-- V4.71 2019-08-21 add subidentifier 2176 to 2184 under unisevtModuleSwitchType by jiangyongjiang
--                  add subidentifier 1010 under unisevtModuleRouterType by zhaomeng
--                  add subidentifier 1011 to 1012 under unisevtModuleRouterType by fujuan
--                  add subidentifier 2185 to 2188 under unisevtModuleSwitchType by qichenlu
--                  add subidentifier 2189 to 2191 under unisevtModuleSwitchType by jiangyongjiang
--                  add subidentifier 60 to 64 under unisevtPortRouterType by zhaomeng
--                  add subidentifier 2192 to 2208 under unisevtModuleSwitchType by jiangyongjiang
--                  add subidentifier 293 to 294  under unisevtPortSwitchType wangzilong
--                  modify name of 901 under unisevtModuleRouterType by ludezhen 19699
--                  add subidentifier 1013 under unisevtModuleRouterType by zhaomeng
--                  add subidentifier 1014 to 1020 under unisevtModuleRouterType by fuzhanfeng
--                  add subidentifier 1021 to 1023 under unisevtModuleRouterType by zhaomeng
--                  add subidentifier 2209 under unisevtModuleSwitchType by liuhaijun
--                  add subidentifier 295  under unisevtPortSwitchType wangzilong
--                  add subidentifier 1024 under unisevtModuleRouterType by wangxinmeng
--                  add subidentifier 1025 to 1034 under unisevtModuleRouterType by ludezhen
--                  add subidentifier 2210 to 2212 under unisevtModuleSwitchType by jiangyongjiang
-- V4.72 2019-12-02 add subidentifier 2213 to 2217 under unisevtModuleSwitchType by lihaijun
--                  add subidentifier 2218 to 2222 under unisevtModuleSwitchType by jiangyongjiang
--                  modify name of 900 under unisevtModuleRouterType by ludezhen
--                  add subidentifier 2223 to 2224 under unisevtModuleSwitchType by maoyun
--                  add subidentifier 2225 to 2226 under unisevtModuleSwitchType by jiangyongjiang
--                  modify name of 864 to 880，890 to 894，901 to 906，924 to 934，938，940 to 943，945，
--                  954 to 958，961 to 962，969，981 to 984，1011，1025 to 1034 under unisevtModuleRouterType by ludezhen
--                  add subidentifier 1035 under  unisevtModuleRouterType by ludezhen
--                  add subidentifier 1036 under  unisevtModuleRouterType by zhaomeng
--                  add subidentifier 1037 to 1040 under  unisevtModuleRouterType by wangxinmeng
--                  add subidentifier 2227 under  unisevtModuleSwitchType by chenke
-- V4.73 2020-01-07 add subidentifier 2228 to 2229 under unisevtModuleSwitchType by chenke
--                  add subidentifier 531 to 538 under unisevtModuleRouterType by fuzhanfeng
--                  modify name of 943,1012,1035 under unisevtModuleRouterType by ludezhen
--                  add subidentifier 2230 under unisevtModuleSwitchType by jiangyongjiang
--                  add subidentifier 1042 to 1044 under unisevtModuleRouterType by zhaomeng
--                  add subidentifier 817 to 819 under unisevtModuleSwitchType by luoguixing
--                  add subidentifier 1042 to 1044 under unisevtModuleRouterType by ludezhen
-- V4.74 2020-02-11 modify name of 1035 under unisevtModuleRouterType by ludezhen
--                  add subidentifier 296  under unisevtPortSwitchType wangzilong
--                  add subidentifier 2231 to 2232  unisevtModuleSwitchType by chenke
--                  add subidentifier 2233 to 2236  unisevtModuleSwitchType by lihaijun
--                  add subidentifier 7  unisevtOther by ludezhen
--                  add subidentifier 2237 unisevtModuleSwitchType by zhanglili
-- V4.75 2020-03-10 add subidentifier 2238 to 2239 unisevtModuleSwitchType by zhanglili
--                  add subidentifier 539 to 546 under unisevtModuleRouterType by fuzhanfeng
--                  add subidentifier 297 under unisevtPortSwitchType wangzilong
--                  add subidentifier 2240 to 2256 unisevtModuleSwitchType by jiangyongjiang
--                  add subidentifier 2257 unisevtModuleSwitchType by zhanglili
-- V4.76 2020-04-13 add subidentifier 1048 to 1049 unisevtModuleRouterType by wangxinmeng
--                  add subidentifier 2258 unisevtModuleSwitchType by jiangyongjiang
--                  add subidentifier 1050 unisevtModuleRouterType by ludezhen
--                  add subidentifier 547 to 549 under unisevtModuleRouterType by fuzhanfeng
--                  add subidentifier 2259 unisevtModuleSwitchType by zhanglili
--                  add subidentifier 2260 unisevtModuleSwitchType by lihaijun
--                  modify name of 2233 to 2236 unisevtModuleSwitchType by lihaijun
-- V4.77 2020-05-13 add subidentifier 550 to unisevtModuleRouterType by wangxinmeng
--                  add subidentifier 1051 unisevtModuleRouterType by zhaomeng
--                  add subidentifier 1052 unisevtModuleRouterType by wangxinmeng
--                  add subidentifier 1053 to 1054 unisevtModuleRouterType by ludezhen
--                  modify name 2231 unisevtModuleRouterType by zhanglili
--                  add subidentifier 2261 unisevtModuleRouterType by zhanglili
--                  add subidentifier 2262 to 2274 unisevtModuleRouterType by jiangyongjiang
--                  add subidentifier 2275 unisevtModuleRouterType by zhanglili
-- V4.78 2020-06-12 add subidentifier 551 to 555 unisevtModuleRouterType by chenwei
--                  add subidentifier 1055 unisevtModuleRouterType by zhaomeng
--                  add subidentifier 2276 unisevtModuleRouterType by zhanglili
--                  add subidentifier 820 unisLswTypeOfSlot by luoguixing
-- V4.79 2020-07-13 add subidentifier 1056 to 1057 unisevtModuleRouterType by zhaomeng
--                  add subidentifier 65 under unisevtPortRouterType by zhaomeng
--                  add subidentifier 5012 to 5016 unisevtModuleRouterType  by songqinghong
--       2020-07-28 add subidentifier 1058 unisevtModuleRouterType by ludezhen
--                  add subidentifier 2277 to 2291 unisevtModuleRouterType by jiangyongjiang
--                  add subidentifier 66 under unisevtPortRouterType by zhaomeng
--                  add subidentifier 2292 unisevtModuleRouterType by qichenglu
--                  modify name 2186 unisevtModuleRouterType by qichenglu
--                  add subidentifier 2293 to 2295 unisevtModuleRouterType by jiangyongjiang
--                  add subidentifier 556 unisevtModuleRouterType by wangyuqiang
-- V4.80 2020-08-17 add subidentifier 778 to 780 unisevtModuleSwitchType by zhouqin
--                  add subidentifier 1059 to 1061  unisevtModuleRouterType by wangxinmeng
--                  add subidentifier 2296 to 2301 unisevtModuleRouterType by jiangyongjiang
--                  add subidentifier 2302 to 2307 unisevtModuleRouterType by zhanglili
--                  add subidentifier 1062 unisevtModuleRouterType by ludezhen
--                  add subidentifier 1063 to 1064  unisevtModuleRouterType by zhaomeng
-- V4.81 2020-09-10 modify name 2303 unisevtModuleRouterType by zhanglili
--                  add subidentifier 298 to 299 under unisevtPortSwitchType wangzilong
--                  add subidentifier 2308 to 2326 unisevtModuleRouterType by zhanglili
--                  add subidentifier 1065 to 1066 unisevtModuleRouterType by ludezhen
--                  add subidentifier 1067 unisevtModuleRouterType by zhaomeng
-- V4.82 2020-10-20 add subidentifier 2327 to 2355 unisevtModuleRouterType by jiangyongjiang
--                  add subidentifier 1068 unisevtModuleRouterType by zhaomeng
--                  add subidentifier 557 unisevtModuleRouterType by chenwei
--                  add subidentifier 67 unisevtPortRouterType by zhaomeng
-- =================================================================
UNIS-ENTITY-VENDORTYPE-OID-MIB DEFINITIONS ::= BEGIN

IMPORTS
    MODULE-IDENTITY
        FROM SNMPv2-SMI
    unisNetworking
        FROM UNIS-OID-MIB;


unisEntityVendorTypeOID MODULE-IDENTITY

        LAST-UPDATED "200903310000Z"
        ORGANIZATION
            "Unisyue Technologies Co., Ltd."
        CONTACT-INFO
            ""
        DESCRIPTION
            "The private MIB includes the definition of the object
            identifiers on products, which are used by the
            entPhysicalTable of the ENTITY-MIB to uniquely identify the
            type of each physical entry."
        ::= { unisNetworking 3 }

unisEntityVendortypeObjects   OBJECT IDENTIFIER ::= { unisEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

unisevtOther     OBJECT IDENTIFIER ::= { unisEntityVendortypeObjects 1 }

-- May be defined detailed in future.

unisevtOtherUnknownCard  OBJECT IDENTIFIER ::= { unisevtOther 1 }
unisevtCPU               OBJECT IDENTIFIER ::= { unisevtOther 2 }
unisevtDOM               OBJECT IDENTIFIER ::= { unisevtOther 3 }  -- Disk on Module
unisevtCFCard            OBJECT IDENTIFIER ::= { unisevtOther 4 }  -- Compact Flash Card
unisevtHardDisk          OBJECT IDENTIFIER ::= { unisevtOther 5 }  -- Hard Disk
unisevtSDCard            OBJECT IDENTIFIER ::= { unisevtOther 6 }  -- Secure Digital Memory Card
unisevtMEM             OBJECT IDENTIFIER ::= { unisevtOther 7 }  -- Internal Memory

-- unisevtGeneralCPU is a general vendor type of CPU.  It is used only for
-- general purpose.  It is strongly recommended that this object should not
-- be used to present the specific CPU vendor type in most cases.  More
-- accurate and clear vendor types should be defined to present specific CPU.
unisevtGeneralCPU        OBJECT IDENTIFIER ::= { unisevtCPU 1 }


unisevtUnknown   OBJECT IDENTIFIER ::= { unisEntityVendortypeObjects 2 }

unisevtChassis   OBJECT IDENTIFIER ::= { unisEntityVendortypeObjects 3 }

-- chassis OID assignments
-- May be substituted by sysObjectID.  So none is assigned at present.

--
-- backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

unisevtBackplane     OBJECT IDENTIFIER ::= { unisEntityVendortypeObjects 4 }

--
-- unisevtContainer section:
--
unisevtContainer     OBJECT IDENTIFIER ::= { unisEntityVendortypeObjects 5 }

--
-- unisevtPowerSupply section:
--
unisevtPowerSupply   OBJECT IDENTIFIER ::= { unisEntityVendortypeObjects 6 }
unisevtPowerSupplyAC            OBJECT IDENTIFIER ::= { unisevtPowerSupply 2 }
unisevtPowerSupplyDC            OBJECT IDENTIFIER ::= { unisevtPowerSupply 3 }
unisevtPowerSupplySTD130W       OBJECT IDENTIFIER ::= { unisevtPowerSupply 4 }     -- Standard 130W PSU
unisevtPowerSupplySTD180W       OBJECT IDENTIFIER ::= { unisevtPowerSupply 5 }     -- Standard 180W PSU
unisevtPowerSupplyPOE24Port     OBJECT IDENTIFIER ::= { unisevtPowerSupply 6 }     -- 24 Port POE PSU 480W
unisevtPowerSupplyPOE48Port     OBJECT IDENTIFIER ::= { unisevtPowerSupply 7 }     -- 48 Port POE PSU 480W
unisevtPowerSupplyLSUM1AC2500   OBJECT IDENTIFIER ::= { unisevtPowerSupply 8 }
unisevtPowerSupplyLSUM2AC2500   OBJECT IDENTIFIER ::= { unisevtPowerSupply 9 }
unisevtPowerSupplyLSUM1DC2400   OBJECT IDENTIFIER ::= { unisevtPowerSupply 10 }
unisevtPowerSupplyLSUM1AC1200   OBJECT IDENTIFIER ::= { unisevtPowerSupply 11 }
unisevtPowerSupplyLSQM1DC2400   OBJECT IDENTIFIER ::= { unisevtPowerSupply 12 }
unisevtPowerSupplyLSUM5AC2500   OBJECT IDENTIFIER ::= { unisevtPowerSupply 13 }
unisevtPowerSupplyLSUM5DC2400   OBJECT IDENTIFIER ::= { unisevtPowerSupply 14 }
unisevtPowerSupplyLSUM6DC2400   OBJECT IDENTIFIER ::= { unisevtPowerSupply 15 }
unisevtPowerSupplyLSUM6AC2500   OBJECT IDENTIFIER ::= { unisevtPowerSupply 16 }
unisevtPowerSupplyLSQM1AC1400   OBJECT IDENTIFIER ::= { unisevtPowerSupply 17 }
unisevtPowerSupplyLSQM1DC1400   OBJECT IDENTIFIER ::= { unisevtPowerSupply 18 }
unisevtPowerSupplyLSQM1AC2800   OBJECT IDENTIFIER ::= { unisevtPowerSupply 19 }
unisevtPowerSupplyLSQM2AC1400   OBJECT IDENTIFIER ::= { unisevtPowerSupply 20 }
unisevtPowerSupplyLSQM1AC6000   OBJECT IDENTIFIER ::= { unisevtPowerSupply 21 }
unisevtPowerSupplyLSQM2AC6000   OBJECT IDENTIFIER ::= { unisevtPowerSupply 22 }
unisevtPowerSupplyLSQM1AC300    OBJECT IDENTIFIER ::= { unisevtPowerSupply 23 }
unisevtPowerSupplyLSQM1AC650    OBJECT IDENTIFIER ::= { unisevtPowerSupply 24 }
unisevtPowerSupplyLSQM1DC650    OBJECT IDENTIFIER ::= { unisevtPowerSupply 25 }
unisevtPowerSupplyLSQM1PWRSPA   OBJECT IDENTIFIER ::= { unisevtPowerSupply 26 }
unisevtPowerSupplyLSWM1RPS800   OBJECT IDENTIFIER ::= { unisevtPowerSupply 27 }
unisevtPowerSupplyLSQM7AC1400   OBJECT IDENTIFIER ::= { unisevtPowerSupply 28 }
unisevtPowerSupplyLSQM7DC1400   OBJECT IDENTIFIER ::= { unisevtPowerSupply 29 }
unisevtPowerSupplyLSQM7AC2800   OBJECT IDENTIFIER ::= { unisevtPowerSupply 30 }
unisevtPowerSupplyLSQM7AC6000   OBJECT IDENTIFIER ::= { unisevtPowerSupply 31 }
unisevtPowerSupplyLSQM7AC300    OBJECT IDENTIFIER ::= { unisevtPowerSupply 32 }
unisevtPowerSupplyLSQM7AC650    OBJECT IDENTIFIER ::= { unisevtPowerSupply 33 }
unisevtPowerSupplyLSQM7DC650    OBJECT IDENTIFIER ::= { unisevtPowerSupply 34 }
unisevtPowerSupplyLSWM2RPS800   OBJECT IDENTIFIER ::= { unisevtPowerSupply 35 }
unisevtPowerSupplySecPathAC     OBJECT IDENTIFIER ::= { unisevtPowerSupply 36 }    -- F5000-NSUM1AC650-650W
unisevtPowerSupplySecPathDC     OBJECT IDENTIFIER ::= { unisevtPowerSupply 37}     -- F5000-NSUM1DC650-650W
--
-- unisevtFan section:
--
unisevtFan       OBJECT IDENTIFIER ::= { unisEntityVendortypeObjects 7 }
unisevtHotSwapFan       OBJECT IDENTIFIER ::=  { unisevtFan 1 }
unisevtNonHotSwapFan    OBJECT IDENTIFIER ::=  { unisevtFan 2 }
unisevtFanLSUM110504    OBJECT IDENTIFIER ::=  { unisevtFan 3 }
unisevtFanLSUM110508    OBJECT IDENTIFIER ::=  { unisevtFan 4 }
unisevtFanLSUM110508V   OBJECT IDENTIFIER ::=  { unisevtFan 5 }
unisevtFanLSUM110512    OBJECT IDENTIFIER ::=  { unisevtFan 6 }
unisevtFanLSUM210512    OBJECT IDENTIFIER ::=  { unisevtFan 7 }
unisevtFanLSUM510504    OBJECT IDENTIFIER ::=  { unisevtFan 8 }
unisevtFanLSUM510508    OBJECT IDENTIFIER ::=  { unisevtFan 9 }
unisevtFanLSUM510508V   OBJECT IDENTIFIER ::=  { unisevtFan 10 }
unisevtFanLSUM510512U   OBJECT IDENTIFIER ::=  { unisevtFan 11 }
unisevtFanLSUM510512D   OBJECT IDENTIFIER ::=  { unisevtFan 12 }
unisevtFanLSUM511908V   OBJECT IDENTIFIER ::=  { unisevtFan 13 }
unisevtFanLSQM17502E    OBJECT IDENTIFIER ::=  { unisevtFan 14 }
unisevtFanLSQM17503E    OBJECT IDENTIFIER ::=  { unisevtFan 15 }
unisevtFanLSQM17503ES   OBJECT IDENTIFIER ::=  { unisevtFan 16 }
unisevtFanLSQM17506E    OBJECT IDENTIFIER ::=  { unisevtFan 17 }
unisevtFanLSQM17506EV   OBJECT IDENTIFIER ::=  { unisevtFan 18 }
unisevtFanLSQM17510E    OBJECT IDENTIFIER ::=  { unisevtFan 19 }
unisevtFanLSQM57503     OBJECT IDENTIFIER ::=  { unisevtFan 20 }
unisevtFanLSQM57502     OBJECT IDENTIFIER ::=  { unisevtFan 21 }
unisevtFanLSQM57506     OBJECT IDENTIFIER ::=  { unisevtFan 22 }
unisevtFanLSQM57510     OBJECT IDENTIFIER ::=  { unisevtFan 23 }
unisevtHotSwapFan-NSUM1BFANSC         OBJECT IDENTIFIER ::=  { unisevtFan 24 }   -- F5000-NSUM1BFANSC
unisevtHotSwapFan-NSUM1BFANSCB        OBJECT IDENTIFIER ::=  { unisevtFan 25 }   -- F5000-NSUM1BFANSCB
--
-- unisevtSensor section:
--
unisevtSensor        OBJECT IDENTIFIER ::= { unisEntityVendortypeObjects 8 }
unisevtSensorTemperature     OBJECT IDENTIFIER ::= { unisevtSensor 1 }
unisevtSensorVoltage         OBJECT IDENTIFIER ::= { unisevtSensor 2 }
unisevtSensorFanSpeed        OBJECT IDENTIFIER ::= { unisevtSensor 3 }


--
-- unisevtModule section:
--
unisevtModule        OBJECT IDENTIFIER ::= { unisEntityVendortypeObjects 9 }

-- unisevtModule is subdivided into sections like Router and Switch. These represent
-- cards used only on the router and switch.
-- unisevtModuleCommonCards contains cards that can be used interchangeably
-- across more than one platform


-- Acronyms used in the unisevtModule section:
--

unisevtModuleUnknownCard     OBJECT IDENTIFIER ::= { unisevtModule 1 }

-- unisevtModuleCommonCards - cards and subcards common to more
-- than one platform
unisevtModuleCommonCards     OBJECT IDENTIFIER ::= { unisevtModule 2 }

unisevtModuleBoxCEN                         OBJECT IDENTIFIER ::= { unisevtModuleCommonCards 1 }
unisevtModuleBoxIRF48GE                     OBJECT IDENTIFIER ::= { unisevtModuleCommonCards 2 }
unisevtModuleBoxIRF24GE24TGE                OBJECT IDENTIFIER ::= { unisevtModuleCommonCards 3 }
unisevtModuleChassisMpu                     OBJECT IDENTIFIER ::= { unisevtModuleCommonCards 4 }
unisevtModuleLPU48GE                        OBJECT IDENTIFIER ::= { unisevtModuleCommonCards 5 }
unisevtModuleLPU4GE4Serial                  OBJECT IDENTIFIER ::= { unisevtModuleCommonCards 6 }
unisevtModuleLPU4GE4Pos                     OBJECT IDENTIFIER ::= { unisevtModuleCommonCards 7 }
unisevtModuleLPU4GE4E1                      OBJECT IDENTIFIER ::= { unisevtModuleCommonCards 8 }


-- unisevtModuleRouterType cards are slot-cards specific to the Router.
unisevtModuleRouterType      OBJECT IDENTIFIER ::= { unisevtModule 3 }

--unisevtModuleRt-Unavailable               OBJECT IDENTIFIER ::= { unisevtModuleRouterType 1 }
unisevtModuleRt-As                          OBJECT IDENTIFIER ::= { unisevtModuleRouterType 2 }
unisevtModuleRt-Sa                          OBJECT IDENTIFIER ::= { unisevtModuleRouterType 3 }
unisevtModuleRt-Bi                          OBJECT IDENTIFIER ::= { unisevtModuleRouterType 4 }
unisevtModuleRt-E12                         OBJECT IDENTIFIER ::= { unisevtModuleRouterType 5 }
unisevtModuleRt-E14                         OBJECT IDENTIFIER ::= { unisevtModuleRouterType 6 }
unisevtModuleRt-Fe1                         OBJECT IDENTIFIER ::= { unisevtModuleRouterType 7 }
unisevtModuleRt-E1                          OBJECT IDENTIFIER ::= { unisevtModuleRouterType 8 }
unisevtModuleRt-Fe2                         OBJECT IDENTIFIER ::= { unisevtModuleRouterType 9 }
unisevtModuleRt-Vi2                         OBJECT IDENTIFIER ::= { unisevtModuleRouterType 11 }
unisevtModuleRt-Vi4                         OBJECT IDENTIFIER ::= { unisevtModuleRouterType 12 }
unisevtModuleRt-Vi30                        OBJECT IDENTIFIER ::= { unisevtModuleRouterType 13 }
unisevtModuleRt-S1b                         OBJECT IDENTIFIER ::= { unisevtModuleRouterType 14 }
unisevtModuleRt-Sa2                         OBJECT IDENTIFIER ::= { unisevtModuleRouterType 15 }
unisevtModuleRt-As16                        OBJECT IDENTIFIER ::= { unisevtModuleRouterType 16 }
unisevtModuleRt-New8as                      OBJECT IDENTIFIER ::= { unisevtModuleRouterType 17 }
unisevtModuleRt-Sa1                         OBJECT IDENTIFIER ::= { unisevtModuleRouterType 18 }
unisevtModuleRt-Fxs2                        OBJECT IDENTIFIER ::= { unisevtModuleRouterType 19 }
unisevtModuleRt-Fxo2                        OBJECT IDENTIFIER ::= { unisevtModuleRouterType 20 }
unisevtModuleRt-Em2                         OBJECT IDENTIFIER ::= { unisevtModuleRouterType 21 }
unisevtModuleRt-Fxs4                        OBJECT IDENTIFIER ::= { unisevtModuleRouterType 22 }
unisevtModuleRt-Fxo4                        OBJECT IDENTIFIER ::= { unisevtModuleRouterType 23 }
unisevtModuleRt-Em4                         OBJECT IDENTIFIER ::= { unisevtModuleRouterType 24 }
unisevtModuleRt-Sab                         OBJECT IDENTIFIER ::= { unisevtModuleRouterType 25 }
unisevtModuleRt-E1vi                        OBJECT IDENTIFIER ::= { unisevtModuleRouterType 26 }
unisevtModuleRt-Am12                        OBJECT IDENTIFIER ::= { unisevtModuleRouterType 27 }
unisevtModuleRt-Am6                         OBJECT IDENTIFIER ::= { unisevtModuleRouterType 28 }
unisevtModuleRt-Ndec                        OBJECT IDENTIFIER ::= { unisevtModuleRouterType 29 }
unisevtModuleRt-Newsa2                      OBJECT IDENTIFIER ::= { unisevtModuleRouterType 30 }
unisevtModuleRt-Aux                         OBJECT IDENTIFIER ::= { unisevtModuleRouterType 31 }
unisevtModuleRt-Console                     OBJECT IDENTIFIER ::= { unisevtModuleRouterType 32 }
unisevtModuleRt-Sic-wan                     OBJECT IDENTIFIER ::= { unisevtModuleRouterType 33 }
unisevtModuleRt-Sic-1fe                     OBJECT IDENTIFIER ::= { unisevtModuleRouterType 34 }
unisevtModuleRt-Sic-1sa                     OBJECT IDENTIFIER ::= { unisevtModuleRouterType 35 }
unisevtModuleRt-Sic-3as                     OBJECT IDENTIFIER ::= { unisevtModuleRouterType 36 }
unisevtModuleRt-Sic-1e1                     OBJECT IDENTIFIER ::= { unisevtModuleRouterType 37 }
unisevtModuleRt-Sic-1t1                     OBJECT IDENTIFIER ::= { unisevtModuleRouterType 38 }
unisevtModuleRt-Sic-1bu                     OBJECT IDENTIFIER ::= { unisevtModuleRouterType 39 }
unisevtModuleRt-Sic-2bu                     OBJECT IDENTIFIER ::= { unisevtModuleRouterType 40 }
unisevtModuleRt-Sic-1bs                     OBJECT IDENTIFIER ::= { unisevtModuleRouterType 41 }
unisevtModuleRt-Sic-2bs                     OBJECT IDENTIFIER ::= { unisevtModuleRouterType 42 }
unisevtModuleRt-Sic-1am                     OBJECT IDENTIFIER ::= { unisevtModuleRouterType 43 }
unisevtModuleRt-Sic-2am                     OBJECT IDENTIFIER ::= { unisevtModuleRouterType 44 }
unisevtModuleRt-Sic-1em                     OBJECT IDENTIFIER ::= { unisevtModuleRouterType 45 }
unisevtModuleRt-Sic-2em                     OBJECT IDENTIFIER ::= { unisevtModuleRouterType 46 }
unisevtModuleRt-Sic-1fxs                    OBJECT IDENTIFIER ::= { unisevtModuleRouterType 47 }
unisevtModuleRt-Sic-2fxs                    OBJECT IDENTIFIER ::= { unisevtModuleRouterType 48 }
unisevtModuleRt-Sic-1fxo                    OBJECT IDENTIFIER ::= { unisevtModuleRouterType 49 }
unisevtModuleRt-Sic-2fxo                    OBJECT IDENTIFIER ::= { unisevtModuleRouterType 50 }
unisevtModuleRt-Fcm6                        OBJECT IDENTIFIER ::= { unisevtModuleRouterType 51 }
unisevtModuleRt-Sa8                         OBJECT IDENTIFIER ::= { unisevtModuleRouterType 52 }
unisevtModuleRt-T11                         OBJECT IDENTIFIER ::= { unisevtModuleRouterType 53 }
unisevtModuleRt-T12                         OBJECT IDENTIFIER ::= { unisevtModuleRouterType 54 }
unisevtModuleRt-T14                         OBJECT IDENTIFIER ::= { unisevtModuleRouterType 55 }
unisevtModuleRt-T1vi                        OBJECT IDENTIFIER ::= { unisevtModuleRouterType 56 }
unisevtModuleRt-Fcm4                        OBJECT IDENTIFIER ::= { unisevtModuleRouterType 57 }
unisevtModuleRt-Fcm2                        OBJECT IDENTIFIER ::= { unisevtModuleRouterType 58 }
unisevtModuleRt-Rtb21ce3                    OBJECT IDENTIFIER ::= { unisevtModuleRouterType 59 }
unisevtModuleRt-Ame6                        OBJECT IDENTIFIER ::= { unisevtModuleRouterType 60 }
unisevtModuleRt-Ame12                       OBJECT IDENTIFIER ::= { unisevtModuleRouterType 61 }
unisevtModuleRt-E11-f                       OBJECT IDENTIFIER ::= { unisevtModuleRouterType 65 }
unisevtModuleRt-E12-f                       OBJECT IDENTIFIER ::= { unisevtModuleRouterType 66 }
unisevtModuleRt-E14-f                       OBJECT IDENTIFIER ::= { unisevtModuleRouterType 67 }
unisevtModuleRt-T11-f                       OBJECT IDENTIFIER ::= { unisevtModuleRouterType 68 }
unisevtModuleRt-T12-f                       OBJECT IDENTIFIER ::= { unisevtModuleRouterType 69 }
unisevtModuleRt-T14-f                       OBJECT IDENTIFIER ::= { unisevtModuleRouterType 70 }
unisevtModuleRt-E11-f-17                    OBJECT IDENTIFIER ::= { unisevtModuleRouterType 71 }
unisevtModuleRt-T11-f-17                    OBJECT IDENTIFIER ::= { unisevtModuleRouterType 72 }
unisevtModuleRt-Rtb21ct3                    OBJECT IDENTIFIER ::= { unisevtModuleRouterType 73 }
unisevtModuleRt-Atmadsl1                    OBJECT IDENTIFIER ::= { unisevtModuleRouterType 74 }
unisevtModuleRt-Atmadsl2                    OBJECT IDENTIFIER ::= { unisevtModuleRouterType 75 }
unisevtModuleRt-Atm155m                     OBJECT IDENTIFIER ::= { unisevtModuleRouterType 76 }
unisevtModuleRt-Ase8                        OBJECT IDENTIFIER ::= { unisevtModuleRouterType 77 }
unisevtModuleRt-Ase16                       OBJECT IDENTIFIER ::= { unisevtModuleRouterType 78 }
unisevtModuleRt-Sae4                        OBJECT IDENTIFIER ::= { unisevtModuleRouterType 79 }
unisevtModuleRt-Sae2                        OBJECT IDENTIFIER ::= { unisevtModuleRouterType 80 }
unisevtModuleRt-Atmshdsl1                   OBJECT IDENTIFIER ::= { unisevtModuleRouterType 90 }
unisevtModuleRt-Atmshdsl2                   OBJECT IDENTIFIER ::= { unisevtModuleRouterType 91 }
unisevtModuleRt-Atmshdsl4                   OBJECT IDENTIFIER ::= { unisevtModuleRouterType 92 }
unisevtModuleRt-Atm25m                      OBJECT IDENTIFIER ::= { unisevtModuleRouterType 93 }
unisevtModuleRt-Atme3                       OBJECT IDENTIFIER ::= { unisevtModuleRouterType 94 }
unisevtModuleRt-Atmt3                       OBJECT IDENTIFIER ::= { unisevtModuleRouterType 95 }
unisevtModuleRt-Xdsl-fec                    OBJECT IDENTIFIER ::= { unisevtModuleRouterType 96 }
unisevtModuleRt-Xdsl-adsl                   OBJECT IDENTIFIER ::= { unisevtModuleRouterType 97 }
unisevtModuleRt-Xdsl-gshdsl                 OBJECT IDENTIFIER ::= { unisevtModuleRouterType 98 }
unisevtModuleRt-Xdsl-bri                    OBJECT IDENTIFIER ::= { unisevtModuleRouterType 99 }
unisevtModuleRt-Xdsl-scc                    OBJECT IDENTIFIER ::= { unisevtModuleRouterType 100 }
unisevtModuleRt-Ge1                         OBJECT IDENTIFIER ::= { unisevtModuleRouterType 101 }
unisevtModuleRt-Pos155m                     OBJECT IDENTIFIER ::= { unisevtModuleRouterType 102 }
unisevtModuleRt-Cpos                        OBJECT IDENTIFIER ::= { unisevtModuleRouterType 103 }
unisevtModuleRt-Fe1op                       OBJECT IDENTIFIER ::= { unisevtModuleRouterType 104 }
unisevtModuleRt-Sae8                        OBJECT IDENTIFIER ::= { unisevtModuleRouterType 105 }
unisevtModuleRt-Atm155m-mm                  OBJECT IDENTIFIER ::= { unisevtModuleRouterType 106 }
unisevtModuleRt-Atm155m-sm                  OBJECT IDENTIFIER ::= { unisevtModuleRouterType 107 }
unisevtModuleRt-Atm155m-sml                 OBJECT IDENTIFIER ::= { unisevtModuleRouterType 108 }
unisevtModuleRt-Fe1op-sfx                   OBJECT IDENTIFIER ::= { unisevtModuleRouterType 109 }
unisevtModuleRt-Fe1op-mfx                   OBJECT IDENTIFIER ::= { unisevtModuleRouterType 110 }
unisevtModuleRt-Cpos-t1                     OBJECT IDENTIFIER ::= { unisevtModuleRouterType 111 }
unisevtModuleRt-Ge1op                       OBJECT IDENTIFIER ::= { unisevtModuleRouterType 112 }
unisevtModuleRt-Ge2op                       OBJECT IDENTIFIER ::= { unisevtModuleRouterType 113 }
unisevtModuleRt-Ge2                         OBJECT IDENTIFIER ::= { unisevtModuleRouterType 114 }
unisevtModuleRt-Fix-1wan                    OBJECT IDENTIFIER ::= { unisevtModuleRouterType 115 }
unisevtModuleRt-Fix-1sae                    OBJECT IDENTIFIER ::= { unisevtModuleRouterType 116 }
unisevtModuleRt-Cavium                      OBJECT IDENTIFIER ::= { unisevtModuleRouterType 117 }
unisevtModuleRt-Sic1Eth                     OBJECT IDENTIFIER ::= { unisevtModuleRouterType 118 }
unisevtModuleRt-atm1ADSLI                   OBJECT IDENTIFIER ::= { unisevtModuleRouterType 119 }
unisevtModuleRt-atm2ADSLI                   OBJECT IDENTIFIER ::= { unisevtModuleRouterType 120 }
unisevtModuleRt-fix-e11                     OBJECT IDENTIFIER ::= { unisevtModuleRouterType 121 }
unisevtModuleRt-fix-t11                     OBJECT IDENTIFIER ::= { unisevtModuleRouterType 122 }
unisevtModuleRt-e18-75                      OBJECT IDENTIFIER ::= { unisevtModuleRouterType 123 }
unisevtModuleRt-e18-120                     OBJECT IDENTIFIER ::= { unisevtModuleRouterType 124 }
unisevtModuleRt-t18                         OBJECT IDENTIFIER ::= { unisevtModuleRouterType 125 }
unisevtModuleRt-sic-1vifxs                  OBJECT IDENTIFIER ::= { unisevtModuleRouterType 126 }
unisevtModuleRt-sic-1vifxo                  OBJECT IDENTIFIER ::= { unisevtModuleRouterType 127 }
unisevtModuleRt-sic-2vifxs                  OBJECT IDENTIFIER ::= { unisevtModuleRouterType 128 }
unisevtModuleRt-sic-2vifxo                  OBJECT IDENTIFIER ::= { unisevtModuleRouterType 129 }
unisevtModuleRt-xdsl-fec-new                OBJECT IDENTIFIER ::= { unisevtModuleRouterType 130 }
unisevtModuleRt-xdsl-sa                     OBJECT IDENTIFIER ::= { unisevtModuleRouterType 131 }
unisevtModuleRt-bs4                         OBJECT IDENTIFIER ::= { unisevtModuleRouterType 132 }
unisevtModuleRt-ima-8e175                   OBJECT IDENTIFIER ::= { unisevtModuleRouterType 133 }
unisevtModuleRt-ima-8e1120                  OBJECT IDENTIFIER ::= { unisevtModuleRouterType 134 }
unisevtModuleRt-ima-4e175                   OBJECT IDENTIFIER ::= { unisevtModuleRouterType 135 }
unisevtModuleRt-ima-4e1120                  OBJECT IDENTIFIER ::= { unisevtModuleRouterType 136 }
unisevtModuleRt-ima-8t1                     OBJECT IDENTIFIER ::= { unisevtModuleRouterType 137 }
unisevtModuleRt-ima-4t1                     OBJECT IDENTIFIER ::= { unisevtModuleRouterType 138 }
unisevtModuleRt-sic-1t1f                    OBJECT IDENTIFIER ::= { unisevtModuleRouterType 139 }
unisevtModuleRT-SIC-1E1F                    OBJECT IDENTIFIER ::= { unisevtModuleRouterType 140 }
unisevtModuleRt-VG-16fxs                    OBJECT IDENTIFIER ::= { unisevtModuleRouterType 141 }
unisevtModuleRt-VG-32fxs                    OBJECT IDENTIFIER ::= { unisevtModuleRouterType 142 }
unisevtModuleRt-VG-8fxo                     OBJECT IDENTIFIER ::= { unisevtModuleRouterType 143 }
unisevtModuleRt-VG-2fe                      OBJECT IDENTIFIER ::= { unisevtModuleRouterType 144 }
unisevtModuleRt-sib                         OBJECT IDENTIFIER ::= { unisevtModuleRouterType 145 } -- SIB card
unisevtModuleRt-cie32                       OBJECT IDENTIFIER ::= { unisevtModuleRouterType 146 } -- 32M SSRAM CIE card
unisevtModuleRt-cie64                       OBJECT IDENTIFIER ::= { unisevtModuleRouterType 147 } -- 64M SSRAM CIE card
unisevtModuleRt-cie96                       OBJECT IDENTIFIER ::= { unisevtModuleRouterType 148 } -- 96M SSRAM CIE card
unisevtModuleRt-Fe4                         OBJECT IDENTIFIER ::= { unisevtModuleRouterType 149 } -- 4FE card
unisevtModuleRt-fxs4fxo1                    OBJECT IDENTIFIER ::= { unisevtModuleRouterType 150 } -- 4 Port Foreign Exchange Station and 1 Port Foreign Exchange Office Interface
unisevtModuleRt-atm1shdsl4wire              OBJECT IDENTIFIER ::= { unisevtModuleRouterType 151 } -- G.SHDSL 4 wire MIM card, 1 port
unisevtModuleRt-atmIma4shdsl                OBJECT IDENTIFIER ::= { unisevtModuleRouterType 152 } -- G.SHDSL 8 wire MIM card, 4 ports
unisevtModuleRt-ls4                         OBJECT IDENTIFIER ::= { unisevtModuleRouterType 153 } -- 4 Ports Layer 2 Lanswitch Module
unisevtModuleRt-ls8                         OBJECT IDENTIFIER ::= { unisevtModuleRouterType 154 } -- 8 Ports Layer 2 Lanswitch Module
unisevtModuleRt-ls16                        OBJECT IDENTIFIER ::= { unisevtModuleRouterType 155 } -- 16 Ports Layer 2 Lanswitch Module
unisevtModuleRt-sic-adls2plus-isdn          OBJECT IDENTIFIER ::= { unisevtModuleRouterType 156 } -- ADLS2Plus SIC card, ISDN port
unisevtModuleRt-sic-adls2plus-pots          OBJECT IDENTIFIER ::= { unisevtModuleRouterType 157 } -- ADLS2Plus SIC card, POTS port
unisevtModuleRt-ft3                         OBJECT IDENTIFIER ::= { unisevtModuleRouterType 158 } -- 1 Port Fractional T3 module
unisevtModuleRt-ce32                        OBJECT IDENTIFIER ::= { unisevtModuleRouterType 159 } -- 2 Port Channelized E3 module
unisevtModuleRt-bsv2                        OBJECT IDENTIFIER ::= { unisevtModuleRouterType 160 } -- 2 Port BSV module
unisevtModuleRt-bsv4                        OBJECT IDENTIFIER ::= { unisevtModuleRouterType 161 } -- 4 Port BSV module
unisevtModuleRt-RPU                         OBJECT IDENTIFIER ::= { unisevtModuleRouterType 162 } -- Route processing unit
unisevtModuleRt-ERPU                        OBJECT IDENTIFIER ::= { unisevtModuleRouterType 163 } -- Enhanced route processing unit
unisevtModuleRt-SSL                         OBJECT IDENTIFIER ::= { unisevtModuleRouterType 164 } -- SSL Encrypt Card
unisevtModuleRt-NSA                         OBJECT IDENTIFIER ::= { unisevtModuleRouterType 165 } -- NSA Encrypt Card

--
-- 166 to 199 reserved for other devices
--


--
-- 200 to 399 reserved for normal routers part I
--
unisevtModuleRT-SIC-1GEC                    OBJECT IDENTIFIER ::= { unisevtModuleRouterType 200 } -- 1-Port 10M/100M/1000M COMBO Ethernet Interface SIC Module
unisevtModuleRT-24FSW                       OBJECT IDENTIFIER ::= { unisevtModuleRouterType 201 } -- 24-Port 10M/100M and 2-Port 1000BASE-T/1000BASE-X(COMBO) Ethernet L2 Switch Module
unisevtModuleRT-24FSWP                      OBJECT IDENTIFIER ::= { unisevtModuleRouterType 202 } -- 24-Port 10M/100M(WITH POE) and 2-Port 1000BASE-T/1000BASE-X(COMBO) Ethernet L2 Switch Module
unisevtModuleRT-16FSW                       OBJECT IDENTIFIER ::= { unisevtModuleRouterType 203 } -- 16-Port 10M/100M Ethernet L2 Switch Module
unisevtModuleRT-16FSWP                      OBJECT IDENTIFIER ::= { unisevtModuleRouterType 204 } -- 16-Port 10M/100M(WITH POE) Ethernet L2 Switch Module
unisevtModuleRT-1VE1                        OBJECT IDENTIFIER ::= { unisevtModuleRouterType 205 } -- 1-Port Voice E1 Module
unisevtModuleRT-1VT1                        OBJECT IDENTIFIER ::= { unisevtModuleRouterType 206 } -- 1-Port Voice T1 Module
unisevtModuleRT-2VE1                        OBJECT IDENTIFIER ::= { unisevtModuleRouterType 207 } -- 2-Port Voice E1 Module
unisevtModuleRT-2VT1                        OBJECT IDENTIFIER ::= { unisevtModuleRouterType 208 } -- 2-Port Voice T1 Module
unisevtModuleRT-SIC-4FSW                    OBJECT IDENTIFIER ::= { unisevtModuleRouterType 209 } -- 4-Port 10M/100M Ethernet L2 Switch Module (RJ45)
unisevtModuleRT-SIC-4FSWP                   OBJECT IDENTIFIER ::= { unisevtModuleRouterType 210 } -- 4-Port 10M/100M Ethernet L2 Switch Module(RJ45,WITH POE)
unisevtModuleRT-DSIC-9FSW                   OBJECT IDENTIFIER ::= { unisevtModuleRouterType 211 } -- 9-Port 10M/100M Ethernet L2 Switch Module(RJ45)
unisevtModuleRT-DSIC-9FSWP                  OBJECT IDENTIFIER ::= { unisevtModuleRouterType 212 } -- 9-Port 10M/100M Ethernet L2 Switch Module(RJ45,WITH POE)
unisevtModuleRT-SIC-1VE1                    OBJECT IDENTIFIER ::= { unisevtModuleRouterType 213 } -- 1-Port Voice E1 SIC Interface Module
unisevtModuleRT-SIC-1VT1                    OBJECT IDENTIFIER ::= { unisevtModuleRouterType 214 } -- 1-Port Voice T1 SIC Interface Module
unisevtModuleRT-VCPM                        OBJECT IDENTIFIER ::= { unisevtModuleRouterType 215 } -- Voice Co-Processing Module
unisevtModuleRT-VPM                         OBJECT IDENTIFIER ::= { unisevtModuleRouterType 216 } -- 32-Channels Voice Processing Module
unisevtModuleRT-VPMA                        OBJECT IDENTIFIER ::= { unisevtModuleRouterType 217 } -- 16-Channels Voice Processing Module
unisevtModuleRT-VPMB                        OBJECT IDENTIFIER ::= { unisevtModuleRouterType 218 } -- 8-Channels Voice Processing Module
unisevtModuleRT-VPMC                        OBJECT IDENTIFIER ::= { unisevtModuleRouterType 219 } -- 24-Channels Voice Processing Module
unisevtModuleRt-fe18-75                     OBJECT IDENTIFIER ::= { unisevtModuleRouterType 220 } -- 8 Port FE1(75 O) module
unisevtModuleRt-fe18-120                    OBJECT IDENTIFIER ::= { unisevtModuleRouterType 221 } -- 8 Port FE1(120 O) module
unisevtModuleRt-ft18                        OBJECT IDENTIFIER ::= { unisevtModuleRouterType 222 } -- 8 Port FT1 module
unisevtModuleRt-CF                          OBJECT IDENTIFIER ::= { unisevtModuleRouterType 223 } -- Compact Flash Card
unisevtModuleRt-bsv2-v2                     OBJECT IDENTIFIER ::= { unisevtModuleRouterType 224 } -- 2 Port BSV Version 2
unisevtModuleRt-e1vi1-v2                    OBJECT IDENTIFIER ::= { unisevtModuleRouterType 225 } -- E1VI Version 2
unisevtModuleRt-e1vi2                       OBJECT IDENTIFIER ::= { unisevtModuleRouterType 226 } -- 2 Port E1VI
unisevtModuleRt-t1vi1-v2                    OBJECT IDENTIFIER ::= { unisevtModuleRouterType 227 } -- T1VI Version 2
unisevtModuleRt-t1vi2                       OBJECT IDENTIFIER ::= { unisevtModuleRouterType 228 } -- 2 Port T1VI
unisevtModuleRt-osm                         OBJECT IDENTIFIER ::= { unisevtModuleRouterType 229 } -- Open Service Module
unisevtModuleRt-sd707                       OBJECT IDENTIFIER ::= { unisevtModuleRouterType 230 } -- Encryption Accelerator
unisevtModuleRt-dm-epri                     OBJECT IDENTIFIER ::= { unisevtModuleRouterType 231 } -- E1 Pri Digital Modem
unisevtModuleRt-dm-tpri                     OBJECT IDENTIFIER ::= { unisevtModuleRouterType 232 } -- T1 Pri Digital Modem
unisevtModuleRt-ERPU-H                      OBJECT IDENTIFIER ::= { unisevtModuleRouterType 233 } -- Enhanced route processing unit with only one optic GE interface
unisevtModuleRT-SIC-1BSV                    OBJECT IDENTIFIER ::= { unisevtModuleRouterType 234 } -- 1-Port Bri S/T VoiceInterface SIC Module
unisevtModuleRT-SIC-2BSV                    OBJECT IDENTIFIER ::= { unisevtModuleRouterType 235 } -- 2-Port Bri S/T VoiceInterface SIC Module
unisevtModuleRt-gbe8                        OBJECT IDENTIFIER ::= { unisevtModuleRouterType 236 } -- 8-Port Gigabit Ethernet interface card
unisevtModuleRt-gbe4                        OBJECT IDENTIFIER ::= { unisevtModuleRouterType 237 } -- 4-Port Gigabit Ethernet interface card
unisevtModuleRt-cpos2-v2                    OBJECT IDENTIFIER ::= { unisevtModuleRouterType 238 } -- 2-Port Channelized Low speed POS interface card
unisevtModuleRt-cpos1-v2                    OBJECT IDENTIFIER ::= { unisevtModuleRouterType 239 } -- 1-Port Channelized Low speed POS interface card
unisevtModuleRt-oap                         OBJECT IDENTIFIER ::= { unisevtModuleRouterType 240 } -- Open Application Platform
unisevtModuleRT-48FSWP                      OBJECT IDENTIFIER ::= { unisevtModuleRouterType 241 } -- 46-Port 10M/100M(With PoE) and 2-Port 1000BASE-T(With PoE) Ethernet L2 Switch Module
unisevtModuleRT-48FSW                       OBJECT IDENTIFIER ::= { unisevtModuleRouterType 242 } -- 46-Port 10M/100M and 2-Port 1000BASE-T Ethernet L2 Switch Module
unisevtModuleRT-ASM                         OBJECT IDENTIFIER ::= { unisevtModuleRouterType 243 } -- Anti-virus Security Module
unisevtModuleRT-SIC-1FEF                    OBJECT IDENTIFIER ::= { unisevtModuleRouterType 244 } -- 1-Port 100M SFP Interface SIC Module
unisevtModuleRT-XMIM-24FSW                  OBJECT IDENTIFIER ::= { unisevtModuleRouterType 245 } -- 24-Port 10M/100MBASE-TX Ethernet L2 Switch Interface XMIM-Module
unisevtModuleRT-WLAN-AG-1RADIO              OBJECT IDENTIFIER ::= { unisevtModuleRouterType 246 } -- Mini PCI Interface 802.11ag Radio Frequency Adapter Card
unisevtModuleRT-1CE3                        OBJECT IDENTIFIER ::= { unisevtModuleRouterType 247 } -- 1-port E3/CE3/FE3 Compatible Interface Module,(M)
unisevtModuleRT-XMIM-16FSW                  OBJECT IDENTIFIER ::= { unisevtModuleRouterType 248 } -- 16-Port 10M/100MBASE-TX Ethernet L2 Switch Interface XMIM-Module
unisevtModuleRT-OAPS                        OBJECT IDENTIFIER ::= { unisevtModuleRouterType 249 } -- Open Application System-Smart
unisevtModuleRT-NAM                         OBJECT IDENTIFIER ::= { unisevtModuleRouterType 250 } -- Network Analysis Module
unisevtModuleRT-RPE-X1                      OBJECT IDENTIFIER ::= { unisevtModuleRouterType 251 } -- Route Processing Engine
unisevtModuleRT-FIP-100                     OBJECT IDENTIFIER ::= { unisevtModuleRouterType 252 } -- Flexible Interface Platform-100
unisevtModuleRT-FIP-200                     OBJECT IDENTIFIER ::= { unisevtModuleRouterType 253 } -- Flexible Interface Platform-200
unisevtModuleRT-SIC-8AS                     OBJECT IDENTIFIER ::= { unisevtModuleRouterType 254 } -- 8-Port Asynchronous Serial
unisevtModuleRT-WAAM                        OBJECT IDENTIFIER ::= { unisevtModuleRouterType 255 } -- WAN Application Acceleration Module
unisevtModuleRt-msp4p-OC3c                  OBJECT IDENTIFIER ::= { unisevtModuleRouterType 256 } -- 4 Port Multi-Speed POS Interface Module (OC-3c Mode)
unisevtModuleRt-1pos-oc48                   OBJECT IDENTIFIER ::= { unisevtModuleRouterType 257 } -- 1 Port Super-Speed POS Interface Card
unisevtModuleRt-xgbe                        OBJECT IDENTIFIER ::= { unisevtModuleRouterType 258 } -- 1-Port 10GBASE-R/W Ethernet Optical Interface Card
unisevtModuleRT-EADM                        OBJECT IDENTIFIER ::= { unisevtModuleRouterType 259 } -- EAD Integrated Module
unisevtModuleRT-VCM                         OBJECT IDENTIFIER ::= { unisevtModuleRouterType 260 } -- Voice Convergence Module
unisevtModuleRT-SIC-2FXS1FXO                OBJECT IDENTIFIER ::= { unisevtModuleRouterType 261 } -- 2FXS+1FXO Interface SIC-Module
unisevtModuleRT-8FXS8FXO                    OBJECT IDENTIFIER ::= { unisevtModuleRouterType 262 } -- 8FXS+8FXO Interface Module
unisevtModuleRT-16FXS                       OBJECT IDENTIFIER ::= { unisevtModuleRouterType 263 } -- 16-port FXS Interface Module
unisevtModuleRT-OAPS-ICM                    OBJECT IDENTIFIER ::= { unisevtModuleRouterType 264 } -- OAPS Information Communication Module
unisevtModuleRT-OAP-ICM                     OBJECT IDENTIFIER ::= { unisevtModuleRouterType 265 } -- OAP Information Communication Module
unisevtModuleRT-8fe                         OBJECT IDENTIFIER ::= { unisevtModuleRouterType 266 } -- 8-Port 100M Ethernet Electrical Interface Module
unisevtModuleRT-4gbp                        OBJECT IDENTIFIER ::= { unisevtModuleRouterType 267 } -- 4-Port GigaBit Ethernet Optical Interface Module(SFP)
unisevtModuleRT-MPU-G2                      OBJECT IDENTIFIER ::= { unisevtModuleRouterType 268 } -- Main Processor Unit
unisevtModuleRT-OAPS-OCE                    OBJECT IDENTIFIER ::= { unisevtModuleRouterType 269 } -- OAPS Office Communication Engine
unisevtModuleRT-OAP-OCE                     OBJECT IDENTIFIER ::= { unisevtModuleRouterType 270 } -- OAP Office Communication Engine
unisevtModuleRT-OAPS-ICE                    OBJECT IDENTIFIER ::= { unisevtModuleRouterType 271 } -- OAPS Information Communication Engine
unisevtModuleRT-OAP-ICE                     OBJECT IDENTIFIER ::= { unisevtModuleRouterType 272 } -- OAP Information Communication Module
unisevtModuleRT-SIC-16AS                    OBJECT IDENTIFIER ::= { unisevtModuleRouterType 273 } -- 16-Port Asynchronous Serial
unisevtModuleRT-SPE-FWM                     OBJECT IDENTIFIER ::= { unisevtModuleRouterType 274 } -- Gigabit Firewall Module
unisevtModuleRT-cls2p                       OBJECT IDENTIFIER ::= { unisevtModuleRouterType 275 } -- 2 Port Channelized 155M POS to E3/T3 Interface Module
unisevtModuleRT-cls1p                       OBJECT IDENTIFIER ::= { unisevtModuleRouterType 276 } -- 1 Port Channelized 155M POS to E3/T3 Interface Module
unisevtModuleRT-SIC-2E1-F                   OBJECT IDENTIFIER ::= { unisevtModuleRouterType 277 } -- 2-Port Fractional E1 Interface SIC-Module
unisevtModuleRT-SIC-1E1-F-V2                OBJECT IDENTIFIER ::= { unisevtModuleRouterType 278 } -- 1-Port Fractional E1 Interface SIC-Module
unisevtModuleRT-MCU                         OBJECT IDENTIFIER ::= { unisevtModuleRouterType 279 } -- Main Control Unit
unisevtModuleRT-ACU                         OBJECT IDENTIFIER ::= { unisevtModuleRouterType 280 } -- Access Control Unit
unisevtModuleRT-1ATM-OC3                    OBJECT IDENTIFIER ::= { unisevtModuleRouterType 281 } -- 1-Port Asynchronous Transfer Mode OC3 Board
unisevtModuleRT-RSE-X1                      OBJECT IDENTIFIER ::= { unisevtModuleRouterType 282 } -- Main Processing Unit With XAUI Switch
unisevtModuleRT-FIP-210                     OBJECT IDENTIFIER ::= { unisevtModuleRouterType 283 } -- Multi-core CPU Line Processing Board with 2 Combo GE Ports
unisevtModuleRT-1expa                       OBJECT IDENTIFIER ::= { unisevtModuleRouterType 284 } -- 1 Port Ten Gigabit Interface Module
unisevtModuleRT-WLAN-SIC-N-1RADIO           OBJECT IDENTIFIER ::= { unisevtModuleRouterType 285 } -- 1 wlan-radio 802.11n sic Interface Board
unisevtModuleRT-WLAN-SIC-BG-1RADIO          OBJECT IDENTIFIER ::= { unisevtModuleRouterType 286 } -- 1 wlan-radio 802.11b/g sic Interface Board
unisevtModuleRT-al2p                        OBJECT IDENTIFIER ::= { unisevtModuleRouterType 287 } -- 2 Port 155M ATM Interface Module
unisevtModuleRT-msp2p-OC3c                  OBJECT IDENTIFIER ::= { unisevtModuleRouterType 288 } -- 2-Port Multi-speed POS Interface Module (OC-3c Mode)
unisevtModuleRT-8gbp                        OBJECT IDENTIFIER ::= { unisevtModuleRouterType 289 } -- 8-Port GigaBit Ethernet Optical Interface Module(SFP)
unisevtModuleRT-SIC-EPON                    OBJECT IDENTIFIER ::= { unisevtModuleRouterType 290 } -- 1-Port Ethernet Passive Optical Network SIC Card(SFF)
unisevtModuleRT-SIC-3G-GSM-H3               OBJECT IDENTIFIER ::= { unisevtModuleRouterType 291 } -- 3G Wireless WAN Interface SIC Module Supporting GPRS/EDGE/UMTS/HSDPA
unisevtModuleRT-msp2p-OC12c                 OBJECT IDENTIFIER ::= { unisevtModuleRouterType 292 } -- 2-Port Multi-speed POS Interface Module (OC-12c Mode)
unisevtModuleRt-msp4p-OC12c                 OBJECT IDENTIFIER ::= { unisevtModuleRouterType 293 } -- 4-Port Multi-Speed POS Interface Module (OC-12c Mode)
unisevtModuleRt-al1p                        OBJECT IDENTIFIER ::= { unisevtModuleRouterType 294 } -- 1-Port 155M ATM Interface Module
unisevtModuleRt-OAP-100                     OBJECT IDENTIFIER ::= { unisevtModuleRouterType 295 } -- Open Application Platform Module
unisevtModuleRt-FIP-110                     OBJECT IDENTIFIER ::= { unisevtModuleRouterType 296 } -- Flexible Interface Platform-110
unisevtModuleRt-OSM-SSM                     OBJECT IDENTIFIER ::= { unisevtModuleRouterType 297 } -- OSM Security Services Module
unisevtModuleRt-OAP-SSM                     OBJECT IDENTIFIER ::= { unisevtModuleRouterType 298 } -- OAP Security Services Module
unisevtModuleRt-rs2p                        OBJECT IDENTIFIER ::= { unisevtModuleRouterType 299 } -- 2-Port OC-48c/STM-16c RPR Interface Module
unisevtModuleRt-SAP-48GBE                   OBJECT IDENTIFIER ::= { unisevtModuleRouterType 300 } -- 48-Port 1000Base-T Gigabit Ethernet Interface Module
unisevtModuleRt-SAP-48GBP                   OBJECT IDENTIFIER ::= { unisevtModuleRouterType 301 } -- 48-Port 1000BASE Ethernet Optical Interface Module
unisevtModuleRt-SAP-24GBP                   OBJECT IDENTIFIER ::= { unisevtModuleRouterType 302 } -- 24-Port 1000BASE Ethernet Optical Interface Module
unisevtModuleRt-SPE-SSL                     OBJECT IDENTIFIER ::= { unisevtModuleRouterType 303 } -- SSL VPN Module
unisevtModuleRt-SIC-AUDIO                   OBJECT IDENTIFIER ::= { unisevtModuleRouterType 304 } -- MOH and PAGE Interface SIC Module Supporting MOH/PAGE/DOOR RELAY
unisevtModuleRt-FIC-1E1POS-H3               OBJECT IDENTIFIER ::= { unisevtModuleRouterType 305 } -- 1-Port E1 POS Interface FIC Module
unisevtModuleRt-DSIC-4FXS1FXO               OBJECT IDENTIFIER ::= { unisevtModuleRouterType 306 } -- 4FXS+1FXO Interface DSIC-Module
unisevtModuleRt-FIC-CPOS                    OBJECT IDENTIFIER ::= { unisevtModuleRouterType 307 } -- 1-Port CPOS Interface Module
unisevtModuleRt-DSIC-1SHDSL-8W              OBJECT IDENTIFIER ::= { unisevtModuleRouterType 308 } -- 1-Port 8 Wire SHDSL Interface DSIC Module
unisevtModuleRt-SIC-3G-TD                   OBJECT IDENTIFIER ::= { unisevtModuleRouterType 309 } -- 1 Port TD-Cellular Interface SIC-Module
unisevtModuleRt-SIC-3G-CDMA                 OBJECT IDENTIFIER ::= { unisevtModuleRouterType 310 } -- 1 Port CDMA-Cellular Interface SIC-Module
unisevtModuleRt-SIC-3G-HSPA                 OBJECT IDENTIFIER ::= { unisevtModuleRouterType 311 } -- 1 Port HSPA-Cellular Interface SIC-Module
unisevtModuleRt-FIC-OAP-V2                  OBJECT IDENTIFIER ::= { unisevtModuleRouterType 312 } -- Open Application Platform V2 FIC Module
unisevtModuleRt-MIM-OAP-V2                  OBJECT IDENTIFIER ::= { unisevtModuleRouterType 313 } -- Open Application Platform V2 MIM Module
unisevtModuleRt-MIM-OAPS-V2                 OBJECT IDENTIFIER ::= { unisevtModuleRouterType 314 } -- Open Application System-Smart V2 MIM Module
unisevtModuleRt-HMIM-1CT3                   OBJECT IDENTIFIER ::= { unisevtModuleRouterType 315 } -- 1 Port Channelized T3 Interface HMIM Module
unisevtModuleRt-HMIM-1CE3                   OBJECT IDENTIFIER ::= { unisevtModuleRouterType 316 } -- 1 Port Channelized E3 Interface HMIM Module
unisevtModuleRt-HMIM-1POS                   OBJECT IDENTIFIER ::= { unisevtModuleRouterType 317 } -- 1 Port POS Interface HMIM Module
unisevtModuleRt-HMIM-2SAE                   OBJECT IDENTIFIER ::= { unisevtModuleRouterType 318 } -- 2 Port SAE Interface HMIM Module
unisevtModuleRt-HMIM-4SAE                   OBJECT IDENTIFIER ::= { unisevtModuleRouterType 319 } -- 4 Port SAE Interface HMIM Module
unisevtModuleRt-HMIM-8SAE                   OBJECT IDENTIFIER ::= { unisevtModuleRouterType 320 } -- 8 Port SAE Interface HMIM Module
unisevtModuleRt-HMIM-8ASE                   OBJECT IDENTIFIER ::= { unisevtModuleRouterType 321 } -- 8 Port ASE Interface HMIM Module
unisevtModuleRt-HMIM-16ASE                  OBJECT IDENTIFIER ::= { unisevtModuleRouterType 322 } -- 16 Port ASE Interface HMIM Module
unisevtModuleRt-HMIM-1E1                    OBJECT IDENTIFIER ::= { unisevtModuleRouterType 323 } -- 1 Port E1 Interface HMIM Module
unisevtModuleRt-HMIM-2E1                    OBJECT IDENTIFIER ::= { unisevtModuleRouterType 324 } -- 2 Port E1 Interface HMIM Module
unisevtModuleRt-HMIM-4E1                    OBJECT IDENTIFIER ::= { unisevtModuleRouterType 325 } -- 4 Port E1 Interface HMIM Module
unisevtModuleRt-HMIM-8E1-75                 OBJECT IDENTIFIER ::= { unisevtModuleRouterType 326 } -- 8 Port E1(75 o) Interface HMIM Module
unisevtModuleRt-HMIM-1E1-F                  OBJECT IDENTIFIER ::= { unisevtModuleRouterType 327 } -- 1 Port E1-F Interface HMIM Module
unisevtModuleRt-HMIM-2E1-F                  OBJECT IDENTIFIER ::= { unisevtModuleRouterType 328 } -- 2 Port E1-F Interface HMIM Module
unisevtModuleRt-HMIM-4E1-F                  OBJECT IDENTIFIER ::= { unisevtModuleRouterType 329 } -- 4 Port E1-F Interface HMIM Module
unisevtModuleRt-HMIM-8E1-F-75               OBJECT IDENTIFIER ::= { unisevtModuleRouterType 330 } -- 8 Port E1-F(75 o) Interface HMIM Module
unisevtModuleRt-HMIM-6AM                    OBJECT IDENTIFIER ::= { unisevtModuleRouterType 331 } -- 6 Port AM Interface HMIM Module
unisevtModuleRt-HMIM-6FCM                   OBJECT IDENTIFIER ::= { unisevtModuleRouterType 332 } -- 6 Port FCM Interface HMIM Module
unisevtModuleRt-HMIM-2T1                    OBJECT IDENTIFIER ::= { unisevtModuleRouterType 333 } -- 2 Port T1 Interface HMIM Module
unisevtModuleRt-HMIM-4T1-F                  OBJECT IDENTIFIER ::= { unisevtModuleRouterType 334 } -- 4 Port T1-F Interface HMIM Module
unisevtModuleRt-HMIM-8T1                    OBJECT IDENTIFIER ::= { unisevtModuleRouterType 335 } -- 8 Port T1 Interface HMIM Module
unisevtModuleRt-HMIM-8T1-F                  OBJECT IDENTIFIER ::= { unisevtModuleRouterType 336 } -- 8 Port T1-F Interface HMIM Module
unisevtModuleRt-HMIM-1VE1                   OBJECT IDENTIFIER ::= { unisevtModuleRouterType 337 } -- 1 Port Voice E1 Interface HMIM Module
unisevtModuleRt-HMIM-1VT1                   OBJECT IDENTIFIER ::= { unisevtModuleRouterType 338 } -- 1 Port Voice T1 Interface HMIM Module
unisevtModuleRt-HMIM-2VE1                   OBJECT IDENTIFIER ::= { unisevtModuleRouterType 339 } -- 2 Port Voice E1 Interface HMIM Module
unisevtModuleRt-HMIM-2VT1                   OBJECT IDENTIFIER ::= { unisevtModuleRouterType 340 } -- 2 Port Voice T1 Interface HMIM Module
unisevtModuleRt-HMIM-8FXS8FXO               OBJECT IDENTIFIER ::= { unisevtModuleRouterType 341 } -- 8FXS + 8FXO Interface HMIM Module
unisevtModuleRt-HMIM-16FXS                  OBJECT IDENTIFIER ::= { unisevtModuleRouterType 342 } -- 16 Port FXS Interface HMIM Module
unisevtModuleRt-HMIM-4FXS                   OBJECT IDENTIFIER ::= { unisevtModuleRouterType 343 } -- 4 Port FXS Interface HMIM Module
unisevtModuleRt-HMIM-4FXO                   OBJECT IDENTIFIER ::= { unisevtModuleRouterType 344 } -- 4 Port FXO Interface HMIM Module
unisevtModuleRt-HMIM-4EM                    OBJECT IDENTIFIER ::= { unisevtModuleRouterType 345 } -- 4 Port E&M Interface HMIM Module
unisevtModuleRt-HMIM-4BSV                   OBJECT IDENTIFIER ::= { unisevtModuleRouterType 346 } -- 4 Port Bri S/T Voice Interface HMIM Module
unisevtModuleRt-SIC-CNDE                    OBJECT IDENTIFIER ::= { unisevtModuleRouterType 347 } -- CNDE Crypto Engine SIC-Module
unisevtModuleRt-ESM-CNDE                    OBJECT IDENTIFIER ::= { unisevtModuleRouterType 348 } -- CNDE Crypto Engine ESM-Module
unisevtModuleRt-ESM-CNDE-M                  OBJECT IDENTIFIER ::= { unisevtModuleRouterType 349 } -- CNDE Crypto Engine MiniPCI-ESM-Module
unisevtModuleRt-SR6602-X1                   OBJECT IDENTIFIER ::= { unisevtModuleRouterType 350 } -- 2U Router Host(4GE Combo/2 HIM slot)
unisevtModuleRt-SR6602-X2                   OBJECT IDENTIFIER ::= { unisevtModuleRouterType 351 } -- 2U Router Host(4GE Combo/2 10G SFP+/2 HIM slot)
unisevtModuleRt-MCP-X1                      OBJECT IDENTIFIER ::= { unisevtModuleRouterType 352 } -- Main Controller and Processor X1
unisevtModuleRt-MCP-X2                      OBJECT IDENTIFIER ::= { unisevtModuleRouterType 353 } -- Main Controller and Processor X2
unisevtModuleRt-FIP-10                      OBJECT IDENTIFIER ::= { unisevtModuleRouterType 354 } -- Flexible Interface Platform 10
unisevtModuleRt-FIP-20                      OBJECT IDENTIFIER ::= { unisevtModuleRouterType 355 } -- Flexible Interface Platform 20
unisevtModuleRt-RSE-X2                      OBJECT IDENTIFIER ::= { unisevtModuleRouterType 356 } -- Route Switch Engine X2
unisevtModuleRt-FIP-600                     OBJECT IDENTIFIER ::= { unisevtModuleRouterType 357 } -- Flexible Interface Platform 600
unisevtModuleRt-SAP-4EXP                    OBJECT IDENTIFIER ::= { unisevtModuleRouterType 358 } -- 4-Port 10GBASE-R/W Ethernet Optical Interface Module(SFP+)
unisevtModuleRt-SFE-X1                      OBJECT IDENTIFIER ::= { unisevtModuleRouterType 359 } -- Switch Fabric Engine X1
unisevtModuleRt-SFE-A1                      OBJECT IDENTIFIER ::= { unisevtModuleRouterType 360 } -- Switch Fabric Engine A1
unisevtModuleRt-HMIM-24GSW                  OBJECT IDENTIFIER ::= { unisevtModuleRouterType 361 } -- 24-Port 10M/100M/1000MBASE-T Ethernet L2 Switch Interface HMIM_Module
unisevtModuleRt-HMIM-24GSWP                 OBJECT IDENTIFIER ::= { unisevtModuleRouterType 362 } -- 24-Port 10M/100M/1000MBASE-T(WITH POE) Ethernet L2 Switch Interface HMIM_Module
unisevtModuleRt-MPU100                      OBJECT IDENTIFIER ::= { unisevtModuleRouterType 363 } -- Main Processing Unit 100
unisevtModuleRt-SPU100                      OBJECT IDENTIFIER ::= { unisevtModuleRouterType 364 } -- Service Processing Unit 100
unisevtModuleRt-SPU200                      OBJECT IDENTIFIER ::= { unisevtModuleRouterType 365 } -- Service Processing Unit 200
unisevtModuleRt-WLAN-N-1RADIO               OBJECT IDENTIFIER ::= { unisevtModuleRouterType 366 } -- Mini PCI Interface 802.11n Radio Frequency Adapter Card
unisevtModuleRt-3G-CDMA                     OBJECT IDENTIFIER ::= { unisevtModuleRouterType 367 } -- 1 Port CDMA-Cellular Interface Adapter Card
unisevtModuleRt-3G-WCDMA                    OBJECT IDENTIFIER ::= { unisevtModuleRouterType 368 } -- 1 Port WCDMA-Cellular Interface Adapter Card
unisevtModuleRt-3G-HSPAPLUS                 OBJECT IDENTIFIER ::= { unisevtModuleRouterType 369 } -- 1 Port HSPA+-Cellular Interface Adapter Card
unisevtModuleRt-VPM-128                     OBJECT IDENTIFIER ::= { unisevtModuleRouterType 370 } -- 128-VoiceChannel VPM Module
unisevtModuleRt-VPM-256                     OBJECT IDENTIFIER ::= { unisevtModuleRouterType 371 } -- 256-VoiceChannel VPM Module
unisevtModuleRt-VPM-512                     OBJECT IDENTIFIER ::= { unisevtModuleRouterType 372 } -- 512-VoiceChannel VPM Module
unisevtModuleRt-HMIM-8GEE                   OBJECT IDENTIFIER ::= { unisevtModuleRouterType 373 } -- 8-port copper GigabitEthernet HMIM Module
unisevtModuleRt-HMIM-4GEE                   OBJECT IDENTIFIER ::= { unisevtModuleRouterType 374 } -- 4-port copper GigabitEthernet HMIM Module
unisevtModuleRt-HMIM-2GEE                   OBJECT IDENTIFIER ::= { unisevtModuleRouterType 375 } -- 2-port copper GigabitEthernet HMIM Module
unisevtModuleRt-HMIM-8GEF                   OBJECT IDENTIFIER ::= { unisevtModuleRouterType 376 } -- 8-port fiber GigabitEthernet HMIM Module
unisevtModuleRt-HMIM-4GEF                   OBJECT IDENTIFIER ::= { unisevtModuleRouterType 377 } -- 4-port fiber GigabitEthernet HMIM Module
unisevtModuleRt-HMIM-2GEF                   OBJECT IDENTIFIER ::= { unisevtModuleRouterType 378 } -- 2-port fiber GigabitEthernet HMIM Module
unisevtModuleRt-SPU300                      OBJECT IDENTIFIER ::= { unisevtModuleRouterType 379 } -- Service Processing Unit 300
unisevtModuleRt-HMIM-1CPOS                  OBJECT IDENTIFIER ::= { unisevtModuleRouterType 380 } -- 1-port CPOS Interface HMIM Module
unisevtModuleRt-HMIM-2CPOS                  OBJECT IDENTIFIER ::= { unisevtModuleRouterType 381 } -- 2-port CPOS Interface HMIM Module
unisevtModuleRt-SPU100-5080                 OBJECT IDENTIFIER ::= { unisevtModuleRouterType 382 } -- Service Processing Unit 100
unisevtModuleRt-SPU200-5080                 OBJECT IDENTIFIER ::= { unisevtModuleRouterType 383 } -- Service Processing Unit 200
unisevtModuleRt-SPU300-5080                 OBJECT IDENTIFIER ::= { unisevtModuleRouterType 384 } -- Service Processing Unit 300
unisevtModuleRt-4G-LTE-Verizon              OBJECT IDENTIFIER ::= { unisevtModuleRouterType 385 } -- 1 Port 4G-LTE-Verizon-Cellular Interface Adapter Card
unisevtModuleRt-4G-LTE-Global               OBJECT IDENTIFIER ::= { unisevtModuleRouterType 386 } -- 1 Port 4G-LTE-Global-Cellular Interface Adapter Card
unisevtModuleRt-HMIM-1ATM-OC3               OBJECT IDENTIFIER ::= { unisevtModuleRouterType 387 } -- 1-Port OC3 ATM MM/SM/SML HMIM Module
unisevtModuleRt-SIC-1E1-V2                  OBJECT IDENTIFIER ::= { unisevtModuleRouterType 388 } -- 1-Port E1/CE1/PRI Interface SIC Module
unisevtModuleRt-FIP-300                     OBJECT IDENTIFIER ::= { unisevtModuleRouterType 389 } -- Flexible Interface Platform 300
unisevtModuleRt-FIP-310                     OBJECT IDENTIFIER ::= { unisevtModuleRouterType 390 } -- Flexible Interface Platform 310
unisevtModuleRt-TS8P                        OBJECT IDENTIFIER ::= { unisevtModuleRouterType 391 } -- 8-Port OC-3c/OC-12c POS or Gigabit Ethernet Optical Interface Module(SFP)
unisevtModuleRt-4G4P                        OBJECT IDENTIFIER ::= { unisevtModuleRouterType 392 } -- 4-Port Gigabit Ethernet Optical Interface and 4-Port OC-3c POS Interface Module(SFP)
unisevtModuleRt-SIC-4G-LTE-V                OBJECT IDENTIFIER ::= { unisevtModuleRouterType 393 } -- 1 Port 4G-LTE-Verizon-Cellular Interface SIC-Module
unisevtModuleRt-SIC-4G-LTE-A                OBJECT IDENTIFIER ::= { unisevtModuleRouterType 394 } -- 1 Port 4G-LTE-AT&T-Cellular Interface SIC-Module
unisevtModuleRt-SIC-4G-LTE-G                OBJECT IDENTIFIER ::= { unisevtModuleRouterType 395 } -- 1 Port 4G-LTE-Global-Cellular Interface SIC-Module
unisevtModuleRt-SIC-2SAE                    OBJECT IDENTIFIER ::= { unisevtModuleRouterType 396 } -- 2 Port SAE Interface SIC Module
unisevtModuleRt-SIC-4SAE                    OBJECT IDENTIFIER ::= { unisevtModuleRouterType 397 } -- 4 Port SAE Interface SIC Module
unisevtModuleRt-HMIM-OAP                    OBJECT IDENTIFIER ::= { unisevtModuleRouterType 398 } -- Open Application Platform HMIM Interface Module with Cloud Virtualization Kernel
unisevtModuleRt-HMIM-8GSW                   OBJECT IDENTIFIER ::= { unisevtModuleRouterType 399 } -- 8-Port 10M/100M/1000MBASE-T Ethernet L2 Switch Interface HMIM-Module,including 2 Combo Ports

--
-- 400 to 599 reserved for security routers
--
unisevtModuleRt-IPU                         OBJECT IDENTIFIER ::= { unisevtModuleRouterType 400 } -- IPS Processing Unit
unisevtModuleRt-MIM2GEBE-PCIE               OBJECT IDENTIFIER ::= { unisevtModuleRouterType 401 } -- 2-port UTM GigabitEthernet Interface Module
unisevtModuleRt-HIM12GE-PCIE                OBJECT IDENTIFIER ::= { unisevtModuleRouterType 402 } -- 12-port GigabitEthernet Interface Module
unisevtModuleRt-HIM2XGE-PCIE                OBJECT IDENTIFIER ::= { unisevtModuleRouterType 403 } -- 2-port Ten-GigabitEthernet Interface Module
unisevtModuleRt-IPU-T1000-M                 OBJECT IDENTIFIER ::= { unisevtModuleRouterType 404 } -- IPS Processing Unit for T1000-M Mainboard Module
unisevtModuleRt-IPU-GX4C                    OBJECT IDENTIFIER ::= { unisevtModuleRouterType 405 } -- 4 Port Gigabit Fiber Module
unisevtModuleRt-IPU-GT4C                    OBJECT IDENTIFIER ::= { unisevtModuleRouterType 406 } -- 4 Port 1000BASE-T Module
unisevtModuleRt-RPU-IAG2000-A               OBJECT IDENTIFIER ::= { unisevtModuleRouterType 407 } -- Intelligence Application Gateway Module
unisevtModuleRt-RPU-AFD1000-A               OBJECT IDENTIFIER ::= { unisevtModuleRouterType 408 } -- Anomaly Flow Detector Module
unisevtModuleRt-RPU-F5000-A                 OBJECT IDENTIFIER ::= { unisevtModuleRouterType 409 } -- Advanced Firewall Module
unisevtModuleRt-ACG-8800S3-MPU              OBJECT IDENTIFIER ::= { unisevtModuleRouterType 410 } -- Main Control Unit,with 24 1000BASE-X/100BASE-FX Optical Ports,including 8 Combo Ports,SFP Req
unisevtModuleRt-T5000S3-MPU                 OBJECT IDENTIFIER ::= { unisevtModuleRouterType 411 } -- Main Control Unit,with 24 1000BASE-X/100BASE-FX Optical Ports,including 8 Combo Ports,SFP Req
unisevtModuleRt-NS21S2MSPB0                 OBJECT IDENTIFIER ::= { unisevtModuleRouterType 412 } -- Multi Service Processing Module
unisevtModuleRt-NS11S2MSPB0                 OBJECT IDENTIFIER ::= { unisevtModuleRouterType 413 } -- Multi Service Processing Module
unisevtModuleRt-NSQ1WLAN                    OBJECT IDENTIFIER ::= { unisevtModuleRouterType 414 } -- Dual-Band,Multi-Mode 802.11a/b/g Wireless LAN card
unisevtModuleRt-NSQ1GP4U0                   OBJECT IDENTIFIER ::= { unisevtModuleRouterType 415 } -- 4 Port Gigabit Fiber Module
unisevtModuleRt-NSQ1GP8C40                  OBJECT IDENTIFIER ::= { unisevtModuleRouterType 416 } -- 12-Port GigabitEthernet Interface Module,with 4 Combo Ports,8 Fiber Ports
unisevtModuleRt-NSQ1XS2U0                   OBJECT IDENTIFIER ::= { unisevtModuleRouterType 417 } -- 2-Port Ten GigabitEthernet Interface Module
unisevtModuleRt-NSQ1G24XS60                 OBJECT IDENTIFIER ::= { unisevtModuleRouterType 418 } -- 12-copper 12-fiber and 6-XGE Interface Module
unisevtModuleRt-NSQ1TGX4EA0                 OBJECT IDENTIFIER ::= { unisevtModuleRouterType 419 } -- 4-XGE Fabric Interface Module
unisevtModuleRt-NSQ1FAB08D0                 OBJECT IDENTIFIER ::= { unisevtModuleRouterType 420 } -- Switch Module
unisevtModuleRt-NSQ1TGS32SF0                OBJECT IDENTIFIER ::= { unisevtModuleRouterType 421 } -- 32-XGE Fabric Interface Module
unisevtModuleRt-NSQ1QGS4SF0                 OBJECT IDENTIFIER ::= { unisevtModuleRouterType 422 } -- 4-XGE Fabric Interface Module
unisevtModuleRt-NSQ1GP24TXEA0               OBJECT IDENTIFIER ::= { unisevtModuleRouterType 423 } -- 16-GE Fabric,8-GE Combo,2-XGE Interface Module
unisevtModuleRt-NSQ1GP48EB0                 OBJECT IDENTIFIER ::= { unisevtModuleRouterType 424 } -- 48-GE Fabric Interface Module
unisevtModuleRt-NSQ1FWCEA0                  OBJECT IDENTIFIER ::= { unisevtModuleRouterType 425 } -- Firewall Module
unisevtModuleRt-NSQ1GT48EA0                 OBJECT IDENTIFIER ::= { unisevtModuleRouterType 426 } -- 48-GE Copper Interface
unisevtModuleRt-NSQ1TGS8EA0                 OBJECT IDENTIFIER ::= { unisevtModuleRouterType 427 } -- 8-XGE Fabric Interface
unisevtModuleRt-NSQ1FAB04B0                 OBJECT IDENTIFIER ::= { unisevtModuleRouterType 428 } -- Switch Module
unisevtModuleRt-NSQ1FAB12D0                 OBJECT IDENTIFIER ::= { unisevtModuleRouterType 429 } -- Switch Module
unisevtModuleRt-NSQ1SUPB0                   OBJECT IDENTIFIER ::= { unisevtModuleRouterType 430 } -- Main Control Module
unisevtModuleRt-VFW1000                     OBJECT IDENTIFIER ::= { unisevtModuleRouterType 431 } -- Virtual Firwall Gateway module over virtual machine
unisevtModuleRt-NSQ1CGC2SE0                 OBJECT IDENTIFIER ::= { unisevtModuleRouterType 432 } -- 2 Port 100GBASE Ethernet Optical Interface Board(CFP)(SE)
unisevtModuleRt-VLB1000                     OBJECT IDENTIFIER ::= { unisevtModuleRouterType 433 } -- Virtual LB module over virtual machine
unisevtModuleRt-NSQM1GT4PFC                 OBJECT IDENTIFIER ::= { unisevtModuleRouterType 434 } -- 4 Port GigabitEthernet Interface
unisevtModuleRt-NSQM1FWDFG0                 OBJECT IDENTIFIER ::= { unisevtModuleRouterType 435 } -- Firewall Module
unisevtModuleRt-NSQM1NATDFGA0               OBJECT IDENTIFIER ::= { unisevtModuleRouterType 436 } -- NAT A module
unisevtModuleRt-NSQM1NATDFGB0               OBJECT IDENTIFIER ::= { unisevtModuleRouterType 437 } -- NAT B module
unisevtModuleRt-VFW2000                     OBJECT IDENTIFIER ::= { unisevtModuleRouterType 438 } -- Virtual Firwall Gateway module over physical machine
unisevtModuleRt-VLB2000                     OBJECT IDENTIFIER ::= { unisevtModuleRouterType 439 } -- Virtual LB module ver physical machine
unisevtModuleRt-NSQM1IPSDFG0                OBJECT IDENTIFIER ::= { unisevtModuleRouterType 440 } -- NSQM1IPSDFG0
unisevtModuleRt-NSQM1FWDFGB0                OBJECT IDENTIFIER ::= { unisevtModuleRouterType 441 } -- NSQM1FWDFGB0-SecBlade IV
unisevtModuleRt-NSQM1FWDFGC0                OBJECT IDENTIFIER ::= { unisevtModuleRouterType 442 } -- NSQM1FWDFGC0-SecBlade IV
unisevtModuleRt-NSQM1FWDFGA1                OBJECT IDENTIFIER ::= { unisevtModuleRouterType 443 } -- NSQM1FWDFGA1-SecBlade IV
unisevtModuleRt-NSQM1FWDFGB1                OBJECT IDENTIFIER ::= { unisevtModuleRouterType 444 } -- NSQM1FWDFGB1-SecBlade IV
unisevtModuleRt-NSQM1FWDFGC1                OBJECT IDENTIFIER ::= { unisevtModuleRouterType 445 } -- NSQM1FWDFGC1-SecBlade IV
unisevtModuleRt-NSQM1FWDFGD1                OBJECT IDENTIFIER ::= { unisevtModuleRouterType 446 } -- NSQM1FWDFGD1-SecBlade IV
unisevtModuleRt-NSQM1SUPC0                  OBJECT IDENTIFIER ::= { unisevtModuleRouterType 447 } -- SecPath T9000-NSQM1SUPC0
unisevtModuleRt-NSQM1TG4FBA                 OBJECT IDENTIFIER ::= { unisevtModuleRouterType 448 } -- SecPath F1000-NSQM1TG4FBA
unisevtModuleRt-NSQM1GP4FBA                 OBJECT IDENTIFIER ::= { unisevtModuleRouterType 449 } -- SecPath F1000-NSQM1GP4FBA
unisevtModuleRt-NSQM2MPUC0                  OBJECT IDENTIFIER ::= { unisevtModuleRouterType 450 } -- M9008-S FW  NSQM2MPUC0
unisevtModuleRt-NSQM2TGS16SF0               OBJECT IDENTIFIER ::= { unisevtModuleRouterType 451 } -- M9008-S FW  NSQM2TGS16SF0
unisevtModuleRt-NSQM2QGS4SC0                OBJECT IDENTIFIER ::= { unisevtModuleRouterType 452 } -- M9008-S FW  NSQM2QGS4SC0
unisevtModuleRt-NSQM2GP24TSSC0              OBJECT IDENTIFIER ::= { unisevtModuleRouterType 453 } -- M9008-S FW  NSQM2GP24TSSC0
unisevtModuleRt-NSQM2FWDSC0                 OBJECT IDENTIFIER ::= { unisevtModuleRouterType 454 } -- M9008-S FW  NSQM2FWDSC0
unisevtModuleRt-NSQM1ADEDFGA0               OBJECT IDENTIFIER ::= { unisevtModuleRouterType 455 } -- NSQM1ADEDFGA0-SecBlade IV ADE A module
unisevtModuleRt-NSQM2FWDSCA0                OBJECT IDENTIFIER ::= { unisevtModuleRouterType 456 } -- M9000-S FW NSQM2FWDSCA0-SecBlade IV
unisevtModuleRt-NSQM1TGS32QSSG0             OBJECT IDENTIFIER ::= { unisevtModuleRouterType 457 } -- SecPath M9000-NSQM1TGS32QSSG0
unisevtModuleRt-NSQM1GT4PFCA                OBJECT IDENTIFIER ::= { unisevtModuleRouterType 458 } -- 4 Port GigabitEthernet Interface Module
unisevtModuleRt-NSQM1TG8A                   OBJECT IDENTIFIER ::= { unisevtModuleRouterType 459 } -- 8 Port Ten-GigabitEthernet Interface Module
unisevtModuleRt-NSQM1QG2A                   OBJECT IDENTIFIER ::= { unisevtModuleRouterType 460 } -- 2 Port Forty-GigabitEthernet Interface Module
unisevtModuleRt-NSQM1GT8A                   OBJECT IDENTIFIER ::= { unisevtModuleRouterType 461 } -- 8-Port Gigabit Ethernet interface Module
unisevtModuleRt-NSQM1GP8A                   OBJECT IDENTIFIER ::= { unisevtModuleRouterType 462 } -- 8 Port Fabric GigabitEthernet Interface Module
unisevtModuleRt-NSQM1MBFE0                  OBJECT IDENTIFIER ::= { unisevtModuleRouterType 463 } -- SecPath M9008-S  NSQM1MBFE0
unisevtModuleRt-NSQM2MBFD0                  OBJECT IDENTIFIER ::= { unisevtModuleRouterType 464 } -- SecPath M9008-S NSQM2MBFD0
unisevtModuleRt-NSQM2QG2TG8GP40             OBJECT IDENTIFIER ::= { unisevtModuleRouterType 465 } -- SecPath M9008-S  NSQM2QG2TG8GP40
unisevtModuleRt-NSQM2QG4GP40                OBJECT IDENTIFIER ::= { unisevtModuleRouterType 466 } -- SecPath M9008-S  NSQM2QG4GP40
unisevtModuleRt-NSQM2TG16GP40               OBJECT IDENTIFIER ::= { unisevtModuleRouterType 467 } -- SecPath M9008-S  NSQM2TG16GP40
unisevtModuleRt-NSQM1CGQ20                  OBJECT IDENTIFIER ::= { unisevtModuleRouterType 468 } -- SecPath M9008-S  NSQM1CGQ20
unisevtModuleRt-NSQM2FWDFG0                 OBJECT IDENTIFIER ::= { unisevtModuleRouterType 469 } -- M9000-S FW NSQM2FWDFG0-SecBlade IV
unisevtModuleRt-NSQM2TMPUC0                 OBJECT IDENTIFIER ::= { unisevtModuleRouterType 470 } -- SecPath T9000-S-NSQM2TMPUC0
unisevtModuleRt-NSQM2IPSDSCA0               OBJECT IDENTIFIER ::= { unisevtModuleRouterType 471 } -- SecPath T9000-S-NSQM2IPSDSCA0-SecBlade IV
unisevtModuleRt-NSQM2AC1400                 OBJECT IDENTIFIER ::= { unisevtModuleRouterType 472 } -- SecPath M9000-S-NSQM2AC1400
unisevtModuleRt-NSQM2DC1400                 OBJECT IDENTIFIER ::= { unisevtModuleRouterType 473 } -- SecPath M9000-S-NSQM2DC1400
unisevtModuleRt-NSQM1F1KGM0                 OBJECT IDENTIFIER ::= { unisevtModuleRouterType 474} -- F1000 GM Crypto Module
unisevtModuleRt-NSQM1F1KGM0-context         OBJECT IDENTIFIER ::= { unisevtModuleRouterType 475} -- F1000 GM Crypto Module
unisevtModuleRt-NSQM1F5KGM0                 OBJECT IDENTIFIER ::= { unisevtModuleRouterType 476} -- F5000 GM Crypto Module
unisevtModuleRt-NSQM1F5KGM0-context         OBJECT IDENTIFIER ::= { unisevtModuleRouterType 477} -- F5000 GM Crypto Module
unisevtModuleRt-NSQM2QG2GP40                OBJECT IDENTIFIER ::= { unisevtModuleRouterType 478 } -- SecPath M9000-NSQM2QG2GP40
unisevtModuleRt-NSQM2TG8GP40                OBJECT IDENTIFIER ::= { unisevtModuleRouterType 479 } -- SecPath M9000-NSQM2TG8GP40

unisevtModuleRt-NSQM2ADEDSCA0               OBJECT IDENTIFIER ::= { unisevtModuleRouterType 482 } -- M9000-S FW NSQM2ADEDSCA0-SecBlade IV
unisevtModuleRt-NSQM2IPSDSCB0               OBJECT IDENTIFIER ::= { unisevtModuleRouterType 483 } -- M9000-S FW NSQM2IPSDSCB0-SecBlade IV
unisevtModuleRt-NSQM1G4XS4                  OBJECT IDENTIFIER ::= { unisevtModuleRouterType 484 } -- 4-GE Fabric,4-XGE Fabric Interface Module
unisevtModuleRt-NSUM1GT4PFCA                OBJECT IDENTIFIER ::= { unisevtModuleRouterType 485 } -- 4 Port GigabitEthernet Interface Module
unisevtModuleRt-NSUM1TG8A                   OBJECT IDENTIFIER ::= { unisevtModuleRouterType 486 } -- 8 Port Ten-GigabitEthernet Interface Module
unisevtModuleRt-NSUM1QG2A                   OBJECT IDENTIFIER ::= { unisevtModuleRouterType 487 } -- 2 Port Forty-GigabitEthernet Interface Module
unisevtModuleRt-NSUM1GT8A                   OBJECT IDENTIFIER ::= { unisevtModuleRouterType 488 } -- 8-Port Gigabit Ethernet interface Module
unisevtModuleRt-NSUM1GP8A                   OBJECT IDENTIFIER ::= { unisevtModuleRouterType 489 } -- 8 Port Fabric GigabitEthernet Interface Module

unisevtModuleRt-NSQM2MPUD0                  OBJECT IDENTIFIER ::= { unisevtModuleRouterType 491 } -- SecPath M9000-S- NSQM2MPUD0
unisevtModuleRt-NSQM1GMDSCA1                OBJECT IDENTIFIER ::= { unisevtModuleRouterType 492 } -- SecPath M9000-GM- NSQM1GMDSCA1
unisevtModuleRt-NSQM1MPULA                  OBJECT IDENTIFIER ::= { unisevtModuleRouterType 493} -- SecPath F50X0-D NSQM1MPULA
unisevtModuleRt-NSQM1MPULA2                 OBJECT IDENTIFIER ::= { unisevtModuleRouterType 494} -- SecPath F5000-AK515 NSQM1MPULA2
unisevtModuleRt-NSQM1GT8A2                  OBJECT IDENTIFIER ::= { unisevtModuleRouterType 495} -- SecPath F5000-AK515 NSQM1GT8A2
unisevtModuleRt-NSQM1GP4TG4A2               OBJECT IDENTIFIER ::= { unisevtModuleRouterType 496} -- SecPath F5000-AK515 NSQM1GP4TG4A2
unisevtModuleRt-NSQM1GP2TG6A2               OBJECT IDENTIFIER ::= { unisevtModuleRouterType 497} -- SecPath F5000-AK515 NSQM1GP2TG6A2
unisevtModuleRt-NSQM1TG4FBA7                OBJECT IDENTIFIER ::= { unisevtModuleRouterType 498} -- SecPath F1000-AK-NSQM1TG4FBA7

unisevtModuleRt-NSQM1F1KGMB                 OBJECT IDENTIFIER ::= { unisevtModuleRouterType 499} -- F1000 GM Crypto Module
unisevtModuleRt-NSQM1F1KGMC                 OBJECT IDENTIFIER ::= { unisevtModuleRouterType 500} -- F1000 GM Crypto Module
unisevtModuleRt-NSQM1F5KGMC                 OBJECT IDENTIFIER ::= { unisevtModuleRouterType 501} -- F1000 GM Crypto Module
unisevtModuleRt-NSQM5SUP08H0                OBJECT IDENTIFIER ::= { unisevtModuleRouterType 502 } -- SecPath M9000-E8-NSQM5SUP08H0
unisevtModuleRt-NSQM5SUP16C0                OBJECT IDENTIFIER ::= { unisevtModuleRouterType 503 } -- SecPath M9000-E16-NSQM5SUP16C0
unisevtModuleRt-NS-FWEMPA0                  OBJECT IDENTIFIER ::= { unisevtModuleRouterType 504 } -- SecPath M9000-E-NS-FWEMPA0
unisevtModuleRt-NSQM5MBSHA0                 OBJECT IDENTIFIER ::= { unisevtModuleRouterType 505 } -- SecPath M9000-E-NSQM5MBSHA0
unisevtModuleRt-NS-C600-CGQ6A0              OBJECT IDENTIFIER ::= { unisevtModuleRouterType 506 } -- SecPath M9000-E-NS-C600-CGQ6A0
unisevtModuleRt-NS-C300-CGQ2TG16A0          OBJECT IDENTIFIER ::= { unisevtModuleRouterType 507 } -- SecPath M9000-E-NS-C300-CGQ2TG16A0
unisevtModuleRt-NS-C300-TG24A0              OBJECT IDENTIFIER ::= { unisevtModuleRouterType 508 } -- SecPath M9000-E-NS-C300-TG24A0
unisevtModuleRt-NS-C300-QG4TG16A0           OBJECT IDENTIFIER ::= { unisevtModuleRouterType 509 } -- SecPath M9000-E-NS-C300-QG4TG16A0
unisevtModuleRt-NSQM5FAB08A0                OBJECT IDENTIFIER ::= { unisevtModuleRouterType 510 } -- SecPath M9000-E-NSQM5FAB08A0
unisevtModuleRt-NSQM5FAB16A0                OBJECT IDENTIFIER ::= { unisevtModuleRouterType 511 } -- SecPath M9000-E-NSQM5FAB16A0
unisevtModuleRt-NSQM5SL16UA0                OBJECT IDENTIFIER ::= { unisevtModuleRouterType 512 } -- SecPath M9000-E-NSQM5SL16UA0
unisevtModuleRt-NSQM5SL16LA0                OBJECT IDENTIFIER ::= { unisevtModuleRouterType 513 } -- SecPath M9000-E-NSQM5SL16LA0
unisevtModuleRt-NSQM2MPU12E0                OBJECT IDENTIFIER ::= { unisevtModuleRouterType 514 } -- SecPath M9000-S-NSQM2MPU12E0
unisevtModuleRt-NSQM2MBFEA0                 OBJECT IDENTIFIER ::= { unisevtModuleRouterType 515 } -- SecPath M9000-S-NSQM2MBFEA0
unisevtModuleRt-NSQM2AC2500HD               OBJECT IDENTIFIER ::= { unisevtModuleRouterType 516 } -- SecPath M9000-S-NSQM2AC2500HD
unisevtModuleRt-NSQM2DC2500                 OBJECT IDENTIFIER ::= { unisevtModuleRouterType 517 } -- SecPath M9000-S-NSQM2DC2500
unisevtModuleRt-NSQM1HTIMGMG2A              OBJECT IDENTIFIER ::= { unisevtModuleRouterType 518 } -- F5080 GM Crypto Module
unisevtModuleRt-NSQM1HTIMGMG2B              OBJECT IDENTIFIER ::= { unisevtModuleRouterType 519 } -- F5080-D GM Crypto Module
unisevtModuleRt-NSQM2V6DSCA0                OBJECT IDENTIFIER ::= { unisevtModuleRouterType 520 } -- SecPath M9000-S-6GW-NSQM2V6DSCA0
unisevtModuleRt-NSQM1AFC2000GDFGA0          OBJECT IDENTIFIER ::= { unisevtModuleRouterType 521 } -- SecPath NSQM1AFC2000GDFGA0
unisevtModuleRt-NSQM2AFC2000GDFGA0          OBJECT IDENTIFIER ::= { unisevtModuleRouterType 522 } -- SecPath NSQM2AFC2000GDFGA0
unisevtModuleRt-NSQM1FWDFGD1-Z              OBJECT IDENTIFIER ::= { unisevtModuleRouterType 523 } -- SecPath NSQM1FWDFGD1
unisevtModuleRt-NSQM1FAB12D0                OBJECT IDENTIFIER ::= { unisevtModuleRouterType 524 } -- SecPath NSQM1FAB12D0
unisevtModuleRt-NSQM1MBFEA0                 OBJECT IDENTIFIER ::= { unisevtModuleRouterType 525 } -- SecPath NSQM1MBFEA0
unisevtModuleRt-NSQM2TG16GP40-Z             OBJECT IDENTIFIER ::= { unisevtModuleRouterType 526 } -- SecPath NSQM2TG16GP40
unisevtModuleRt-NSQM2QG4GP40-Z              OBJECT IDENTIFIER ::= { unisevtModuleRouterType 527 } -- SecPath NSQM2QG4GP40
unisevtModuleRt-NSQM1CGQ20-Z                OBJECT IDENTIFIER ::= { unisevtModuleRouterType 528 } -- SecPath NSQM1CGQ20
unisevtModuleRt-NSQM1TGS32QSSG0-Z           OBJECT IDENTIFIER ::= { unisevtModuleRouterType 529 } -- SecPath NSQM1TGS32QSSG0
unisevtModuleRt-NSQM1AFC2000GDFGA0-Z        OBJECT IDENTIFIER ::= { unisevtModuleRouterType 530 } -- SecPath NSQM1AFC2000GDFGA0
unisevtModuleRt-NSQM5AIASKA1                OBJECT IDENTIFIER ::= { unisevtModuleRouterType 531 } -- SecPath M9000-AI-E- NSQM5AIASKA1
unisevtModuleRt-NSQM1FWEFGA0                OBJECT IDENTIFIER ::= { unisevtModuleRouterType 532 } -- SecPath M9000-NSQM1FMEFGA0
unisevtModuleRt-NS-ADEEMPA0                 OBJECT IDENTIFIER ::= { unisevtModuleRouterType 533 } -- SecPath M9000-AD-NSQM6ADEEMPA0-SecBlade V
unisevtModuleRt-NSQM2QG2TG8A0               OBJECT IDENTIFIER ::= { unisevtModuleRouterType 534 } -- SecPath M9000-AD-NSQM2QG2TG8A0
unisevtModuleRt-NS-ADEEMPB0                 OBJECT IDENTIFIER ::= { unisevtModuleRouterType 535 } -- SecPath M9000-AD-NSQM6ADEEMPB0-SecBlade V
unisevtModuleRt-NSQM2TG16A0                 OBJECT IDENTIFIER ::= { unisevtModuleRouterType 536 } -- SecPath M9000-AD-NSQM2TG16A0
unisevtModuleRt-NSQM6SUP04A0                OBJECT IDENTIFIER ::= { unisevtModuleRouterType 537 } -- SecPath M9000-AD-NSQM6SUP04A0
unisevtModuleRt-NSQM2QG4A0                  OBJECT IDENTIFIER ::= { unisevtModuleRouterType 538 } -- SecPath M9000-AD-NSQM2QG4A0
unisevtModuleRt-NSQM1SUPD0                  OBJECT IDENTIFIER ::= { unisevtModuleRouterType 539 } -- SecPath M9000-NSQM1SUPD0
unisevtModuleRt-NSQM1FAB08E0                OBJECT IDENTIFIER ::= { unisevtModuleRouterType 540 } -- SecPath M9016-V-NSQM1FAB08E0
unisevtModuleRt-NSQM1CGQ4TG24SHA0           OBJECT IDENTIFIER ::= { unisevtModuleRouterType 541 } -- SecPath M9000-NSQM1CGQ4TG24SHA0
unisevtModuleRt-NSQM2MPUF0                  OBJECT IDENTIFIER ::= { unisevtModuleRouterType 542 } -- SecPath M9000-S-V-NSQM2MPUF0
unisevtModuleRt-NSQM2FWDFGD0                OBJECT IDENTIFIER ::= { unisevtModuleRouterType 543 } -- SecPath M9000-S-V-NSQM2FWDFGD0-SecBlade IV
unisevtModuleRt-NSQM2MBFDB0                 OBJECT IDENTIFIER ::= { unisevtModuleRouterType 544 } -- SecPath M9000-S-V-NSQM2MBFDB0
unisevtModuleRt-NSQM2QG2TG8GP4B0            OBJECT IDENTIFIER ::= { unisevtModuleRouterType 545 } -- SecPath M9000系列-NSQM2QG2TG8GP4B0
unisevtModuleRt-NSQM2FAN08B                 OBJECT IDENTIFIER ::= { unisevtModuleRouterType 546 } -- SecPath M9000-S-V-NSQM2FAN08B
unisevtModuleRt-NSQM5TSUP08A0               OBJECT IDENTIFIER ::= { unisevtModuleRouterType 547 } -- SecPath T9000-E8-NSQM5TSUP08A0
unisevtModuleRt-NSQM5TIPSEMPA0              OBJECT IDENTIFIER ::= { unisevtModuleRouterType 548 } -- SecPath T9000-E-NS-IPSEMPA0
unisevtModuleRt-NSQM5AIASKB1                OBJECT IDENTIFIER ::= { unisevtModuleRouterType 549 } -- SecPath M9000-AI-E-NSQM5AIASKB1
unisevtModuleRt-NSQM1G4XS4-Z                OBJECT IDENTIFIER ::= { unisevtModuleRouterType 550 } -- 4-GE Fabric,4-XGE Fabric Interface Module
unisevtModuleRt-NSQM5TIPSEMPB0              OBJECT IDENTIFIER ::= { unisevtModuleRouterType 551 } -- SecPath T9000-E-NS-IPSEMPB0
unisevtModuleRt-NSQM5SUP04A1                OBJECT IDENTIFIER ::= { unisevtModuleRouterType 552 } -- SecPath M9000-E-NSQM5SUP04A1
unisevtModuleRt-NS-FWEMPB1                  OBJECT IDENTIFIER ::= { unisevtModuleRouterType 553 } -- SecPath M9000-E-NSQM5FWEMPB1
unisevtModuleRt-NS-AFC2000EMPB1             OBJECT IDENTIFIER ::= { unisevtModuleRouterType 554 } -- SecPath M9000-E-NSQM5AFC2000EMPB1
unisevtModuleRt-NS-AFC2000EMPA1             OBJECT IDENTIFIER ::= { unisevtModuleRouterType 555 } -- SecPath M9000-E-NSQM5AFC2000EMPA1
unisevtModuleRt-NS-ADEEMPC0                 OBJECT IDENTIFIER ::= { unisevtModuleRouterType 556 } -- SecPath M9000-AD-NSQM6ADEEMPC0-SecBlade V
unisevtModuleRt-NSQM1CGQ6SH0                OBJECT IDENTIFIER ::= { unisevtModuleRouterType 557 } -- H3C SecPath NSQM1CGQ6SH0
-- 600 to 799 reserved for voice router--
unisevtModuleRt-VG-8fxs                     OBJECT IDENTIFIER ::= { unisevtModuleRouterType 600 } -- 8 Port Foreign Exchange Station module
unisevtModuleRt-VG-24fxs                    OBJECT IDENTIFIER ::= { unisevtModuleRouterType 601 } -- 24 Port Foreign Exchange Station module
unisevtModuleRt-VG-24fxs24fxo               OBJECT IDENTIFIER ::= { unisevtModuleRouterType 602 } -- 24 Port Foreign Exchange Station and 24 Port Foreign Exchange Office module
unisevtModuleRt-VG-MPU                      OBJECT IDENTIFIER ::= { unisevtModuleRouterType 603 } -- Media Processing Unit
unisevtModuleRt-MIM-VCX-CONNECT-P-3C        OBJECT IDENTIFIER ::= { unisevtModuleRouterType 604 } -- MIM VCX Connect Primary module
unisevtModuleRt-MIM-VCX-CONNECT-S-3C        OBJECT IDENTIFIER ::= { unisevtModuleRouterType 605 } -- MIM VCX Connect Secondary module
unisevtModuleRt-MIM-VCX-3C                  OBJECT IDENTIFIER ::= { unisevtModuleRouterType 606 } -- MIM VCX Enterprise module
unisevtModuleRt-VNIC-VMXNET3                OBJECT IDENTIFIER ::= { unisevtModuleRouterType 607 } -- 1 Port Gigabit Ethernet interface virtual VMXNET3 module
unisevtModuleRt-VNIC-E1000                  OBJECT IDENTIFIER ::= { unisevtModuleRouterType 608 } -- 1 Port Gigabit Ethernet interface virtual E1000 module
unisevtModuleRt-VNIC-VIRTIO                 OBJECT IDENTIFIER ::= { unisevtModuleRouterType 609 } -- 1 Port Gigabit Ethernet interface virtual VIRTIO module
unisevtModuleRt-VNIC-RTL8139                OBJECT IDENTIFIER ::= { unisevtModuleRouterType 610 } -- 1 Port Gigabit Ethernet interface virtual RTL8139 module
unisevtModuleRt-VNIC-IXGBEVF                OBJECT IDENTIFIER ::= { unisevtModuleRouterType 611 } -- 1 Port Ten-Gigabit Ethernet interface virtual IXGBEVF module
unisevtModuleRt-IXGBE-2XGE                  OBJECT IDENTIFIER ::= { unisevtModuleRouterType 612 } -- 2 Port Ten-Gigabit Ethernet interface IXGBE module
unisevtModuleRt-TG3-4GE                     OBJECT IDENTIFIER ::= { unisevtModuleRouterType 613 } -- 4 Port Gigabit Ethernet interface TG3 module
unisevtModuleRt-MPUV16                      OBJECT IDENTIFIER ::= { unisevtModuleRouterType 614 } -- Main Processing Unit over virtual machine
unisevtModuleRt-MPUP6                       OBJECT IDENTIFIER ::= { unisevtModuleRouterType 615 } -- Main Processing Unit over physical machine
unisevtModuleRt-IGB-1GE                     OBJECT IDENTIFIER ::= { unisevtModuleRouterType 616 } -- 1 Port Gigabit Ethernet interface IGB module
unisevtModuleRt-IGB-2GE                     OBJECT IDENTIFIER ::= { unisevtModuleRouterType 617 } -- 2 Port Gigabit Ethernet interface IGB module
unisevtModuleRt-IGB-4GE                     OBJECT IDENTIFIER ::= { unisevtModuleRouterType 618 } -- 4 Port Gigabit Ethernet interface IGB module
unisevtModuleRt-VLNS1000                    OBJECT IDENTIFIER ::= { unisevtModuleRouterType 619 } -- Virtual L2TP Network Server over virtual machine
unisevtModuleRt-VLNS2000                    OBJECT IDENTIFIER ::= { unisevtModuleRouterType 620 } -- Virtual L2TP Network Server over physical machine
unisevtModuleRt-NS-MIM-GP4A2                OBJECT IDENTIFIER ::= { unisevtModuleRouterType 621 } -- 4 Port GigabitEthernet Interface Module
unisevtModuleRt-NS-MIM-GT4PFCA2             OBJECT IDENTIFIER ::= { unisevtModuleRouterType 622 } -- 4 Port GigabitEthernet Interface Module
unisevtModuleRt-NS-NIM-TG6A2                OBJECT IDENTIFIER ::= { unisevtModuleRouterType 623 } -- 6 Port Ten-GigabitEthernet Interface Module
unisevtModuleRt-NS-SIM-GT4PFCA2             OBJECT IDENTIFIER ::= { unisevtModuleRouterType 624 } -- 4 Port GigabitEthernet Interface Module
unisevtModuleRt-NS-NIM-TG6A-Z               OBJECT IDENTIFIER ::= { unisevtModuleRouterType 625 } -- 6 Port Ten-GigabitEthernet Interface Module

--
-- 800 to 999 reserved for normal routers part II
--
unisevtModuleRt-SIC-4GSW                    OBJECT IDENTIFIER ::= { unisevtModuleRouterType 800 } -- 4-Port 10M/100M/1000MBASE-T Ethernet L2 Switch Interface SIC-Module
unisevtModuleRt-SIC-4GSWP                   OBJECT IDENTIFIER ::= { unisevtModuleRouterType 801 } -- 4-Port 10M/100M/1000MBASE-T(WITH POE) Ethernet L2 Switch Interface SIC-Module
unisevtModuleRt-SIC-1GEC-V2                 OBJECT IDENTIFIER ::= { unisevtModuleRouterType 802 } -- 1-Port Combo Gigabit Ethernet Interface SIC-Module
unisevtModuleRt-4G-LTE-ATT                  OBJECT IDENTIFIER ::= { unisevtModuleRouterType 803 } -- 1 Port 4G-LTE-ATT-Cellular Interface Adapter Card
unisevtModuleRt-4G-TD-LTE                   OBJECT IDENTIFIER ::= { unisevtModuleRouterType 804 } -- 1 Port 4G-TD-LTE-Cellular Interface Adapter Card
unisevtModuleRt-FIP-240                     OBJECT IDENTIFIER ::= { unisevtModuleRouterType 805 } -- Flexible Interface Platform 240
unisevtModuleRt-8GBP-V2                     OBJECT IDENTIFIER ::= { unisevtModuleRouterType 806 } -- 8-Port GigaBit Ethernet Optical Interface Module(SFP) V2
unisevtModuleRt-HMIM-CNDE                   OBJECT IDENTIFIER ::= { unisevtModuleRouterType 807 } -- CNDE Crypto Engine HMIM-Module
unisevtModuleRt-4G-LTE-Mobile               OBJECT IDENTIFIER ::= { unisevtModuleRouterType 808 } -- 1 Port 4G-LTE-Mobile-Cellular Interface Adapter Card
unisevtModuleRt-SIC-4G-LTE-M                OBJECT IDENTIFIER ::= { unisevtModuleRouterType 809 } -- 1 Port 4G-LTE/TD-SCDMA/WCDMA Cellular Interface SIC-Module
unisevtModuleRt-CRSE-X3                     OBJECT IDENTIFIER ::= { unisevtModuleRouterType 810 } -- Carrier Route Switch Engine X3
unisevtModuleRt-CFIP-300                    OBJECT IDENTIFIER ::= { unisevtModuleRouterType 811 } -- Carrier Flexible Interface Platform 300
unisevtModuleRt-CFIP-310                    OBJECT IDENTIFIER ::= { unisevtModuleRouterType 812 } -- Carrier Flexible Interface Platform 310
unisevtModuleRt-CSAP-4EXP                   OBJECT IDENTIFIER ::= { unisevtModuleRouterType 813 } -- Carrier 4-Port 10GBASE-R/W Ethernet Optical Interface Module(SFP+)
unisevtModuleRt-RSU                         OBJECT IDENTIFIER ::= { unisevtModuleRouterType 814 } -- Route Switch Unit
unisevtModuleRt-CFIP-610                    OBJECT IDENTIFIER ::= { unisevtModuleRouterType 815 } -- Carrier Flexible Interface Platform 610
unisevtModuleRt-2EXP                        OBJECT IDENTIFIER ::= { unisevtModuleRouterType 816 } -- 2-Port 10GBASE-R/W Ethernet Optical Interface Module(SFP+)
unisevtModuleRt-16GBP                       OBJECT IDENTIFIER ::= { unisevtModuleRouterType 817 } -- 16-Port Gigabit Ethernet Optical Interface Module(SFP)
unisevtModuleRt-CFIP-240                    OBJECT IDENTIFIER ::= { unisevtModuleRouterType 818 } -- Carrier Flexible Interface Platform 240
unisevtModuleRt-RSE-X3                      OBJECT IDENTIFIER ::= { unisevtModuleRouterType 819 } -- Route Switch Engine X3
unisevtModuleRt-SAP-8EXP                    OBJECT IDENTIFIER ::= { unisevtModuleRouterType 820 } -- 8-Port 10GBASE-R/W Ethernet Optical Interface Module(SFP+)
unisevtModuleRt-SAP-16EXP                   OBJECT IDENTIFIER ::= { unisevtModuleRouterType 821 } -- 16-Port 10GBASE-R/W Ethernet Optical Interface Module(SFP+)
unisevtModuleRt-PU1P                        OBJECT IDENTIFIER ::= { unisevtModuleRouterType 822 } -- 1-Port 10G POS/RPR Interface Module(XFP)
unisevtModuleRt-RSU100                      OBJECT IDENTIFIER ::= { unisevtModuleRouterType 823 } -- Router Switch Unit 100
unisevtModuleRt-SAP-2QGP                    OBJECT IDENTIFIER ::= { unisevtModuleRouterType 824 } -- 2-Port 40GBASE Ethernet Optical Interface Module(QSFP+)
unisevtModuleRt-CSFE-X1                     OBJECT IDENTIFIER ::= { unisevtModuleRouterType 825 } -- Carrier Switch Fabric Engine X1
unisevtModuleRt-RIC-4GEE                    OBJECT IDENTIFIER ::= { unisevtModuleRouterType 826 } -- 4-Port 10M/100M/1000MBASE-T Ethernet Interface RIC-Module
unisevtModuleRt-RIC-4GEF                    OBJECT IDENTIFIER ::= { unisevtModuleRouterType 827 } -- 4-Port 1000M Base-F Optical Ethernet Interface RIC-Module
unisevtModuleRt-RIC-8GEE                    OBJECT IDENTIFIER ::= { unisevtModuleRouterType 828 } -- 8-Port 10M/100M/1000MBASE-T Ethernet Interface RIC-Module
unisevtModuleRt-RIC-8GEF                    OBJECT IDENTIFIER ::= { unisevtModuleRouterType 829 } -- 8-Port 1000M Base-F Optical Ethernet Interface RIC-Module
unisevtModuleRt-RIC-1XGEF                   OBJECT IDENTIFIER ::= { unisevtModuleRouterType 830 } -- 1-Port Ten-GigabitEthernet Optical Interface RIC-Module
unisevtModuleRt-HMIM-1E1POS                 OBJECT IDENTIFIER ::= { unisevtModuleRouterType 831 } -- 1 PORT E1 Interface HMIM-Module
unisevtModuleRt-DHMIM-1DM                   OBJECT IDENTIFIER ::= { unisevtModuleRouterType 832 } -- 1 PORT E1 Interface DHMIM-Module
unisevtModuleRt-DHMIM-1E1POS1DM             OBJECT IDENTIFIER ::= { unisevtModuleRouterType 833 } -- 1 PORT E1 Interface DHMIM-Module
unisevtModuleRt-RPE-X3                      OBJECT IDENTIFIER ::= { unisevtModuleRouterType 834 } -- Route Processing Engine X3
unisevtModuleRt-CRPE-X3                     OBJECT IDENTIFIER ::= { unisevtModuleRouterType 835 } -- Carrier Route Processing Engine X3
unisevtModuleRt-SAP-28GE                    OBJECT IDENTIFIER ::= { unisevtModuleRouterType 836 } -- 16-Port SFP and 12-Port Combo GE Module
unisevtModuleRt-SAP-20GE2XP                 OBJECT IDENTIFIER ::= { unisevtModuleRouterType 837 } -- 16-Port SFP 4-Port Combo GE and 2-Port 10GE Module
unisevtModuleRt-SFE-L1                      OBJECT IDENTIFIER ::= { unisevtModuleRouterType 838 } -- Switch Fabric Engine L1
unisevtModuleRt-FIP-640                     OBJECT IDENTIFIER ::= { unisevtModuleRouterType 839 } -- Flexible Interface Platform 640
unisevtModuleRt-HMIM-8GSWF                  OBJECT IDENTIFIER ::= { unisevtModuleRouterType 840 } -- 8-Port 1000M Base-F Optical Ethernet L2 Switch Interface HMIM_Module, including 4 Combo Ports
unisevtModuleRt-HMIM-8E1T1                  OBJECT IDENTIFIER ::= { unisevtModuleRouterType 841 } -- 8-port E1/CE1/T1/CT1/PRI HMIM Module
unisevtModuleRt-HMIM-4E1T1                  OBJECT IDENTIFIER ::= { unisevtModuleRouterType 842 } -- 4-port E1/CE1/T1/CT1/PRI HMIM Module
unisevtModuleRt-HMIM-2E1T1                  OBJECT IDENTIFIER ::= { unisevtModuleRouterType 843 } -- 2-port E1/CE1/T1/CT1/PRI HMIM Module
unisevtModuleRt-HMIM-8E1T1-F                OBJECT IDENTIFIER ::= { unisevtModuleRouterType 844 } -- 8-port E1/T1/Fractional E1/T1 HMIM Module
unisevtModuleRt-HMIM-4E1T1-F                OBJECT IDENTIFIER ::= { unisevtModuleRouterType 845 } -- 4-port E1/T1/Fractional E1/T1 HMIM Module
unisevtModuleRt-HMIM-2E1T1-F                OBJECT IDENTIFIER ::= { unisevtModuleRouterType 846 } -- 2-port E1/T1/Fractional E1/T1 HMIM Module
unisevtModuleRt-SIC-3G-HSPA-V2              OBJECT IDENTIFIER ::= { unisevtModuleRouterType 847 } -- 1 Port HSPA-Cellular Interface SIC-Module V2
unisevtModuleRt-SIC-4GSWF                   OBJECT IDENTIFIER ::= { unisevtModuleRouterType 848 } -- 4-Port 1000M Base-F Optical Ethernet L2 Switch Interface SIC-Module
unisevtModuleRt-SIC-4G-LTE-G-V2             OBJECT IDENTIFIER ::= { unisevtModuleRouterType 849 } -- 1 Port 4G-LTE-G-V2 Cellular Interface SIC-Module
unisevtModuleRt-SIC-4G-LTE-A-V2             OBJECT IDENTIFIER ::= { unisevtModuleRouterType 850 } -- 1 Port 4G-LTE-A-V2 Cellular Interface SIC-Module
unisevtModuleRt-SIC-4G-LTE-V-V2             OBJECT IDENTIFIER ::= { unisevtModuleRouterType 851 } -- 1 Port 4G-LTE-V-V2 Cellular Interface SIC-Module
unisevtModuleRt-MPU60                       OBJECT IDENTIFIER ::= { unisevtModuleRouterType 852 } -- Main Processing Unit 60
unisevtModuleRt-SPU                         OBJECT IDENTIFIER ::= { unisevtModuleRouterType 853 } -- Service Processing Unit
unisevtModuleRt-SIC-1VE1T1                  OBJECT IDENTIFIER ::= { unisevtModuleRouterType 854 } -- 1-Port E1/T1 Voice SIC Module,Domestic&Overseas Version
unisevtModuleRt-CFIP-700                    OBJECT IDENTIFIER ::= { unisevtModuleRouterType 855 } -- Carrier Flexible Interface Platform 700
unisevtModuleRt-HIM-20GBP-H3                OBJECT IDENTIFIER ::= { unisevtModuleRouterType 856 } -- 20-Port Gigabit Ethernet Optical Interface Module(SFP)
unisevtModuleRt-HIM-4EXP-H3                 OBJECT IDENTIFIER ::= { unisevtModuleRouterType 857 } -- 4-Port 10GBASE-R/W Ethernet Optical Interface Module(SFP+)
unisevtModuleRt-HIM-2EXP-H3                 OBJECT IDENTIFIER ::= { unisevtModuleRouterType 858 } -- 2-Port 10GBASE-R/W Ethernet Optical Interface Module(SFP+)
unisevtModuleRt-HIM-8GBE-V3                 OBJECT IDENTIFIER ::= { unisevtModuleRouterType 859 } -- 8-port GigaBit Ethernet Electrical Interface Module
unisevtModuleRt-HIM-4GBE-V3                 OBJECT IDENTIFIER ::= { unisevtModuleRouterType 860 } -- 4-port GigaBit Ethernet Electrical Interface Module
unisevtModuleRt-HIM-8GBP-V3                 OBJECT IDENTIFIER ::= { unisevtModuleRouterType 861 } -- 8-Port GigaBit Ethernet Optical Interface Module(SFP)
unisevtModuleRt-HIM-4GBP-V3                 OBJECT IDENTIFIER ::= { unisevtModuleRouterType 862 } -- 4-Port GigaBit Ethernet Optical Interface Module(SFP)
unisevtModuleRt-SIC-AP                      OBJECT IDENTIFIER ::= { unisevtModuleRouterType 863 } -- 1-Port AP SIC Module,Domestic&Overseas Version
unisevtModuleRt-CR-MPU-04B                  OBJECT IDENTIFIER ::= { unisevtModuleRouterType 864 } -- CR Main Processing Unit B for 04 Chassis
unisevtModuleRt-CR-MPU-16B                  OBJECT IDENTIFIER ::= { unisevtModuleRouterType 865 } -- CR Main Processing Unit B for 08 and 16 Chassis
unisevtModuleRt-CR-MPU-16E                  OBJECT IDENTIFIER ::= { unisevtModuleRouterType 866 } -- CR Main Processing Unit E for 08 and 16 Chassis
unisevtModuleRt-CR-SFU-04D-H                OBJECT IDENTIFIER ::= { unisevtModuleRouterType 867 } -- CR Switching Fabric Unit(HD) for 04 Chassis
unisevtModuleRt-CR-SFU-08C-H                OBJECT IDENTIFIER ::= { unisevtModuleRouterType 868 } -- CR Switching Fabric Unit(HC) for 08 Chassis
unisevtModuleRt-CR-SFU-08D-H                OBJECT IDENTIFIER ::= { unisevtModuleRouterType 869 } -- CR Switching Fabric Unit(HD) for 08 Chassis
unisevtModuleRt-CR-SFU-16B-H                OBJECT IDENTIFIER ::= { unisevtModuleRouterType 870 } -- CR Switching Fabric Unit(HB) for 16 Chassis
unisevtModuleRt-CR-SFU-16C-H                OBJECT IDENTIFIER ::= { unisevtModuleRouterType 871 } -- CR Switching Fabric Unit(HC) for 16 Chassis
unisevtModuleRt-CR-LPU-CQ12                 OBJECT IDENTIFIER ::= { unisevtModuleRouterType 872 } -- CR 12-Port 100G Ethernet Optical Interface Module
unisevtModuleRt-CR-LPU-4004                 OBJECT IDENTIFIER ::= { unisevtModuleRouterType 873 } -- CR Flexible Interface Module 4004
unisevtModuleRt-CR-HIC-PU02                 OBJECT IDENTIFIER ::= { unisevtModuleRouterType 874 } -- CR 2-Port 10G POS Optical Interface Card
unisevtModuleRt-CR-HIC-XP12                 OBJECT IDENTIFIER ::= { unisevtModuleRouterType 875 } -- CR 12-Port 10G Ethernet Optical Interface Card
unisevtModuleRt-CR-HIC-GP12                 OBJECT IDENTIFIER ::= { unisevtModuleRouterType 876 } -- CR 12-Port Gigabit Ethernet Optical Interface Card
unisevtModuleRt-CR-HIC-QQ03                 OBJECT IDENTIFIER ::= { unisevtModuleRouterType 877 } -- CR 3-Port 40G Ethernet Optical Interface Card(QSFP+)
unisevtModuleRt-CR-HIC-CC01                 OBJECT IDENTIFIER ::= { unisevtModuleRouterType 878 } -- CR 1-Port 100G Ethernet Optical Interface Card(CFP2)
unisevtModuleRt-CR-HIC-CP01                 OBJECT IDENTIFIER ::= { unisevtModuleRouterType 879 } -- CR 1-Port 100G Ethernet Optical Interface Card(CFP)
unisevtModuleRt-CR-MPU-16C                  OBJECT IDENTIFIER ::= { unisevtModuleRouterType 880 } -- CR Main Processing Unit C for 08 and 16 Chassis
unisevtModuleRt-MPU-100-X1                  OBJECT IDENTIFIER ::= { unisevtModuleRouterType 881 } -- Main Processing Unit 100-X1
unisevtModuleRt-SPU-100-X1                  OBJECT IDENTIFIER ::= { unisevtModuleRouterType 882 } -- Service Processing Unit 100-X1
unisevtModuleRt-SPU-200-X1                  OBJECT IDENTIFIER ::= { unisevtModuleRouterType 883 } -- Service Processing Unit 200-X1
unisevtModuleRt-SPU-400-X1                  OBJECT IDENTIFIER ::= { unisevtModuleRouterType 884 } -- Service Processing Unit 400-X1
unisevtModuleRt-HIM-10GB2EXP-H3             OBJECT IDENTIFIER ::= { unisevtModuleRouterType 885 } -- 10-port 1000BASE-X Ethernet Optical Interface(SFP)+2-port 10GBASE-R/W Ethernet Optical Interface Card(SFP+)
unisevtModuleRt-HIM-11GB1EXP-H3             OBJECT IDENTIFIER ::= { unisevtModuleRouterType 886 } -- 11-port 1000BASE-X Ethernet Optical Interface(SFP)+1-port 10GBASE-R/W Ethernet Optical Interface Card(SFP+)
unisevtModuleRt-HMIM-1E3T3                  OBJECT IDENTIFIER ::= { unisevtModuleRouterType 887 } -- 1-port T3 HMIM-Module
unisevtModuleRt-SIC-4G-CNDE                 OBJECT IDENTIFIER ::= { unisevtModuleRouterType 888 } -- 1-port 4G LTE and CNDE SIC Module
unisevtModuleRt-SIC-D4G-CNDE                OBJECT IDENTIFIER ::= { unisevtModuleRouterType 889 } -- 2-port 4G LTE and CNDE SIC Module
unisevtModuleRt-CR-LPU-CC08                 OBJECT IDENTIFIER ::= { unisevtModuleRouterType 890 } -- CR 8-Port 100G Ethernet Optical Interface Module
unisevtModuleRt-CR-LPU-2002                 OBJECT IDENTIFIER ::= { unisevtModuleRouterType 891 } -- CR Flexible Interface Module 2002
unisevtModuleRt-CR-LPU-XP20CC02             OBJECT IDENTIFIER ::= { unisevtModuleRouterType 892 } -- CR 20-Port 10G Ethernet Optical Interface Module and 2-Port 100G Ethernet Optical Interface Module
unisevtModuleRt-CR-LPU-XP40                 OBJECT IDENTIFIER ::= { unisevtModuleRouterType 893 } -- CR 40-Port 10G Ethernet Optical Interface Module
unisevtModuleRt-CR-LPU-CC04                 OBJECT IDENTIFIER ::= { unisevtModuleRouterType 894 } -- CR 4-Port 100G Ethernet Optical Interface Module
unisevtModuleRt-FIP-680                     OBJECT IDENTIFIER ::= { unisevtModuleRouterType 895 } -- Service Processing Unit(680)
unisevtModuleRt-MIC-XP4L                    OBJECT IDENTIFIER ::= { unisevtModuleRouterType 896 } -- 4-port 10GBASE-R/W Ethernet Optical Interface Card(SFP+,LC)
unisevtModuleRt-MIM-1T3-V2                  OBJECT IDENTIFIER ::= { unisevtModuleRouterType 897 } -- 1-port T3 Interface Card
unisevtModuleRt-MIC-GP4L                    OBJECT IDENTIFIER ::= { unisevtModuleRouterType 898 } -- 4-Port 1000BASE-X COMBO Interface Card,(SFP,LC)
unisevtModuleRt-MIC-GP8L                    OBJECT IDENTIFIER ::= { unisevtModuleRouterType 899 } -- 8-Port 1000BASE-X Optical Interface Card,(SFP,LC)
unisevtModuleRt-CR-19K-MPU-20A              OBJECT IDENTIFIER ::= { unisevtModuleRouterType 900 } -- CR Main Processing Unit A for 19 Chassis
unisevtModuleRt-CR-19K-MPU-20B              OBJECT IDENTIFIER ::= { unisevtModuleRouterType 901 } -- CR Main Processing Unit B for 19 Chassis
unisevtModuleRt-CR-19K-SFU-20C              OBJECT IDENTIFIER ::= { unisevtModuleRouterType 902 } -- CR Switching Fabric Unit(HC) for 20 Chassis
unisevtModuleRt-CR-19K-MSFU-20B             OBJECT IDENTIFIER ::= { unisevtModuleRouterType 903 } -- CR Multi-Switching Fabric Unit(HB) for 20 Chassis
unisevtModuleRt-CR-19K-MSFU-20C             OBJECT IDENTIFIER ::= { unisevtModuleRouterType 904 } -- CR Multi-Switching Fabric Unit(HC) for 20 Chassis
unisevtModuleRt-CR-19K-MCCU-24A             OBJECT IDENTIFIER ::= { unisevtModuleRouterType 905 } -- CR Multi-Control Connection A Unit for 24 Chassis
unisevtModuleRt-CR-19K-MFCU-24A             OBJECT IDENTIFIER ::= { unisevtModuleRouterType 906 } -- CR Multi-Fabric Connection A Unit for 24 Chassis
unisevtModuleRt-RIC-8E1                     OBJECT IDENTIFIER ::= { unisevtModuleRouterType 907 } -- 8-Port E1/CE1/PRI Interface RIC-Module
unisevtModuleRt-RIC-1XGEF4GEF               OBJECT IDENTIFIER ::= { unisevtModuleRouterType 908 } -- 1-Port 10M/100M/1000M/10000MBASE-F and 4-Port 10M/100M/1000MBASE-F Ethernet Interface 1XGEF4GEFModule
unisevtModuleRt-RIC-TU01A                   OBJECT IDENTIFIER ::= { unisevtModuleRouterType 909 } -- 1-Port 10M/100M/1000M/10000MBASE-F and 4-Port 10M/100M/1000MBASE-F Ethernet Interface TU01AModule
unisevtModuleRt-SPE-S1                      OBJECT IDENTIFIER ::= { unisevtModuleRouterType 910 } -- Service Processing Engine S1
unisevtModuleRt-SPE-S3                      OBJECT IDENTIFIER ::= { unisevtModuleRouterType 911 } -- Service Processing Engine S3
unisevtModuleRt-SPU-600-X1                  OBJECT IDENTIFIER ::= { unisevtModuleRouterType 912 } -- Service Processing Unit 600-X1
unisevtModuleRt-RIC-CP08                    OBJECT IDENTIFIER ::= { unisevtModuleRouterType 913 } -- 8-Port E1/CE1/PRI Interface RIC-Module
unisevtModuleRt-MIC-SP4L                    OBJECT IDENTIFIER ::= { unisevtModuleRouterType 914 } -- 4-Port OC-3/STM-1 POS/CPOS/ATM or 1-Port OC-12/STM-4 POS/ATM Optical Interface Card,(SFP,LC)
unisevtModuleRt-MIC-ET16L                   OBJECT IDENTIFIER ::= { unisevtModuleRouterType 915 } -- 16-Port E1/T1 Electrical Interface Card
unisevtModuleRt-MIC-CLP4L                   OBJECT IDENTIFIER ::= { unisevtModuleRouterType 916 } -- 4-Port OC-3/STM-1 CPOS/POS Optical Interface Card,(SFP,LC)
unisevtModuleRt-MIC-CLP2L                   OBJECT IDENTIFIER ::= { unisevtModuleRouterType 917 } -- 2-Port OC-3/STM-1 CPOS/POS Optical Interface Card,(SFP,LC)
unisevtModuleRt-MIC-SP8L                    OBJECT IDENTIFIER ::= { unisevtModuleRouterType 918 } -- 8-Port OC-3c/STM-1c POS Optical Interface Card
unisevtModuleRt-HMIM-8EM                    OBJECT IDENTIFIER ::= { unisevtModuleRouterType 919 } -- 8-Port E&M Interface HMIM-Module
unisevtModuleRt-SFU                         OBJECT IDENTIFIER ::= { unisevtModuleRouterType 920 } -- Switching Fabric Unit
unisevtModuleRt-SFE-L2                      OBJECT IDENTIFIER ::= { unisevtModuleRouterType 921 } -- Switching Fabric Engine L2
unisevtModuleRt-SFU-UNFIXED                 OBJECT IDENTIFIER ::= { unisevtModuleRouterType 922 } -- Unfixed Switching Fabric Unit
unisevtModuleRt-FIP-380                     OBJECT IDENTIFIER ::= { unisevtModuleRouterType 923 } -- Flexible Interface Platform-380
unisevtModuleRt-CR-19K-MPU-08A              OBJECT IDENTIFIER ::= { unisevtModuleRouterType 924 } -- CR Main Processing Unit A for 08 Chassis
unisevtModuleRt-CR-19K-MPU-16A              OBJECT IDENTIFIER ::= { unisevtModuleRouterType 925 } -- CR Main Processing Unit A for 16 Chassis
unisevtModuleRt-CR-19K-SFU-08C              OBJECT IDENTIFIER ::= { unisevtModuleRouterType 926 } -- CR Switching Fabric Unit(HC) for 08 Chassis
unisevtModuleRt-CR-19K-SFU-16C              OBJECT IDENTIFIER ::= { unisevtModuleRouterType 927 } -- CR Switching Fabric Unit(HC) for 16 Chassis
unisevtModuleRt-CR-19K-LPU-CC08             OBJECT IDENTIFIER ::= { unisevtModuleRouterType 928 } -- CR 8-Port 100G Ethernet Optical Interface Module
unisevtModuleRt-CR-19K-LPU-2002             OBJECT IDENTIFIER ::= { unisevtModuleRouterType 929 } -- CR Flexible Interface Module 2002
unisevtModuleRt-CR-19K-LPU-XP20CC02         OBJECT IDENTIFIER ::= { unisevtModuleRouterType 930 } -- CR 20-Port 10G Ethernet Optical Interface Module and 2-Port 100G Ethernet Optical Interface Module
unisevtModuleRt-CR-19K-LPU-XP40             OBJECT IDENTIFIER ::= { unisevtModuleRouterType 931 } -- CR 40-Port 10G Ethernet Optical Interface Module
unisevtModuleRt-CR-19K-LPU-CC04             OBJECT IDENTIFIER ::= { unisevtModuleRouterType 932 } -- CR 4-Port 100G Ethernet Optical Interface Module
unisevtModuleRt-CR-19K-LPU-CQ12             OBJECT IDENTIFIER ::= { unisevtModuleRouterType 933 } -- CR 12-Port 100G Ethernet Optical Interface Module
unisevtModuleRt-MIC-X-GT8                   OBJECT IDENTIFIER ::= { unisevtModuleRouterType 934 } -- 8-Port 10/100/1000BASE-T Electronic Multi-functional Interface Card
unisevtModuleRt-MIC-X-GP4GT4                OBJECT IDENTIFIER ::= { unisevtModuleRouterType 935 } -- 4-Port 10/100/1000BASE-T Electronic + 4-Port 1000BASE-X Optical Multi-functional Interface Card
unisevtModuleRt-MIC-X-GP10                  OBJECT IDENTIFIER ::= { unisevtModuleRouterType 936 } -- 10-Port 1000BASE-X Optical Multi-functional Interface Card
unisevtModuleRt-MIC-X-GP8                   OBJECT IDENTIFIER ::= { unisevtModuleRouterType 937 } -- 8-Port 1000BASE-X Optical Multi-functional Interface Card
unisevtModuleRt-CR-19K-LPU-4004             OBJECT IDENTIFIER ::= { unisevtModuleRouterType 938 } -- CR Flexible Interface Module 4004
unisevtModuleRt-FIP-260                     OBJECT IDENTIFIER ::= { unisevtModuleRouterType 939 } -- Flexible Interface Platform-260
unisevtModuleRt-CR-LPU-XP72                 OBJECT IDENTIFIER ::= { unisevtModuleRouterType 940 } -- CR 72-Port 10G Ethernet Optical Interface Module
unisevtModuleRt-CR-LPU-XP48                 OBJECT IDENTIFIER ::= { unisevtModuleRouterType 941 } -- CR 48-Port 10G Ethernet Optical Interface Module
unisevtModuleRt-CR-LPU-CC04B                OBJECT IDENTIFIER ::= { unisevtModuleRouterType 942 } -- CR 4-Port 100G Ethernet Optical Interface Module
unisevtModuleRt-CR-LPU-2002B                OBJECT IDENTIFIER ::= { unisevtModuleRouterType 943 } -- CR Flexible Interface Module 2002B
unisevtModuleRt-LPU-1001B                   OBJECT IDENTIFIER ::= { unisevtModuleRouterType 944 } -- CR Flexible Interface Module 1001B
unisevtModuleRt-CR-19K-MSFU-08A             OBJECT IDENTIFIER ::= { unisevtModuleRouterType 945 } -- CR Multi-Switching Fabric Unit for 8 Chassis
unisevtModuleRt-Sic-AP220                   OBJECT IDENTIFIER ::= { unisevtModuleRouterType 946 } -- SIC-AP220 External Antennas 3 Streams Dual Radio
unisevtModuleRt-FIP-660                     OBJECT IDENTIFIER ::= { unisevtModuleRouterType 947 } -- Flexible Interface Platform 660
unisevtModuleRT-MIC-X-ET16                  OBJECT IDENTIFIER ::= { unisevtModuleRouterType 948 } -- 16-Port E1/T1 Electrical Interface Card,(RJ45)
unisevtModuleRT-MIC-X-SP4                   OBJECT IDENTIFIER ::= { unisevtModuleRouterType 949 } -- 4-Port OC-3/STM-1 POS or 1-Port OC-12/STM-4 POS Optical Interface Card,(SFP)
unisevtModuleRT-MIC-X-SP8                   OBJECT IDENTIFIER ::= { unisevtModuleRouterType 950 } -- 8-Port OC-3c/STM-1c POS Optical Interface Card,(SFP)
unisevtModuleRT-MIC-X-CLP2                  OBJECT IDENTIFIER ::= { unisevtModuleRouterType 951 } -- 2-Port OC-3/STM-1 CPOS Optical Interface Card,(SFP)
unisevtModuleRT-MIC-X-CLP4                  OBJECT IDENTIFIER ::= { unisevtModuleRouterType 952 } -- 4-Port OC-3/STM-1 CPOS Optical Interface Card,(SFP)
unisevtModuleRt-SPU-300                     OBJECT IDENTIFIER ::= { unisevtModuleRouterType 953 } -- ICG Service Processing Unit 300(10GE Combo)
unisevtModuleRt-CR-19K-LPU-XP72             OBJECT IDENTIFIER ::= { unisevtModuleRouterType 954 } -- 72-Port 10G Ethernet Optical Interface Module for 19 chassis
unisevtModuleRt-CR-19K-LPU-XP48             OBJECT IDENTIFIER ::= { unisevtModuleRouterType 955 } -- 48-Port 10G Ethernet Optical Interface Module for 19 chassis
unisevtModuleRt-CR-19K-LPU-2002B            OBJECT IDENTIFIER ::= { unisevtModuleRouterType 956 } -- Flexible Interface Module 2002B for 19 chassis
unisevtModuleRt-CR-19K-LPU-CC04B            OBJECT IDENTIFIER ::= { unisevtModuleRouterType 957 } -- 4-Port 100G Ethernet Optical Interface Module for 19 chassis
unisevtModuleRt-CR-19K-MPU-16B              OBJECT IDENTIFIER ::= { unisevtModuleRouterType 958 } -- Main Processing Unit B for 19016 Chassis
unisevtModuleRT-RPE-X5                      OBJECT IDENTIFIER ::= { unisevtModuleRouterType 959 } -- Route Processing Engine X5
unisevtModuleRT-RPE-X5E                     OBJECT IDENTIFIER ::= { unisevtModuleRouterType 960 } -- Route Processing Engine X5E
unisevtModuleRt-CR-HIC-PS04                 OBJECT IDENTIFIER ::= { unisevtModuleRouterType 961 } -- CR 4-Port non-channelized POS(155M/622M/2.5G) Interface Card,Sub Module
unisevtModuleRt-CR-HIC-PL08                 OBJECT IDENTIFIER ::= { unisevtModuleRouterType 962 } -- CR 8-Port non-channelized POS(155M) Interface Card,Sub Module
unisevtModuleRT-MIC-X-XP2                   OBJECT IDENTIFIER ::= { unisevtModuleRouterType 963 } -- 2-Port 1000BASE-R-SFP+ Optical Multi-functional Interface Card
unisevtModuleRT-MIC-X-XP4                   OBJECT IDENTIFIER ::= { unisevtModuleRouterType 964 } -- 4-Port 1000BASE-R-SFP+ Optical Multi-functional Interface Card
unisevtModuleRT-MIC-X-XP4W                  OBJECT IDENTIFIER ::= { unisevtModuleRouterType 965 } -- 4-Port 1000BASE-R-SFP+ Optical Multi-functional Interface Card(Support LAN/WAN mode)
unisevtModuleRT-SIC-CNDE-SJK                OBJECT IDENTIFIER ::= { unisevtModuleRouterType 966 } -- SJK CNDE SIC Module
unisevtModuleRT-SIC-4G-CNDE-SJK             OBJECT IDENTIFIER ::= { unisevtModuleRouterType 967 } -- SJK 4G LTE and CNDE SIC Module
unisevtModuleRT-SIC-D4G-CNDE-SJK            OBJECT IDENTIFIER ::= { unisevtModuleRouterType 968 } -- SJK Double 4G LTE and CNDE SIC Module
unisevtModuleRt-CR-19K-MSFU-16A             OBJECT IDENTIFIER ::= { unisevtModuleRouterType 969 } -- CR Multi-Switching Fabric Unit(A) for 16 Chassis
unisevtModuleRT-HMIM-CNDE-SJK               OBJECT IDENTIFIER ::= { unisevtModuleRouterType 970 } -- SJK CNDE HMIM Module
unisevtModuleRT-MIBIF-MINI-CNDE-SJK         OBJECT IDENTIFIER ::= { unisevtModuleRouterType 971 } -- SJK MINI CNDE Module
unisevtModuleRT-SIC-AP320-FIT               OBJECT IDENTIFIER ::= { unisevtModuleRouterType 972 } -- AP320 FIT SIC Module
unisevtModuleRT-SAP-XP4GE32                 OBJECT IDENTIFIER ::= { unisevtModuleRouterType 973 } -- 4-Port 10G and 32-Port G Ethernet Optical Interface Module(SFP+)
unisevtModuleRT-SIC-4E1-F-Z                 OBJECT IDENTIFIER ::= { unisevtModuleRouterType 974 } -- 4-Port Fractional E1 Interface SIC-Module
unisevtModuleRT-HRIC-CLGQ2                  OBJECT IDENTIFIER ::= { unisevtModuleRouterType 975 } -- 1-Port 50-100-GigabitEthernet and 1-Port 50 GigabitEthernet Optical Interface HRIC-Module
unisevtModuleRT-HRIC-YGS4                   OBJECT IDENTIFIER ::= { unisevtModuleRouterType 976 } -- 4-Port 25-GigabitEthernet Optical Interface HRIC-Module
unisevtModuleRT-HRIC-XP8                    OBJECT IDENTIFIER ::= { unisevtModuleRouterType 977 } -- 8-Port Ten-GigabitEthernet Optical Interface HRIC-Module
unisevtModuleRT-HRIC-GP8                    OBJECT IDENTIFIER ::= { unisevtModuleRouterType 978 } -- 8-Port 1000M Base-F Optical Ethernet Interface HRIC-Module
unisevtModuleRT-HRIC-GT8                    OBJECT IDENTIFIER ::= { unisevtModuleRouterType 979 } -- 8-Port 1000M Base-T Ethernet Interface HRIC-Module

unisevtModuleRT-MIC-X-CNDE-SJK             OBJECT IDENTIFIER ::= { unisevtModuleRouterType 980 } -- SJK CNDE MIC-X Module
unisevtModuleRt-CR-19K-LPU-CQ18            OBJECT IDENTIFIER ::= { unisevtModuleRouterType 981 }
unisevtModuleRt-CR-19K-LPU-CQ12B           OBJECT IDENTIFIER ::= { unisevtModuleRouterType 982 }
unisevtModuleRt-CR-19K-LPU-SP              OBJECT IDENTIFIER ::= { unisevtModuleRouterType 983 }
unisevtModuleRt-CR-HIC-CQ01                OBJECT IDENTIFIER ::= { unisevtModuleRouterType 984 }
unisevtModuleRt-NS-NIM-TG6A                OBJECT IDENTIFIER ::= { unisevtModuleRouterType 985 }
unisevtModuleRtNS-NIM-TG4A3                OBJECT IDENTIFIER ::= { unisevtModuleRouterType 986 }
unisevtModuleRtNSQM2CGQ20                  OBJECT IDENTIFIER ::= { unisevtModuleRouterType 987 }
unisevtModuleRtNSQM2FWDFGC0                OBJECT IDENTIFIER ::= { unisevtModuleRouterType 988 }
unisevtModuleRtNSQM2FWDFGB0                OBJECT IDENTIFIER ::= { unisevtModuleRouterType 989 }
unisevtModuleRt-NS-TIM-TG8A2               OBJECT IDENTIFIER ::= { unisevtModuleRouterType 990 }
unisevtModuleRtNSQM5MBSHA1                 OBJECT IDENTIFIER ::= { unisevtModuleRouterType 991 }
unisevtModuleRtNS-C600-CGQ6A1              OBJECT IDENTIFIER ::= { unisevtModuleRouterType 992 }
unisevtModuleRtNSQM5SUP08A1                OBJECT IDENTIFIER ::= { unisevtModuleRouterType 993 }
unisevtModuleRtNSQ1M9ESL16UA0              OBJECT IDENTIFIER ::= { unisevtModuleRouterType 994 }
unisevtModuleRtNS-C300-CGQ2TG16A1          OBJECT IDENTIFIER ::= { unisevtModuleRouterType 995 }
unisevtModuleRtNS-FWEMPA1                  OBJECT IDENTIFIER ::= { unisevtModuleRouterType 996 }
unisevtModuleRtNSQM5FAB08A1                OBJECT IDENTIFIER ::= { unisevtModuleRouterType 997 }
unisevtModuleRtNS-C300-QG4TG16A1           OBJECT IDENTIFIER ::= { unisevtModuleRouterType 998 }
unisevtModuleRtNSQM5FAB16A1                OBJECT IDENTIFIER ::= { unisevtModuleRouterType 999 }
unisevtModuleRtNSQM5SUP16A1                OBJECT IDENTIFIER ::= { unisevtModuleRouterType 1000 }
unisevtModuleRtNSQ1M9ESL16LA0              OBJECT IDENTIFIER ::= { unisevtModuleRouterType 1001 }
unisevtModuleRtNS-C300-TG24A1              OBJECT IDENTIFIER ::= { unisevtModuleRouterType 1002 }
unisevtModuleRtNSQM1SSICASK1               OBJECT IDENTIFIER ::= { unisevtModuleRouterType 1003 }
unisevtModuleRtNSQM2AFC2000DGDSCA0         OBJECT IDENTIFIER ::= { unisevtModuleRouterType 1004 }
unisevtModuleRt-MPU-60-WiNet               OBJECT IDENTIFIER ::= { unisevtModuleRouterType 1005 }
unisevtModuleRtNSQM2VGDSCA0                OBJECT IDENTIFIER ::= { unisevtModuleRouterType 1006 }
unisevtModuleRt-HRIC-YGS2                  OBJECT IDENTIFIER ::= { unisevtModuleRouterType 1007 }  -- 2-Port 25-GigabitEthernet Optical Interface HRIC-Module
unisevtModuleRt-HRIC-LGQ1                  OBJECT IDENTIFIER ::= { unisevtModuleRouterType 1008 }  -- 1-Port 50-GigabitEthernet Optical Interface HRIC-Module
unisevtModuleRt-HRIC-XP4                   OBJECT IDENTIFIER ::= { unisevtModuleRouterType 1009 }  -- 4-Port Ten-GigabitEthernet Optical Interface HRIC-Module
unisevtModuleRt-RSU-300                    OBJECT IDENTIFIER ::= { unisevtModuleRouterType 1010 }
unisevtModuleRt-CR-19K-LPU-CQ06B           OBJECT IDENTIFIER ::= { unisevtModuleRouterType 1011 }
unisevtModuleRt-CR-HIC-XP10                OBJECT IDENTIFIER ::= { unisevtModuleRouterType 1012 }
unisevtModuleRt-SIC-1SSD                   OBJECT IDENTIFIER ::= { unisevtModuleRouterType 1013 }
unisevtModuleRtNSQM1AFC2000GDFGA0-Z        OBJECT IDENTIFIER ::= { unisevtModuleRouterType 1014 }
unisevtModuleRtNSQM2QG4GP40-Z              OBJECT IDENTIFIER ::= { unisevtModuleRouterType 1015 }
unisevtModuleRtNSQM1CGQ20-Z                OBJECT IDENTIFIER ::= { unisevtModuleRouterType 1016 }
unisevtModuleRtNSQM1FWDFGD1-Z              OBJECT IDENTIFIER ::= { unisevtModuleRouterType 1017 }
unisevtModuleRtNSQM1TGS32QSSG0-Z           OBJECT IDENTIFIER ::= { unisevtModuleRouterType 1018 }
unisevtModuleRtNSQM2TG16GP40-Z             OBJECT IDENTIFIER ::= { unisevtModuleRouterType 1019 }
unisevtModuleRtNSQM2TMPU12E0               OBJECT IDENTIFIER ::= { unisevtModuleRouterType 1020 }
unisevtModuleRt-HMIM-4XP                   OBJECT IDENTIFIER ::= { unisevtModuleRouterType 1021 }  -- 4-Port 10GBASE-R-SFP+ Optical Ethernet Interface Card
unisevtModuleRt-SIC-1POS-STM1              OBJECT IDENTIFIER ::= { unisevtModuleRouterType 1022 }
unisevtModuleRt-HMIM-4POS                  OBJECT IDENTIFIER ::= { unisevtModuleRouterType 1023 }
unisevtModuleRt-NSQM1MPULB                 OBJECT IDENTIFIER ::= { unisevtModuleRouterType 1024 }
unisevtModuleRt-CR-LPU-CQ12B               OBJECT IDENTIFIER ::= { unisevtModuleRouterType 1025 }
unisevtModuleRt-CR-LPU-CQ18                OBJECT IDENTIFIER ::= { unisevtModuleRouterType 1026 }
unisevtModuleRt-CR-MPU-20A                 OBJECT IDENTIFIER ::= { unisevtModuleRouterType 1027 }
unisevtModuleRt-CR-HIC-CLP04               OBJECT IDENTIFIER ::= { unisevtModuleRouterType 1028 }
unisevtModuleRt-CR-SFU-08C                 OBJECT IDENTIFIER ::= { unisevtModuleRouterType 1029 }
unisevtModuleRt-CR-HIC-PHP08               OBJECT IDENTIFIER ::= { unisevtModuleRouterType 1030 }
unisevtModuleRt-CR-MPU-08A                 OBJECT IDENTIFIER ::= { unisevtModuleRouterType 1031 }
unisevtModuleRt-CR-HIC-XP12B               OBJECT IDENTIFIER ::= { unisevtModuleRouterType 1032 }
unisevtModuleRt-CR-HIC-ET16                OBJECT IDENTIFIER ::= { unisevtModuleRouterType 1033 }
unisevtModuleRt-CR-MSFU-08A                OBJECT IDENTIFIER ::= { unisevtModuleRouterType 1034 }
unisevtModuleRt-CR-SFU-20C                 OBJECT IDENTIFIER ::= { unisevtModuleRouterType 1035 }
unisevtModuleRt-SIC-M2-SATA                OBJECT IDENTIFIER ::= { unisevtModuleRouterType 1036 }
unisevtModuleRtNSQM1MPULC                  OBJECT IDENTIFIER ::= { unisevtModuleRouterType 1037 }
unisevtModuleRt-NSUM1QG1A                  OBJECT IDENTIFIER ::= { unisevtModuleRouterType 1038 }
unisevtModuleRt-NSUM1TG4A                  OBJECT IDENTIFIER ::= { unisevtModuleRouterType 1039 }
unisevtModuleRt-NSUM1GP4A                  OBJECT IDENTIFIER ::= { unisevtModuleRouterType 1040 }
unisevtModuleRt-FIP-30                     OBJECT IDENTIFIER ::= { unisevtModuleRouterType 1041 }  -- Flexible Interface Platform Module 30,2 MIC-X Slots, 4*10GBASE-R SFP+ Ports, and 16*1000BASE-X SFP Ports
unisevtModuleRt-RISER-FHFL-X16             OBJECT IDENTIFIER ::= { unisevtModuleRouterType 1042 }  ---SR6602-I PCIe Riser Module(FHFL, 1 PCIe X16 Slot)
unisevtModuleRt-RISER-GPU                  OBJECT IDENTIFIER ::= { unisevtModuleRouterType 1043 } --- Graphic Processiong Unit On Riser Card
unisevtModuleRt-RISER-RAID                 OBJECT IDENTIFIER ::= { unisevtModuleRouterType 1044 } --- Redundant Arrays of Independent Disks On Riser Card
unisevtModuleRt-CR-19K-LPU-8004            OBJECT IDENTIFIER ::= { unisevtModuleRouterType 1045 }  -- CR Flexible Interface Module 8004
unisevtModuleRt-CR-19K-MPU-08B             OBJECT IDENTIFIER ::= { unisevtModuleRouterType 1046 }  -- CR Main Processing Unit B for 08 Chassis
unisevtModuleRt-CR-HIC-CQ02                OBJECT IDENTIFIER ::= { unisevtModuleRouterType 1047 }  -- 2-Port 100-GigabitEthernet Optical Interface HIC-Module
unisevtModuleRt-NSQM1ISPAXA1               OBJECT IDENTIFIER ::= { unisevtModuleRouterType 1048 }  -- 2-Port 10/100/1000BASE-T and 2-Port 1000BASE-X SFP Interface Module
unisevtModuleRt-NSQM1ISPAXB1               OBJECT IDENTIFIER ::= { unisevtModuleRouterType 1049 }  -- 2-Port 10/100/1000BASE-T and 2-Port 1000BASE-X SFP Interface Module
unisevtModuleRt-CR-USBDISK                 OBJECT IDENTIFIER ::= { unisevtModuleRouterType 1050 }  -- CR USB DISK
unisevtModuleRt-SIC-4RS                    OBJECT IDENTIFIER ::= { unisevtModuleRouterType 1051 }  -- H3C MSR,RTU1S4RS,4-Port Asynchronous Serial Interface SIC Interface Board,2*1
unisevtModuleRt-NSQM1MPULC-Z               OBJECT IDENTIFIER ::= { unisevtModuleRouterType 1052 }
unisevtModuleRt-CR-18K-MPU-16B             OBJECT IDENTIFIER ::= { unisevtModuleRouterType 1053 } -- CR Main Processing Unit B for 18 Chassis
unisevtModuleRt-CR-18K-SFU-16C             OBJECT IDENTIFIER ::= { unisevtModuleRouterType 1054 } -- CR Switching Fabric Unit(HC) C for 18 Chassis
unisevtModuleRt-DS-3RH-4T                  OBJECT IDENTIFIER ::= { unisevtModuleRouterType 1055 } -- H Series Enterprise Router 4 Gigabit Electrical Port SIC Module
unisevtModuleRt-HRIC-CQ1F                  OBJECT IDENTIFIER ::= { unisevtModuleRouterType 1056 } -- 1-Port 100-GigabitEthernet Optical Interface HRIC-Module
unisevtModuleRt-HRIC-LGQ2F                 OBJECT IDENTIFIER ::= { unisevtModuleRouterType 1057 } -- 1-Port 50-100-GigabitEthernet and 1-Port 50 GigabitEthernet Optical Interface HRIC-Module
unisevtModuleRt-CR-HIC-CLGQ04              OBJECT IDENTIFIER ::= { unisevtModuleRouterType 1058 } -- CR 4-Port FlexE Optical SubCard
unisevtModuleRt-NSQM1QG1A-Z                OBJECT IDENTIFIER ::= { unisevtModuleRouterType 1059 } -- 1-Port 40GBASE Ethernet Optical Interface Module(QSFP+)
unisevtModuleRt-NSQM1TG4A-Z                OBJECT IDENTIFIER ::= { unisevtModuleRouterType 1060 } -- 4-Port 10GBASE Ethernet Optical Interface Module(SFP+)
unisevtModuleRt-NSQM1GP4A-Z                OBJECT IDENTIFIER ::= { unisevtModuleRouterType 1061 } -- 4-Port Gigabit Ethernet Optical Interface Module(SFP)
unisevtModuleRt-CR-LPU-8004                OBJECT IDENTIFIER ::= { unisevtModuleRouterType 1062 }  -- CR Flexible Interface Module 8004
unisevtModuleRt-MPU-100-G                  OBJECT IDENTIFIER ::= { unisevtModuleRouterType 1063 } -- MPU-100-G Main Processing Unit
unisevtModuleRt-SPU-300-G                  OBJECT IDENTIFIER ::= { unisevtModuleRouterType 1064 } -- SPU-300-G Service Processing Unit
unisevtModuleRt-CR-19K-MPU-20C             OBJECT IDENTIFIER ::= { unisevtModuleRouterType 1065 } -- CR X86 MPU  for 20 Chassis
unisevtModuleRt-CR-18K-MPU-16C             OBJECT IDENTIFIER ::= { unisevtModuleRouterType 1066 } -- CR X86 MPU  for 18 Chassis
unisevtModuleRt-SIC-5G                     OBJECT IDENTIFIER ::= { unisevtModuleRouterType 1067 } -- H3C MSR,RTUM1S5G,5G(5G NR/NSA/SA/4G FDD/TDD LTE-A/3G WCDMA,Sub6,GNSS)SIC Module,Domestic&Overseas Version
unisevtModuleRt-RSU-400                    OBJECT IDENTIFIER ::= { unisevtModuleRouterType 1068 } -- Router Switch Unit 400
















-- 1000 to 4999 for united assignment
--


--
-- reserved for other brands from 5000
--
hpevtModuleRt-SIC-EPRI                     OBJECT IDENTIFIER ::= { unisevtModuleRouterType 5000 } -- 1-Port E1/CE1/PRI Interface Card
hpevtModuleRt-MIM-1E1-V2                   OBJECT IDENTIFIER ::= { unisevtModuleRouterType 5001 } -- 1-Port CE1/PRI Interface Module
hpevtModuleRt-MIM-1E1-F-V2                 OBJECT IDENTIFIER ::= { unisevtModuleRouterType 5002 } -- 1-Port E1 & Fractional E1 Interface Module
hpevtModuleRt-MIM-2E1-F-V2                 OBJECT IDENTIFIER ::= { unisevtModuleRouterType 5003 } -- 2-Port E1 & Fractional E1 Interface Module
hpevtModuleRt-MIM-4E1-F-V2                 OBJECT IDENTIFIER ::= { unisevtModuleRouterType 5004 } -- 4-Port E1 & Fractional E1 Interface Module
hpevtModuleRt-MIM-8E1-75                   OBJECT IDENTIFIER ::= { unisevtModuleRouterType 5005 } -- 8-port E1/CE1/PRI Module(75ohm)
hpevtModuleRt-MIM-8E1-75-F                 OBJECT IDENTIFIER ::= { unisevtModuleRouterType 5006 } -- 8-Port E1 Module-Fractional(75ohm)
hpevtModuleRt-MIM-8T1                      OBJECT IDENTIFIER ::= { unisevtModuleRouterType 5007 } -- 8-Port T1 Interface Module
hpevtModuleRt-MIM-8T1-F                    OBJECT IDENTIFIER ::= { unisevtModuleRouterType 5008 } -- 8-Port T1 Module-Fractional
hpevtModuleRt-MIM-IMA-8E1-75               OBJECT IDENTIFIER ::= { unisevtModuleRouterType 5009 } -- 8-Port E1 ATM IMA Interface Module(75ohm)
hpevtModuleRt-FIC-2E1-V3                   OBJECT IDENTIFIER ::= { unisevtModuleRouterType 5010 } -- 2-Port E1/CE1/PRI Interface FIC Module
hpevtModuleRt-FIC-IMA-8T1-V2               OBJECT IDENTIFIER ::= { unisevtModuleRouterType 5011 } -- 8-Port T1 ATM IMA Interface FIC Module
unisevtModuleRtCN-MSU-X3                   OBJECT IDENTIFIER ::= { unisevtModuleRouterType 5012 } -- Mainboard Switch Unit X3
unisevtModuleRtCN-FSP-660                  OBJECT IDENTIFIER ::= { unisevtModuleRouterType 5013 } -- Flexible Service Platform 660
unisevtModuleRtCN-MIC-X-XP4W               OBJECT IDENTIFIER ::= { unisevtModuleRouterType 5014 } -- 4-Port 1000BASE-R-SFP+ Optical Multi-functional Interface Card
unisevtModuleRtCN-MIC-X-GP8                OBJECT IDENTIFIER ::= { unisevtModuleRouterType 5015 } -- 8-Port 1000BASE-X Optical Multi-functional Interface Card
unisevtModuleRtCN-MIC-X-GT8                OBJECT IDENTIFIER ::= { unisevtModuleRouterType 5016 } -- 8-Port 10/100/1000BASE-T Electronic Multi-functional Interface Card

-- unisevtModuleSwitchType cards are slot-cards specific to the Switch.
unisevtModuleSwitchType  OBJECT IDENTIFIER ::= { unisevtModule 4 }

--unisevtModuleNULL(0),
unisevtModuleSw-10OR100M                    OBJECT IDENTIFIER ::= { unisevtModuleSwitchType 1 }
unisevtModuleSw-1000BASE-LX-SM              OBJECT IDENTIFIER ::= { unisevtModuleSwitchType 2 }
unisevtModuleSw-1000BASE-SX-MM              OBJECT IDENTIFIER ::= { unisevtModuleSwitchType 3 }
unisevtModuleSw-1000BASE-TX                 OBJECT IDENTIFIER ::= { unisevtModuleSwitchType 4 }
unisevtModuleSw-100M-SINGLEMODE-FX          OBJECT IDENTIFIER ::= { unisevtModuleSwitchType 5 }
unisevtModuleSw-100M-MULTIMODE-FX           OBJECT IDENTIFIER ::= { unisevtModuleSwitchType 6 }
unisevtModuleSw-100M-100BASE-TX             OBJECT IDENTIFIER ::= { unisevtModuleSwitchType 7 }
unisevtModuleSw-100M-HUB                    OBJECT IDENTIFIER ::= { unisevtModuleSwitchType 8 }
unisevtModuleSw-VDSL                        OBJECT IDENTIFIER ::= { unisevtModuleSwitchType 9 }
unisevtModuleSw-STACK                       OBJECT IDENTIFIER ::= { unisevtModuleSwitchType 10 }
unisevtModuleSw-1000BASE-ZENITH-FX          OBJECT IDENTIFIER ::= { unisevtModuleSwitchType 11 }
unisevtModuleSw-1000BASE-LONG-FX            OBJECT IDENTIFIER ::= { unisevtModuleSwitchType 12 }
unisevtModuleSw-ADSL                        OBJECT IDENTIFIER ::= { unisevtModuleSwitchType 13 }
unisevtModuleSw-4T10OR100-4FX100SM          OBJECT IDENTIFIER ::= { unisevtModuleSwitchType 14 }
unisevtModuleSw-4T10OR100-4FX100MM          OBJECT IDENTIFIER ::= { unisevtModuleSwitchType 15 }
unisevtModuleSw-VSPL                        OBJECT IDENTIFIER ::= { unisevtModuleSwitchType 16 }
unisevtModuleSw-ASPL                        OBJECT IDENTIFIER ::= { unisevtModuleSwitchType 17 }
unisevtModuleSw-1000M-SFP                   OBJECT IDENTIFIER ::= { unisevtModuleSwitchType 18 }
unisevtModuleSw-LS82O2CM                    OBJECT IDENTIFIER ::= { unisevtModuleSwitchType 19 }
unisevtModuleSw-LS82P2CM                    OBJECT IDENTIFIER ::= { unisevtModuleSwitchType 20 }
unisevtModuleSw-LS82O4GM                    OBJECT IDENTIFIER ::= { unisevtModuleSwitchType 21 }
unisevtModuleSw-LS82GB4C                    OBJECT IDENTIFIER ::= { unisevtModuleSwitchType 22 }
unisevtModuleSw-LS82GT4C                    OBJECT IDENTIFIER ::= { unisevtModuleSwitchType 23 }
unisevtModuleSw-LS82ST4C                    OBJECT IDENTIFIER ::= { unisevtModuleSwitchType 24 }
unisevtModuleSw-BOARD-LS82DSPU              OBJECT IDENTIFIER ::= { unisevtModuleSwitchType 25 }
unisevtModuleSw-BOARD-LS81GP8U              OBJECT IDENTIFIER ::= { unisevtModuleSwitchType 26 }
unisevtModuleSw-BOARD-LS82GT20              OBJECT IDENTIFIER ::= { unisevtModuleSwitchType 27 }
unisevtModuleSw-BOARD-LS82FE48              OBJECT IDENTIFIER ::= { unisevtModuleSwitchType 28 }
unisevtModuleSw-LS82T24B                    OBJECT IDENTIFIER ::= { unisevtModuleSwitchType 29 }
unisevtModuleSw-LSB1SRPA                    OBJECT IDENTIFIER ::= { unisevtModuleSwitchType 30 }
unisevtModuleSw-LSB1FT48A                   OBJECT IDENTIFIER ::= { unisevtModuleSwitchType 31 }
unisevtModuleSw-LSB1FT48B                   OBJECT IDENTIFIER ::= { unisevtModuleSwitchType 32 }
unisevtModuleSw-LSB1F48GA                   OBJECT IDENTIFIER ::= { unisevtModuleSwitchType 33 }
unisevtModuleSw-LSB1F48GB                   OBJECT IDENTIFIER ::= { unisevtModuleSwitchType 34 }
unisevtModuleSw-LSB1FP20A                   OBJECT IDENTIFIER ::= { unisevtModuleSwitchType 35 }
unisevtModuleSw-LSB1FP20B                   OBJECT IDENTIFIER ::= { unisevtModuleSwitchType 36 }
unisevtModuleSw-FT48A                       OBJECT IDENTIFIER ::= { unisevtModuleSwitchType 37 }
unisevtModuleSw-GP4U                        OBJECT IDENTIFIER ::= { unisevtModuleSwitchType 38 }
unisevtModuleSw-GP2U                        OBJECT IDENTIFIER ::= { unisevtModuleSwitchType 39 }
unisevtModuleSw-TGX1A                       OBJECT IDENTIFIER ::= { unisevtModuleSwitchType 40 }
unisevtModuleSw-1000BASE-LX-SM-IR-SC        OBJECT IDENTIFIER ::= { unisevtModuleSwitchType 41 }
unisevtModuleSw-1000BASE-SX-MM-SR-SC        OBJECT IDENTIFIER ::= { unisevtModuleSwitchType 42 }
unisevtModuleSw-1000BASE-T-RJ45             OBJECT IDENTIFIER ::= { unisevtModuleSwitchType 43 }
unisevtModuleSw-100BASE-FX-SM-IR-SC         OBJECT IDENTIFIER ::= { unisevtModuleSwitchType 44 }
unisevtModuleSw-100BASE-FX-MM-SR-SC         OBJECT IDENTIFIER ::= { unisevtModuleSwitchType 45 }
unisevtModuleSw-GIGA-STACK-1M-PC            OBJECT IDENTIFIER ::= { unisevtModuleSwitchType 46 }
unisevtModuleSw-1000BASE-LX-SM-VLR-LC       OBJECT IDENTIFIER ::= { unisevtModuleSwitchType 47 }
unisevtModuleSw-1000BASE-LX-SM-LR-LC        OBJECT IDENTIFIER ::= { unisevtModuleSwitchType 48 }
unisevtModuleSw-100BASE-FX-SM-LR-SC         OBJECT IDENTIFIER ::= { unisevtModuleSwitchType 49 }
unisevtModuleSw-1000BASE-X-GBIC             OBJECT IDENTIFIER ::= { unisevtModuleSwitchType 50 }
unisevtModuleSw-100M-SINGLEMODE-FX-LC       OBJECT IDENTIFIER ::= { unisevtModuleSwitchType 51 }
unisevtModuleSw-100M-MULTIMODE-FX-LC        OBJECT IDENTIFIER ::= { unisevtModuleSwitchType 52 }
unisevtModuleSw-1000BASE-4SFP               OBJECT IDENTIFIER ::= { unisevtModuleSwitchType 53 }
unisevtModuleSw-1000BASE-4GBIC              OBJECT IDENTIFIER ::= { unisevtModuleSwitchType 54 }
unisevtModuleSw-1000BASE-FIXED-4SFP         OBJECT IDENTIFIER ::= { unisevtModuleSwitchType 55 }
unisevtModuleSw-1000BASE-FIXED-4GBIC        OBJECT IDENTIFIER ::= { unisevtModuleSwitchType 56 }
unisevtModuleSw-LSB1GP12A                   OBJECT IDENTIFIER ::= { unisevtModuleSwitchType 57 }
unisevtModuleSw-LSB1GP12B                   OBJECT IDENTIFIER ::= { unisevtModuleSwitchType 58 }
unisevtModuleSw-LSB1TGX1A                   OBJECT IDENTIFIER ::= { unisevtModuleSwitchType 59 }
unisevtModuleSw-LSB1TGX1B                   OBJECT IDENTIFIER ::= { unisevtModuleSwitchType 60 }
unisevtModuleSw-LSB1P4G8A                   OBJECT IDENTIFIER ::= { unisevtModuleSwitchType 61 }
unisevtModuleSw-LSB1P4G8B                   OBJECT IDENTIFIER ::= { unisevtModuleSwitchType 62 }
unisevtModuleSw-LSB1A4G8A                   OBJECT IDENTIFIER ::= { unisevtModuleSwitchType 63 }
unisevtModuleSw-LSB1A4G8B                   OBJECT IDENTIFIER ::= { unisevtModuleSwitchType 64 }
unisevtModuleSw-FT48C                       OBJECT IDENTIFIER ::= { unisevtModuleSwitchType 65 }
unisevtModuleSw-FP20                        OBJECT IDENTIFIER ::= { unisevtModuleSwitchType 66 }
unisevtModuleSw-BOARD-LS81FT48              OBJECT IDENTIFIER ::= { unisevtModuleSwitchType 67 }
unisevtModuleSw-BOARD-LS81GB8U              OBJECT IDENTIFIER ::= { unisevtModuleSwitchType 68 }
unisevtModuleSw-BOARD-LS81GT8U              OBJECT IDENTIFIER ::= { unisevtModuleSwitchType 69 }
unisevtModuleSw-BOARD-LS81FS24              OBJECT IDENTIFIER ::= { unisevtModuleSwitchType 70 }
unisevtModuleSw-BOARD-LS81FM24              OBJECT IDENTIFIER ::= { unisevtModuleSwitchType 71 }
unisevtModuleSw-BOARD-LS82GP20              OBJECT IDENTIFIER ::= { unisevtModuleSwitchType 72 }
unisevtModuleSw-LSB1SRPB                    OBJECT IDENTIFIER ::= { unisevtModuleSwitchType 73 }
unisevtModuleSw-LSB1F32GA                   OBJECT IDENTIFIER ::= { unisevtModuleSwitchType 74 }
unisevtModuleSw-LSB1F32GB                   OBJECT IDENTIFIER ::= { unisevtModuleSwitchType 75 }
unisevtModuleSw-LSB2FT48A                   OBJECT IDENTIFIER ::= { unisevtModuleSwitchType 76 }
unisevtModuleSw-LSB2FT48B                   OBJECT IDENTIFIER ::= { unisevtModuleSwitchType 77 }
unisevtModuleSw-LSB1GT12A                   OBJECT IDENTIFIER ::= { unisevtModuleSwitchType 78 }
unisevtModuleSw-LSB1GT12B                   OBJECT IDENTIFIER ::= { unisevtModuleSwitchType 79 }
unisevtModuleSw-PC4U                        OBJECT IDENTIFIER ::= { unisevtModuleSwitchType 80 }
unisevtModuleSw-FT32A                       OBJECT IDENTIFIER ::= { unisevtModuleSwitchType 81 }
unisevtModuleSw-GT4U                        OBJECT IDENTIFIER ::= { unisevtModuleSwitchType 82 }
unisevtModuleSw-BOARD-LS83FP20A             OBJECT IDENTIFIER ::= { unisevtModuleSwitchType 83 }
unisevtModuleSw-BOARD-LS82HGMU              OBJECT IDENTIFIER ::= { unisevtModuleSwitchType 84 }
unisevtModuleSw-LSB1GP8TB                   OBJECT IDENTIFIER ::= { unisevtModuleSwitchType 85 }
unisevtModuleSw-LSB1GP8TC                   OBJECT IDENTIFIER ::= { unisevtModuleSwitchType 86 }
unisevtModuleSw-LSB1GT8PB                   OBJECT IDENTIFIER ::= { unisevtModuleSwitchType 87 }
unisevtModuleSw-LSB1GT8PC                   OBJECT IDENTIFIER ::= { unisevtModuleSwitchType 88 }
unisevtModuleSw-LSB1FT48C                   OBJECT IDENTIFIER ::= { unisevtModuleSwitchType 89 }
unisevtModuleSw-LSB1FP20C                   OBJECT IDENTIFIER ::= { unisevtModuleSwitchType 90 }
unisevtModuleSw-LSB1F32GC                   OBJECT IDENTIFIER ::= { unisevtModuleSwitchType 91 }
unisevtModuleSw-LSB1GT12C                   OBJECT IDENTIFIER ::= { unisevtModuleSwitchType 92 }
unisevtModuleSw-LSB1GP12C                   OBJECT IDENTIFIER ::= { unisevtModuleSwitchType 93 }
unisevtModuleSw-LSB1P4G8C                   OBJECT IDENTIFIER ::= { unisevtModuleSwitchType 94 }
unisevtModuleSw-LSB1TGX1C                   OBJECT IDENTIFIER ::= { unisevtModuleSwitchType 95 }
unisevtModuleSw-LSB1GT24B                   OBJECT IDENTIFIER ::= { unisevtModuleSwitchType 96 }
unisevtModuleSw-LSB1GT24C                   OBJECT IDENTIFIER ::= { unisevtModuleSwitchType 97 }
unisevtModuleSw-LSB1GP24B                   OBJECT IDENTIFIER ::= { unisevtModuleSwitchType 98 }
unisevtModuleSw-LSB1GP24C                   OBJECT IDENTIFIER ::= { unisevtModuleSwitchType 99 }
unisevtModuleSw-LSB1XP2B                    OBJECT IDENTIFIER ::= { unisevtModuleSwitchType 100 }
unisevtModuleSw-LSB1XP2C                    OBJECT IDENTIFIER ::= { unisevtModuleSwitchType 101 }
unisevtModuleSw-LSB1GV48B                   OBJECT IDENTIFIER ::= { unisevtModuleSwitchType 102 }
unisevtModuleSw-LSB1GV48C                   OBJECT IDENTIFIER ::= { unisevtModuleSwitchType 103 }
unisevtModuleSw-LSB1SRPC                    OBJECT IDENTIFIER ::= { unisevtModuleSwitchType 104 }
unisevtModuleSw-LSB1SRP1N0                  OBJECT IDENTIFIER ::= { unisevtModuleSwitchType 105 }
unisevtModuleSw-LSB1SRP1N1                  OBJECT IDENTIFIER ::= { unisevtModuleSwitchType 106 }
unisevtModuleSw-LSB1SRP1N2                  OBJECT IDENTIFIER ::= { unisevtModuleSwitchType 107 }
unisevtModuleSw-GT24                        OBJECT IDENTIFIER ::= { unisevtModuleSwitchType 108 }
unisevtModuleSw-GP24                        OBJECT IDENTIFIER ::= { unisevtModuleSwitchType 109 }
unisevtModuleSw-XP2                         OBJECT IDENTIFIER ::= { unisevtModuleSwitchType 110 }
unisevtModuleSw-GV48                        OBJECT IDENTIFIER ::= { unisevtModuleSwitchType 111 }
unisevtModuleSw-LSG1GP8U                    OBJECT IDENTIFIER ::= { unisevtModuleSwitchType 112 }
unisevtModuleSw-LSG1GT8U                    OBJECT IDENTIFIER ::= { unisevtModuleSwitchType 113 }
unisevtModuleSw-LSG1TG1U                    OBJECT IDENTIFIER ::= { unisevtModuleSwitchType 114 }
unisevtModuleSw-LSG1TD1U                    OBJECT IDENTIFIER ::= { unisevtModuleSwitchType 115 }
unisevtModuleSw-LSB2FT48C                   OBJECT IDENTIFIER ::= { unisevtModuleSwitchType 116 } -- 48-Ports 100Base-TX Ethernet Interface module C
unisevtModuleSw-LSB1GT48B                   OBJECT IDENTIFIER ::= { unisevtModuleSwitchType 117 } -- 48-Ports 10/100/1000Base-T Ethernet Interface Module B
unisevtModuleSw-LSB1GT48C                   OBJECT IDENTIFIER ::= { unisevtModuleSwitchType 118 } -- 48-Ports 10/100/1000Base-T Ethernet Interface Module C
unisevtModuleSw-LS81GT48                    OBJECT IDENTIFIER ::= { unisevtModuleSwitchType 119 } -- 48 Port Gigabit Ethernet Electric Interface Unit
unisevtModuleSw-LS81SRPG0                   OBJECT IDENTIFIER ::= { unisevtModuleSwitchType 120 } -- Salience III, Switch and Route Processing Board
unisevtModuleSw-LS81SRPG1                   OBJECT IDENTIFIER ::= { unisevtModuleSwitchType 121 } -- Salience III Plus
unisevtModuleSw-LS81SRPG2                   OBJECT IDENTIFIER ::= { unisevtModuleSwitchType 122 } -- Salience III Lite
unisevtModuleSw-LS81SRPG3                   OBJECT IDENTIFIER ::= { unisevtModuleSwitchType 123 } -- Salience III Edge

unisevtModuleSw-SR01SRPUB                   OBJECT IDENTIFIER ::= { unisevtModuleSwitchType 125 } -- Switching and Route Processing Unit
unisevtModuleSw-SR01SRPUA                   OBJECT IDENTIFIER ::= { unisevtModuleSwitchType 126 } -- Switching and Route Processing Unit
unisevtModuleSw-SR01GP12L                   OBJECT IDENTIFIER ::= { unisevtModuleSwitchType 127 } -- 12-Port 1000Base-X Ethernet SFP Optical Interface Line Card(L)
unisevtModuleSw-SR01GP12W                   OBJECT IDENTIFIER ::= { unisevtModuleSwitchType 128 } -- 12-Port 1000Base-X Ethernet SFP Optical Interface Line Card(W)
unisevtModuleSw-SR01FT48L                   OBJECT IDENTIFIER ::= { unisevtModuleSwitchType 129 } -- 48-Port 10/100Base-TX Ethernet RJ45 Electrical Interface Line Card (L)
unisevtModuleSw-SR01FT48W                   OBJECT IDENTIFIER ::= { unisevtModuleSwitchType 130 } -- 48-Port 10/100Base-TX Ethernet RJ45 Electrical Interface Line Card (W)
unisevtModuleSw-SR01XK1W                    OBJECT IDENTIFIER ::= { unisevtModuleSwitchType 131 } -- 1-Port 10GBase-R Ethernet XENPAK Optical Interface Line Card (W)
unisevtModuleSw-SR01FP20W                   OBJECT IDENTIFIER ::= { unisevtModuleSwitchType 132 } -- 20-Port 100Base-FX Ethernet SFP Optical Interface Line Card (W)
unisevtModuleSw-SR01GT12W                   OBJECT IDENTIFIER ::= { unisevtModuleSwitchType 133 } -- 12-Port 10/100/1000Base-T Ethernet RJ45 Electrical Interface Line Card (W)
unisevtModuleSw-SR01F32GL                   OBJECT IDENTIFIER ::= { unisevtModuleSwitchType 134 } -- 32-Port 10/100Base-TX Ethernet RJ45 Electrical Interface + 4-Port 1000Base-X Ethernet SFP Optical interface Line Card (L)
unisevtModuleSw-SR01F32GW                   OBJECT IDENTIFIER ::= { unisevtModuleSwitchType 135 } -- 32-Port 10/100Base-TX Ethernet RJ45 Electrical Interface  + 4-Port 1000Base-X  Ethernet SFP Optical interface Line Card (W)
unisevtModuleSw-SR01GT8PL                   OBJECT IDENTIFIER ::= { unisevtModuleSwitchType 136 } -- 8-Port 10/100/1000Base-T Ethernet RJ45 Electrical Interface + 4-Port 1000Base-X Ethernet SFP Optical Line Card (L)
unisevtModuleSw-SR01GT8PW                   OBJECT IDENTIFIER ::= { unisevtModuleSwitchType 137 } -- 8-Port 10/100/1000Base-T Ethernet RJ45 Electrical Interface + 4-Port 1000Base-X Ethernet SFP Optical Line Card (W)
unisevtModuleSw-SR01P4G8W                   OBJECT IDENTIFIER ::= { unisevtModuleSwitchType 138 } -- 4-Port 155M POS Optical Interface + 8-Port 1000Base-X Ethernet SFP Optical Interface Line Card (W)
unisevtModuleSw-LSA1FP8U                    OBJECT IDENTIFIER ::= { unisevtModuleSwitchType 139 } -- 8 Ports 100Base-FX Ethernet SFP Card
unisevtModuleSw-LSB1SP4B                    OBJECT IDENTIFIER ::= { unisevtModuleSwitchType 140 } -- 4-Port OC-48 POS SFP Optical Interface Board B
unisevtModuleSw-LSB1SP4C                    OBJECT IDENTIFIER ::= { unisevtModuleSwitchType 141 } -- 4-Port OC-48 POS SFP Optical Interface Board C
unisevtModuleSw-LSB1UP1B                    OBJECT IDENTIFIER ::= { unisevtModuleSwitchType 142 } -- 1-Port OC-192 POS XFP Optical Interface Board B
unisevtModuleSw-LSB1UP1C                    OBJECT IDENTIFIER ::= { unisevtModuleSwitchType 143 } -- 1-Port OC-192 POS XFP Optical Interface Board C
unisevtModuleSw-LSB1XP4B                    OBJECT IDENTIFIER ::= { unisevtModuleSwitchType 144 } -- 4-Port 10GBase Ethernet XFP Optical Interface Board B
unisevtModuleSw-LSB1XP4C                    OBJECT IDENTIFIER ::= { unisevtModuleSwitchType 145 } -- 4-Port 10GBase Ethernet XFP Optical Interface Board C
unisevtModuleSw-SP4                         OBJECT IDENTIFIER ::= { unisevtModuleSwitchType 146 } -- 4-Port OC-48 POS SFP Optical Interface Module
unisevtModuleSw-UP1                         OBJECT IDENTIFIER ::= { unisevtModuleSwitchType 147 } -- 1-Port OC-192 POS XFP Optical Interface Module
unisevtModuleSw-XP4                         OBJECT IDENTIFIER ::= { unisevtModuleSwitchType 148 } -- 4-Port 10GBase Ethernet XFP Optical Interface Module
unisevtModuleSw-LS81VSNP                    OBJECT IDENTIFIER ::= { unisevtModuleSwitchType 149 } -- VerSatile Network Processing Board
unisevtModuleSw-LS81T12P                    OBJECT IDENTIFIER ::= { unisevtModuleSwitchType 150 } -- 12-Port 1000Base-T Gigabit Ethernet Interface(RJ45)+4-Port 1000BASE-X  Gigabit Ethernet Optical Interface Board(SFP,LC)
unisevtModuleSw-LS81P12T                    OBJECT IDENTIFIER ::= { unisevtModuleSwitchType 151 } -- 12-Port 1000BASE-X Gigabit Ethernet Optical Interface(SFP,LC)+4-Port 1000BASE-T Gigabit Ethernet Interface Board(RJ45)
unisevtModuleSw-LS81GP8UB                   OBJECT IDENTIFIER ::= { unisevtModuleSwitchType 152 } -- 8-Port 1000M Ethernet Optical Interface Board(SFP,LC),LC Connector
unisevtModuleSw-LS81FT48E                   OBJECT IDENTIFIER ::= { unisevtModuleSwitchType 153 } -- 48-Port 100M Ethernet Electrical Interface Switch Unit(RJ45)
unisevtModuleSw-LS81GP4UB                   OBJECT IDENTIFIER ::= { unisevtModuleSwitchType 154 } -- 4-Port 1000M Ethernet Optical Interface Board(SFP,LC)
unisevtModuleSw-LS81GT8UE                   OBJECT IDENTIFIER ::= { unisevtModuleSwitchType 155 } -- 8-Port 1000M Ethernet Electrical Interface Switch Unit (RJ45)
unisevtModuleSw-LS81GT48A                   OBJECT IDENTIFIER ::= { unisevtModuleSwitchType 156 } -- 48 Port Gigabit Ethernet Electric Interface Unit
unisevtModuleSw-LS81FP48                    OBJECT IDENTIFIER ::= { unisevtModuleSwitchType 157 } -- 48 Port 100M Ethernet Optical Interface Board(SFP,LC)
unisevtModuleSw-LSB1XK1B                    OBJECT IDENTIFIER ::= { unisevtModuleSwitchType 158 } -- 1-Port 10GBase-R Ethernet XENPAK Optical Interface Board B
unisevtModuleSw-LSB1XK1C                    OBJECT IDENTIFIER ::= { unisevtModuleSwitchType 159 } -- 1-Port 10GBase-R Ethernet XENPAK Optical Interface Board C
unisevtModuleSw-SR01SRPUC                   OBJECT IDENTIFIER ::= { unisevtModuleSwitchType 160 } -- Switching and Route Processing Unit C
unisevtModuleSw-SR01SRPUD                   OBJECT IDENTIFIER ::= { unisevtModuleSwitchType 161 } -- Switching and Route Processing Unit D
unisevtModuleSw-SR01SRPUE                   OBJECT IDENTIFIER ::= { unisevtModuleSwitchType 162 } -- Switching and Route Processing Unit E
unisevtModuleSw-LSB1SRP1N3                  OBJECT IDENTIFIER ::= { unisevtModuleSwitchType 163 } -- Switching and Route Process Unit, Clock Module
unisevtModuleSw-LSB1VP2B                    OBJECT IDENTIFIER ::= { unisevtModuleSwitchType 164 } -- 2*10G Resilient Packet Ring Interface Line Card
unisevtModuleSw-LSB1NATB                    OBJECT IDENTIFIER ::= { unisevtModuleSwitchType 165 } -- NAT Service Processing Card (B)
unisevtModuleSw-LSB1VPNB                    OBJECT IDENTIFIER ::= { unisevtModuleSwitchType 166 } -- VPN Service Processing Card (B)
unisevtModuleSw-LSGP8P                      OBJECT IDENTIFIER ::= { unisevtModuleSwitchType 167 } -- 8-Port 1000M SFP Module
unisevtModuleSw-LSXK1P                      OBJECT IDENTIFIER ::= { unisevtModuleSwitchType 168 } -- 1-Port 10G Xenpak Module
unisevtModuleSw-LSXP2P                      OBJECT IDENTIFIER ::= { unisevtModuleSwitchType 169 } -- 2-Port 10G XFP Module
unisevtModuleSw-LS81FT48F                   OBJECT IDENTIFIER ::= { unisevtModuleSwitchType 170 } -- 48-Port 100M Ethernet Electrical Interface Switch Unit(RJ45)
unisevtModuleSw-LS81PT8G                    OBJECT IDENTIFIER ::= { unisevtModuleSwitchType 171 } -- 8 Port 1000BASE-X Gigabit Passive Optical Line Interface Board
unisevtModuleSw-LS81PT4G                    OBJECT IDENTIFIER ::= { unisevtModuleSwitchType 172 } -- 4 Port 1000BASE-X Gigabit Passive Optical Line Interface Board
unisevtModuleSw-LSSTK24G                    OBJECT IDENTIFIER ::= { unisevtModuleSwitchType 173 } -- 24G Stacking Ports Module
unisevtModuleSw-LS82GT20A                   OBJECT IDENTIFIER ::= { unisevtModuleSwitchType 174 } -- 20-Port 1000Base-T Gigabit Ethernet Electrical Interface Board(RJ45), BCM5697
unisevtModuleSw-LS82GP20A                   OBJECT IDENTIFIER ::= { unisevtModuleSwitchType 175 } -- 20-Port 1000BASE-X Gigabit Ethernet Optical Interface Board(SFP,LC), BCM5697
unisevtModuleSw-LS81TGX1C                   OBJECT IDENTIFIER ::= { unisevtModuleSwitchType 176 } -- 1-Port 10G Base-R Ethernet Board
unisevtModuleSw-VP2                         OBJECT IDENTIFIER ::= { unisevtModuleSwitchType 177 } -- 2*10G Resilient Packet Ring Interface Module
unisevtModuleSw-LSA1FB8U                    OBJECT IDENTIFIER ::= { unisevtModuleSwitchType 178 } -- 8-Port 100Base-Fx BIDI Ethernet Board
unisevtModuleSw-LS81T12PE                   OBJECT IDENTIFIER ::= { unisevtModuleSwitchType 179 } -- 12-Port 1000Base-T GE Interface+4-Port 1000BASE-X GE Optical Interface Board(SFP,LC)
unisevtModuleSw-LS81P12TE                   OBJECT IDENTIFIER ::= { unisevtModuleSwitchType 180 } -- 12-Port 1000BASE-X GE Optical Interface(SFP,LC)+4-Port 1000 BASE-T GE Interface Board(RJ45)
unisevtModuleSw-LSB1SRP2N0                  OBJECT IDENTIFIER ::= { unisevtModuleSwitchType 181 } -- Switching and Route Process Unit,12*LPU
unisevtModuleSw-LSB1SRP2N3                  OBJECT IDENTIFIER ::= { unisevtModuleSwitchType 182 } -- Switching and Route Process Unit, Clock Module
unisevtModuleSw-LSB1GV48DB                  OBJECT IDENTIFIER ::= { unisevtModuleSwitchType 183 } -- 48 Ports 1000Base-T Ethernet Interface Line Card with POE(DB)
unisevtModuleSw-LSB1FW8B                    OBJECT IDENTIFIER ::= { unisevtModuleSwitchType 184 } -- Firewall Service Processing Board with 8GE (B)
unisevtModuleSw-LSB1IPSEC8B                 OBJECT IDENTIFIER ::= { unisevtModuleSwitchType 185 } -- VPN Service Processing Board with 8GE (B)
unisevtModuleSw-LSB1IDSB                    OBJECT IDENTIFIER ::= { unisevtModuleSwitchType 186 } -- IDS Service Processing Board (B)
unisevtModuleSw-LSB1IPSB                    OBJECT IDENTIFIER ::= { unisevtModuleSwitchType 187 } -- IPS Service Processing Board (B)
unisevtModuleSw-LSB2FT48CA                  OBJECT IDENTIFIER ::= { unisevtModuleSwitchType 188 } -- 48 Ports 100Base-TX Ethernet Line Card (CA)
unisevtModuleSw-LSB1FP20CA                  OBJECT IDENTIFIER ::= { unisevtModuleSwitchType 189 } -- 20 Ports 100Base-FX Ethernet Interface Service Card (CA)
unisevtModuleSw-LSB1F32GCA                  OBJECT IDENTIFIER ::= { unisevtModuleSwitchType 190 } -- 32 Ports FE and 4 Ports GE Line Card(CA)
unisevtModuleSw-LSB1P4G8CA                  OBJECT IDENTIFIER ::= { unisevtModuleSwitchType 191 } -- 4 Ports OC-3c POS and 8 Ports GE Line Card(CA)
unisevtModuleSw-LSB1GT12CA                  OBJECT IDENTIFIER ::= { unisevtModuleSwitchType 192 } -- 12 Ports 1000Base-T Ethernet Interface Line Card(CA)
unisevtModuleSw-LSB1GT24CA                  OBJECT IDENTIFIER ::= { unisevtModuleSwitchType 193 } -- 24 Ports 1000Base-T Ethernet Interface Line Card(CA)
unisevtModuleSw-LSB1GP12CA                  OBJECT IDENTIFIER ::= { unisevtModuleSwitchType 194 } -- 12 Ports 1000Base Ethernet Optical Interface Service Card(CA)
unisevtModuleSw-LSB1GP24CA                  OBJECT IDENTIFIER ::= { unisevtModuleSwitchType 195 } -- 24 Ports 1000Base-X Ethernet Interface Line Card (CA)
unisevtModuleSw-LSB1GT8PCA                  OBJECT IDENTIFIER ::= { unisevtModuleSwitchType 196 } -- 8 Ports 1000Base-T Ethernet Interface & 4 Ports 1000Base-X Ethernet SFP Interface Line Card(CA)
unisevtModuleSw-LSB1XP2CA                   OBJECT IDENTIFIER ::= { unisevtModuleSwitchType 197 } -- 2-Port 10GBase-R/W Ethernet XFP Optical Interface Card(CA)
unisevtModuleSw-LSB1XK1CA                   OBJECT IDENTIFIER ::= { unisevtModuleSwitchType 198 } -- 10GBase-R Ethernet XENPAK Optical Interface Line Card(CA)
unisevtModuleSw-LSB1XP4CA                   OBJECT IDENTIFIER ::= { unisevtModuleSwitchType 199 } -- 4-Port 10GBase-R/X Ethernet Optical Interface Line Card(CA)
unisevtModuleSw-LSB1UP1CA                   OBJECT IDENTIFIER ::= { unisevtModuleSwitchType 200 } -- Single Port OC-192c POS XFP Optical Interface Card(CA)
unisevtModuleSw-LSB1SP4CA                   OBJECT IDENTIFIER ::= { unisevtModuleSwitchType 201 } -- 4-Port OC-48c POS SFP Optical Interface Card(CA)
unisevtModuleSw-LSB1VP2CA                   OBJECT IDENTIFIER ::= { unisevtModuleSwitchType 202 } -- 2*10G RPR Process Unit(CA)
unisevtModuleSw-SR01FT48WA                  OBJECT IDENTIFIER ::= { unisevtModuleSwitchType 203 } -- 48 Ports 100Base-TX Ethernet Line Card (WA)
unisevtModuleSw-SR01FP20WA                  OBJECT IDENTIFIER ::= { unisevtModuleSwitchType 204 } -- 20 Ports 100Base-FX Ethernet Interface Service Card (WA)
unisevtModuleSw-SR01F32GWA                  OBJECT IDENTIFIER ::= { unisevtModuleSwitchType 205 } -- 32 Ports FE and 4 Ports GE Line Card(WA)
unisevtModuleSw-SR01P4G8WA                  OBJECT IDENTIFIER ::= { unisevtModuleSwitchType 206 } -- 4 Ports OC-3c POS and 8 Ports GE Line Card(WA)
unisevtModuleSw-SR01GT12WA                  OBJECT IDENTIFIER ::= { unisevtModuleSwitchType 207 } -- 12 Ports 1000Base-T Ethernet Interface Line Card(WA)
unisevtModuleSw-SR01GT24WA                  OBJECT IDENTIFIER ::= { unisevtModuleSwitchType 208 } -- 24 Ports 1000Base-T Ethernet Interface Line Card(WA)
unisevtModuleSw-SR01GP12WA                  OBJECT IDENTIFIER ::= { unisevtModuleSwitchType 209 } -- 12 Ports 1000Base Ethernet Optical Interface Service Card(WA)
unisevtModuleSw-SR01GP24WA                  OBJECT IDENTIFIER ::= { unisevtModuleSwitchType 210 } -- 24 Ports 1000Base-X Ethernet Interface Line Card (WA)
unisevtModuleSw-SR01GT8PWA                  OBJECT IDENTIFIER ::= { unisevtModuleSwitchType 211 } -- 8 Ports 1000Base-T Ethernet Interface & 4 Ports 1000Base-X Ethernet SFP Interface Line Card(WA)
unisevtModuleSw-SR01XP2WA                   OBJECT IDENTIFIER ::= { unisevtModuleSwitchType 212 } -- 2-Port 10GBase-R/W Ethernet XFP Optical Interface Card(WA)
unisevtModuleSw-SR01XK1WA                   OBJECT IDENTIFIER ::= { unisevtModuleSwitchType 213 } -- 10GBase-R Ethernet XENPAK Optical Interface Line Card(WA)
unisevtModuleSw-SR01UP1WA                   OBJECT IDENTIFIER ::= { unisevtModuleSwitchType 214 } -- Single Port OC-192c POS XFP Optical Interface Card(WA)
unisevtModuleSw-SR01SP4WA                   OBJECT IDENTIFIER ::= { unisevtModuleSwitchType 215 } -- 4-Port OC-48c POS SFP Optical Interface Card(WA)
unisevtModuleSw-GP8U                        OBJECT IDENTIFIER ::= { unisevtModuleSwitchType 216 } -- 8-Port 1000Base-X SFP Optical Interface Module
unisevtModuleSw-LSEXP1P                     OBJECT IDENTIFIER ::= { unisevtModuleSwitchType 217 } -- Single 10G SFP Optical Interface Module
unisevtModuleSw-LSEXK1P                     OBJECT IDENTIFIER ::= { unisevtModuleSwitchType 218 } -- Single 10G XENPAK Interface Module
unisevtModuleSw-LSEXS1P                     OBJECT IDENTIFIER ::= { unisevtModuleSwitchType 219 } -- Single 10G STACK Interface Module
unisevtModuleSw-LS81GP48                    OBJECT IDENTIFIER ::= { unisevtModuleSwitchType 220 } -- 48-Port 1000M Ethernet Optical Interface Board(SFP,LC),LC Connector
unisevtModuleSw-LS81GT48B                   OBJECT IDENTIFIER ::= { unisevtModuleSwitchType 221 } -- 48-Port 1000Base-T Gigabit Ethernet Interface Board(RJ45)
unisevtModuleSw-LS81T16P                    OBJECT IDENTIFIER ::= { unisevtModuleSwitchType 222 } -- 16-Port 1000Base-T Gigabit Ethernet Interface(RJ45) + 8-Port 1000BASE-X Gigabit Ethernet Optical Interface Board(SFP,LC)
unisevtModuleSw-LS81T32P                    OBJECT IDENTIFIER ::= { unisevtModuleSwitchType 223 } -- 32-Port 1000Base-T Gigabit Ethernet Interface(RJ45) + 16-Port 1000BASE-X Gigabit Ethernet Optical Interface Board(SFP,LC)
unisevtModuleSw-LS81TGX2                    OBJECT IDENTIFIER ::= { unisevtModuleSwitchType 224 } -- 2-Port 10GBASE Ethernet Interface Board(XFP,LC)
unisevtModuleSw-LS81TGX4                    OBJECT IDENTIFIER ::= { unisevtModuleSwitchType 225 } -- 4-Port 10GBASE Ethernet Interface Module(XFP,LC),XG
unisevtModuleSw-LSB1GV48DA                  OBJECT IDENTIFIER ::= { unisevtModuleSwitchType 226 } -- 48 Ports 1000Base-T Ethernet Interface Line Card with POE(DA)
unisevtModuleSw-SR01GV48VB                  OBJECT IDENTIFIER ::= { unisevtModuleSwitchType 227 } -- 48 Ports 1000Base-T Ethernet Interface Line Card with POE(VB)
unisevtModuleSw-LSB1GT24DB                  OBJECT IDENTIFIER ::= { unisevtModuleSwitchType 228 } -- 24 Ports 1000Base-T Ethernet Interface Line Card(DB)
unisevtModuleSw-LSB1GP24DB                  OBJECT IDENTIFIER ::= { unisevtModuleSwitchType 229 } -- 24 Ports 1000Base-X Ethernet Interface Line Card(DB)
unisevtModuleSw-LSB1GP24DC                  OBJECT IDENTIFIER ::= { unisevtModuleSwitchType 230 } -- 24 Ports 1000Base-X Ethernet Interface Line Card(DC)
unisevtModuleSw-LSB1FW8DB                   OBJECT IDENTIFIER ::= { unisevtModuleSwitchType 231 } -- 8-port 1000BASE-X (SFP) Firewall Service Card(DB)
unisevtModuleSw-LSB1IPSEC8DB                OBJECT IDENTIFIER ::= { unisevtModuleSwitchType 232 } -- 8-port 1000BASE-X (SFP) IPSEC Service Card(DB)
unisevtModuleSw-SR01GT24VB                  OBJECT IDENTIFIER ::= { unisevtModuleSwitchType 233 } -- 24 Ports 1000Base-T Ethernet Interface Line Card(VB)
unisevtModuleSw-SR01GP24VC                  OBJECT IDENTIFIER ::= { unisevtModuleSwitchType 234 } -- 24 Ports 1000Base-X Ethernet Interface Line Card(VC)
unisevtModuleSw-SR01VP2WA                   OBJECT IDENTIFIER ::= { unisevtModuleSwitchType 235 } -- 2*10G RPR Process Unit(WA)
unisevtModuleSw-SR01FW8VB                   OBJECT IDENTIFIER ::= { unisevtModuleSwitchType 236 } -- 8-port 1000BASE-X (SFP) Firewall Service Card(VB)
unisevtModuleSw-SR01IPSEC8VB                OBJECT IDENTIFIER ::= { unisevtModuleSwitchType 237 } -- 8-port 1000BASE-X (SFP) IPSEC Service Card(VB)
unisevtModuleSw-SR01NATL                    OBJECT IDENTIFIER ::= { unisevtModuleSwitchType 238 } -- NAT Service Processing Card (L)
unisevtModuleSw-SR01VPNL                    OBJECT IDENTIFIER ::= { unisevtModuleSwitchType 239 } -- VPN Service Processing Card (L)
unisevtModuleSw-LSB1GP24CB                  OBJECT IDENTIFIER ::= { unisevtModuleSwitchType 240 } -- 24 Ports 1000Base-X Ethernet Interface Line Card(CB)
unisevtModuleSw-LSB1GP48DB                  OBJECT IDENTIFIER ::= { unisevtModuleSwitchType 241 } -- 48-Port Gigabit Ethernet Optical Interface Line Card(DB)
unisevtModuleSw-LSB1XP2CB                   OBJECT IDENTIFIER ::= { unisevtModuleSwitchType 242 } -- 2-Port 10Gigabit Ethernet Optical Interface Card(CB)
unisevtModuleSw-XP4L                        OBJECT IDENTIFIER ::= { unisevtModuleSwitchType 243 } -- 4 Port 1000BASE Optic Interface Module (XFP)
unisevtModuleSw-LSB1XP4LDB                  OBJECT IDENTIFIER ::= { unisevtModuleSwitchType 244 } -- 4-Port 10GBase-R/W Ethernet XFP Optical Interface Line Speed Card(DB)
unisevtModuleSw-LSB1XP4LDC                  OBJECT IDENTIFIER ::= { unisevtModuleSwitchType 245 } -- 4-Port 10GBase-R/W Ethernet XFP Optical Interface Line Speed Card(DC)
unisevtModuleSw-AHP4                        OBJECT IDENTIFIER ::= { unisevtModuleSwitchType 246 } -- 2-Port OC-3 ATM and 2-Port OC-3/12 ATM Interface Module (SFP)
unisevtModuleSw-LSB1AHP4GCA                 OBJECT IDENTIFIER ::= { unisevtModuleSwitchType 247 } -- 2-Port OC-3 ATM and 2-Port OC-3/12 ATM and 8-Port 1000Base-X Ethernet Optical Interface Line Card(CA)
unisevtModuleSw-CLP4                        OBJECT IDENTIFIER ::= { unisevtModuleSwitchType 248 } -- 4 Ports OC-3/STM-1 CPOS Optical Interface Module (SFP)
unisevtModuleSw-LSB1CLP4GCA                 OBJECT IDENTIFIER ::= { unisevtModuleSwitchType 249 } -- 4 Ports OC-3/STM-1 CPOS Optical Interface and 4-Port 1000Base-X Ethernet Optical Interface Line Card(CA)
unisevtModuleSw-ET32                        OBJECT IDENTIFIER ::= { unisevtModuleSwitchType 250 } -- 32-Port Channelized E1/T1 Interface Module
unisevtModuleSw-LSB1ET32GCA                 OBJECT IDENTIFIER ::= { unisevtModuleSwitchType 251 } -- 32-Port Channelized E1/T1 Interface and 4-Port 1000Base-X Ethernet Optical Interface Line Card(CA)
unisevtModuleSw-LSB1IDSDB                   OBJECT IDENTIFIER ::= { unisevtModuleSwitchType 252 } -- Intrusion Detection Service Card(DB)
unisevtModuleSw-LSB1SRP2N1                  OBJECT IDENTIFIER ::= { unisevtModuleSwitchType 253 } -- Switching and Route Processing Board,8*LPU
unisevtModuleSw-BOARD-LS82SRPB              OBJECT IDENTIFIER ::= { unisevtModuleSwitchType 254 }
unisevtModuleSw-BORAD-LS83SRPC              OBJECT IDENTIFIER ::= { unisevtModuleSwitchType 255 }
unisevtModuleSw-Main                        OBJECT IDENTIFIER ::= { unisevtModuleSwitchType 256 }
unisevtModuleSw-LSB1SRP2N2                  OBJECT IDENTIFIER ::= { unisevtModuleSwitchType 257 } -- Switching and Route Processing Board,5*LPU
unisevtModuleSw-LSB1NAMB                    OBJECT IDENTIFIER ::= { unisevtModuleSwitchType 258 } -- NAM Service Processing Card (B)
unisevtModuleSw-RSP2                        OBJECT IDENTIFIER ::= { unisevtModuleSwitchType 259 } -- 2*2.5G Resilient Packet Ring Interface
unisevtModuleSw-LSB1RSP2CA                  OBJECT IDENTIFIER ::= { unisevtModuleSwitchType 260 } -- 2*2.5G Resilient Packet Ring Interface Line Card(CA)
unisevtModuleSw-SR01XP4LVC                  OBJECT IDENTIFIER ::= { unisevtModuleSwitchType 261 } -- 4-Port 10GBase-R/W Ethernet XFP Optical Interface Line Speed Card(VC)
unisevtModuleSw-SR01AHP4GWA                 OBJECT IDENTIFIER ::= { unisevtModuleSwitchType 262 } -- 2-Port OC-3 ATM and 2-Port OC-3/12 ATM and 8-Port 1000Base-X Ethernet Optical Interface Line Card(WA)
unisevtModuleSw-SR01CLP4GWA                 OBJECT IDENTIFIER ::= { unisevtModuleSwitchType 263 } -- 4 Ports OC-3/STM-1 CPOS Optical Interface and 4-Port 1000Base-X Ethernet Optical Interface Line Card(WA)
unisevtModuleSw-SR01ET32GWA                 OBJECT IDENTIFIER ::= { unisevtModuleSwitchType 264 } -- 32-Port Channelized E1/T1 Interface and 4-Port 1000Base-X Ethernet Optical Interface Line Card(WA)
unisevtModuleSw-SR01IDSVB                   OBJECT IDENTIFIER ::= { unisevtModuleSwitchType 265 } -- Intrusion Detection Service Card(VB)
unisevtModuleSw-SR01SRPUF                   OBJECT IDENTIFIER ::= { unisevtModuleSwitchType 266 } -- Switching and Route Processing Board,12*LPU
unisevtModuleSw-SR01NAML                    OBJECT IDENTIFIER ::= { unisevtModuleSwitchType 267 } -- NAM Service Processing Card (L)
unisevtModuleSw-SR01RSP2WA                  OBJECT IDENTIFIER ::= { unisevtModuleSwitchType 268 } -- 2*2.5G Resilient Packet Ring Interface Line Card(WA)
unisevtModuleSw-LSPM1XP1P                   OBJECT IDENTIFIER ::= { unisevtModuleSwitchType 269 } -- 1-Port 10G XFP Module
unisevtModuleSw-LSPM1XP2P                   OBJECT IDENTIFIER ::= { unisevtModuleSwitchType 270 } -- 2-Port 10G XFP Module
unisevtModuleSw-LSPM1CX2P                   OBJECT IDENTIFIER ::= { unisevtModuleSwitchType 271 } -- 2-Port 10G CX4 Module
unisevtModuleSw-STK-1000BASE-T              OBJECT IDENTIFIER ::= { unisevtModuleSwitchType 272 } -- Single Port 1000BASE-T Stack Ethernet Interface Card

--
-- 273 to 299 reserved for other product
--


--
-- 300 to 499 reserved for advanced switches part I
--
unisevtModuleSw-LSB1SRP1M0                  OBJECT IDENTIFIER ::= { unisevtModuleSwitchType 300 } -- Switching and Route Process Unit,2*LPU or 3*LPU
unisevtModuleSw-LSB1SRP1M1                  OBJECT IDENTIFIER ::= { unisevtModuleSwitchType 301 } -- Switching and Route Process Unit
unisevtModuleSw-LSB1GP12DB                  OBJECT IDENTIFIER ::= { unisevtModuleSwitchType 302 } -- 12 Ports 1000Base Ethernet Optical Interface Service Card(DB)
unisevtModuleSw-LSB1GT12DB                  OBJECT IDENTIFIER ::= { unisevtModuleSwitchType 303 } -- 12 Ports 1000Base-T Ethernet Interface Line Card(DB)
unisevtModuleSw-LSB1XK1DB                   OBJECT IDENTIFIER ::= { unisevtModuleSwitchType 304 } -- 10GBase-R Ethernet XENPAK Optical Interface Line Card(DB)
unisevtModuleSw-LSB1XP2DB                   OBJECT IDENTIFIER ::= { unisevtModuleSwitchType 305 } -- 2-Port 10GBase-R/W Ethernet XFP Optical Interface Card(DB)
unisevtModuleSw-LSB1XP2DC                   OBJECT IDENTIFIER ::= { unisevtModuleSwitchType 306 } -- 2-Port 10GBase-R/W Ethernet XFP Optical Interface Card(DC)
unisevtModuleSw-LSB1GT48LDB                 OBJECT IDENTIFIER ::= { unisevtModuleSwitchType 307 } -- 48-Port Gigabit Ethernet RJ45 Electrical Interface Card (DB)
unisevtModuleSw-LSB1XP4TDB                  OBJECT IDENTIFIER ::= { unisevtModuleSwitchType 308 } -- 4-Port 10GBase-R/W Ethernet XFP Optical Interface Line Speed Test Card(DB)
unisevtModuleSw-LSB1XP4TDC                  OBJECT IDENTIFIER ::= { unisevtModuleSwitchType 309 } -- 4-Port 10GBase-R/W Ethernet XFP Optical Interface Line Speed Test Card(DC)
unisevtModuleSw-LSB1RSP2DC                  OBJECT IDENTIFIER ::= { unisevtModuleSwitchType 310 } -- 2*2.5G Resilient Packet Ring Interface Line Card(DC)
unisevtModuleSw-LSB1VP2DC                   OBJECT IDENTIFIER ::= { unisevtModuleSwitchType 311 } -- 2*10G Resilient Packet Ring Process Unit(DC)
unisevtModuleSw-LSB1XP4DB                   OBJECT IDENTIFIER ::= { unisevtModuleSwitchType 312 } -- 4-Port 10GBase-R/X Ethernet Optical Interface Line Card(DB)
unisevtModuleSw-LSB1SRP2E0                  OBJECT IDENTIFIER ::= { unisevtModuleSwitchType 313 } -- Switching and Route Process Unit,12*LPU
unisevtModuleSw-LSB1SRP2E1                  OBJECT IDENTIFIER ::= { unisevtModuleSwitchType 314 } -- Switching and Route Process Unit,8*LPU
unisevtModuleSw-LSB1SRP2E2                  OBJECT IDENTIFIER ::= { unisevtModuleSwitchType 315 } -- Switching and Route Process Unit,5*LPU
unisevtModuleSw-LSB1SRP2E3                  OBJECT IDENTIFIER ::= { unisevtModuleSwitchType 316 } -- Switching and Route Process Unit, Clock module
unisevtModuleSw-SR01SRPUQ                   OBJECT IDENTIFIER ::= { unisevtModuleSwitchType 317 } -- Switching and Route Processing Unit Q
unisevtModuleSw-AHP1                        OBJECT IDENTIFIER ::= { unisevtModuleSwitchType 318 } -- 1-Port OC-12c(3c)/STM-4(1) ATM Optical Interface Module(SFP)
unisevtModuleSw-AHP2                        OBJECT IDENTIFIER ::= { unisevtModuleSwitchType 319 } -- 2-Port OC-12c(3c)/STM-4(1) ATM Optical Interface Module(SFP)
unisevtModuleSw-CLP1                        OBJECT IDENTIFIER ::= { unisevtModuleSwitchType 320 } -- 1-Port OC-3/STM-1 CPOS Optical Interface Module(SFP)
unisevtModuleSw-CLP2                        OBJECT IDENTIFIER ::= { unisevtModuleSwitchType 321 } -- 2-Port OC-3/STM-1 CPOS Optical Interface Module(SFP)
unisevtModuleSw-ET16                        OBJECT IDENTIFIER ::= { unisevtModuleSwitchType 322 } -- 16-Port Channelized E1/T1 Interface Module
unisevtModuleSw-LSB1SRP1NA0                 OBJECT IDENTIFIER ::= { unisevtModuleSwitchType 323 } -- Switching and Route Process Unit,12*LPU
unisevtModuleSw-LSB1SRP1NA1                 OBJECT IDENTIFIER ::= { unisevtModuleSwitchType 324 } -- Switching and Route Process Unit,8*LPU
unisevtModuleSw-LSB1SRP1NA2                 OBJECT IDENTIFIER ::= { unisevtModuleSwitchType 325 } -- Switching and Route Process Unit,5*LPU
unisevtModuleSw-LSB1SRP1NA3                 OBJECT IDENTIFIER ::= { unisevtModuleSwitchType 326 } -- Switching and Route Process Unit, Clock module
unisevtModuleSw-SR01AHP1GWA                 OBJECT IDENTIFIER ::= { unisevtModuleSwitchType 327 } -- 1-Port OC-12c(3c)/STM-4(1) ATM Optical Interface and 4-Port 1000Base-X Ethernet Optical Interface Line Card(WA)
unisevtModuleSw-SR01AHP2GWA                 OBJECT IDENTIFIER ::= { unisevtModuleSwitchType 328 } -- 2-Port OC-12c(3c)/STM-4(1) ATM Optical Interface and 4-Port 1000Base-X Ethernet Optical Interface Line Card(WA)
unisevtModuleSw-SR01CLP1GWA                 OBJECT IDENTIFIER ::= { unisevtModuleSwitchType 329 } -- 1-Port OC-3/STM-1 CPOS Optical Interface and 4-Port 1000Base-X Ethernet Optical Interface Line Card(WA)
unisevtModuleSw-SR01CLP2GWA                 OBJECT IDENTIFIER ::= { unisevtModuleSwitchType 330 } -- 2-Port OC-3/STM-1 CPOS Optical Interface and 4-Port 1000Base-X Ethernet Optical Interface Line Card(WA)
unisevtModuleSw-SR01ET16GWA                 OBJECT IDENTIFIER ::= { unisevtModuleSwitchType 331 } -- 16-Port Channelized E1/T1 Interface and  4-Port 1000Base-X Ethernet Optical Interface Line Card(WA)
unisevtModuleSw-SR01GP12VB                  OBJECT IDENTIFIER ::= { unisevtModuleSwitchType 332 } -- 12-Port Gigabit Ethernet Optical Interface Card(VB)
unisevtModuleSw-SR01XK1VB                   OBJECT IDENTIFIER ::= { unisevtModuleSwitchType 333 } -- 1-Port 10Gigabit Ethernet Optical Interface Card(VB)
unisevtModuleSw-SR01XP2VC                   OBJECT IDENTIFIER ::= { unisevtModuleSwitchType 334 } -- 2-Port 10GBase-RW Ethernet XFP Optical Interface Line Card(VC)
unisevtModuleSw-SR01XP4LVB                  OBJECT IDENTIFIER ::= { unisevtModuleSwitchType 335 } -- 4-Port 10GBase-R/W Ethernet XFP Optical Interface Line Speed Card(VB)
unisevtModuleSw-SR01SRPUEA                  OBJECT IDENTIFIER ::= { unisevtModuleSwitchType 336 } -- Switching and Route Process Unit, Clock Module
unisevtModuleSw-LSB1SRP1N4                  OBJECT IDENTIFIER ::= { unisevtModuleSwitchType 337 } -- Switching and Route Process Unit, 12*LPU
unisevtModuleSw-LSB1SRP1N5                  OBJECT IDENTIFIER ::= { unisevtModuleSwitchType 338 } -- Switching and Route Process Unit, 8*LPU
unisevtModuleSw-LSB1SRP1N6                  OBJECT IDENTIFIER ::= { unisevtModuleSwitchType 339 } -- Switching and Route Process Unit, 5*LPU
unisevtModuleSw-LSB1SRP1N7                  OBJECT IDENTIFIER ::= { unisevtModuleSwitchType 340 } -- Switching and Route Process Unit, Clock Module
unisevtModuleSw-LSB1SRP2N4                  OBJECT IDENTIFIER ::= { unisevtModuleSwitchType 341 } -- Switching and Route Process Unit, 12*LPU
unisevtModuleSw-LSB1SRP2N5                  OBJECT IDENTIFIER ::= { unisevtModuleSwitchType 342 } -- Switching and Route Process Unit, 8*LPU
unisevtModuleSw-LSB1SRP2N6                  OBJECT IDENTIFIER ::= { unisevtModuleSwitchType 343 } -- Switching and Route Process Unit, 5*LPU
unisevtModuleSw-LSB1SRP2N7                  OBJECT IDENTIFIER ::= { unisevtModuleSwitchType 344 } -- Switching and Route Process Unit, Clock Module
unisevtModuleSw-LSB1SRP1NA4                 OBJECT IDENTIFIER ::= { unisevtModuleSwitchType 345 } -- Switching and Route Process Unit, 12*LPU
unisevtModuleSw-LSB1SRP1NA5                 OBJECT IDENTIFIER ::= { unisevtModuleSwitchType 346 } -- Switching and Route Process Unit, 8*LPU
unisevtModuleSw-LSB1SRP1NA6                 OBJECT IDENTIFIER ::= { unisevtModuleSwitchType 347 } -- Switching and Route Process Unit, 5*LPU
unisevtModuleSw-LSB1SRP1NA7                 OBJECT IDENTIFIER ::= { unisevtModuleSwitchType 348 } -- Switching and Route Process Unit, Clock Module
unisevtModuleSw-LSB2GV48DA                  OBJECT IDENTIFIER ::= { unisevtModuleSwitchType 349 } -- 48-Ports 1000Base-T Ethernet Interface Line Card with POE(DA)
unisevtModuleSw-LSB1RGP2GDB                 OBJECT IDENTIFIER ::= { unisevtModuleSwitchType 350 } -- 2-Port GE RPR and 8-Port GE Optical Interface Service Card(DB)
unisevtModuleSw-LSB1RGP4GDB                 OBJECT IDENTIFIER ::= { unisevtModuleSwitchType 351 } -- 4-Port GE RPR and 8-Port GE Optical Interface Service Card(DB)
unisevtModuleSw-LSB2GP24DB                  OBJECT IDENTIFIER ::= { unisevtModuleSwitchType 352 } -- 24-Port 1000BASE-X  Interface Module(DB),(SFP,LC)
unisevtModuleSw-LSB2GP24DC                  OBJECT IDENTIFIER ::= { unisevtModuleSwitchType 353 } -- 24-Port 1000BASE-X  Interface Module(DC),(SFP,LC)
unisevtModuleSw-LSB2GT24DB                  OBJECT IDENTIFIER ::= { unisevtModuleSwitchType 354 } -- 24-Port 10/100/1000BASE-T Interface Module(DB),(RJ45)
unisevtModuleSw-LSB2FW8DB                   OBJECT IDENTIFIER ::= { unisevtModuleSwitchType 355 } -- 8-Port 1000BASE-X Interface Firewall Service Module(DB),(SFP,LC)
unisevtModuleSw-LSB2IPSEC8DB                OBJECT IDENTIFIER ::= { unisevtModuleSwitchType 356 } -- 8-Port 1000BASE-X Interface IPSEC Service Module(DB),(SFP,LC)
unisevtModuleSw-LSB2GV48DB                  OBJECT IDENTIFIER ::= { unisevtModuleSwitchType 357 } -- 48-Port 10/100/1000BASE-T Interface Module(DB),(PoE,RJ45)
unisevtModuleSw-RGP2                        OBJECT IDENTIFIER ::= { unisevtModuleSwitchType 358 } -- 2-Port GE Resilient Packet Ring Interface Module
unisevtModuleSw-RGP4                        OBJECT IDENTIFIER ::= { unisevtModuleSwitchType 359 } -- 4-Port GE Resilient Packet Ring Interface Module
unisevtModuleSw-SR02FW8VB                   OBJECT IDENTIFIER ::= { unisevtModuleSwitchType 360 } -- 8-Port 1000BASE-X Interface Firewall Service Module(VB),(SFP,LC)
unisevtModuleSw-SR02IPSEC8VB                OBJECT IDENTIFIER ::= { unisevtModuleSwitchType 361 } -- 8-Port 1000BASE-X Interface IPSEC Service Module(VB),(SFP,LC)
unisevtModuleSw-LSB2SRP1N0                  OBJECT IDENTIFIER ::= { unisevtModuleSwitchType 362 } -- Switching and Route Process Unit, 12*LPU
unisevtModuleSw-LSB2SRP1N1                  OBJECT IDENTIFIER ::= { unisevtModuleSwitchType 363 } -- Switching and Route Process Unit, 8*LPU
unisevtModuleSw-LSB2SRP1N2                  OBJECT IDENTIFIER ::= { unisevtModuleSwitchType 364 } -- Switching and Route Process Unit, 5*LPU
unisevtModuleSw-LSB2SRP1N3                  OBJECT IDENTIFIER ::= { unisevtModuleSwitchType 365 } -- Switching and Route Process Unit, Clock module
unisevtModuleSw-LSB2SRP1N4                  OBJECT IDENTIFIER ::= { unisevtModuleSwitchType 366 } -- Switching and Route Process Unit, 12*LPU
unisevtModuleSw-LSB2SRP1N5                  OBJECT IDENTIFIER ::= { unisevtModuleSwitchType 367 } -- Switching and Route Process Unit, 8*LPU
unisevtModuleSw-LSB2SRP1N6                  OBJECT IDENTIFIER ::= { unisevtModuleSwitchType 368 } -- Switching and Route Process Unit, 5*LPU
unisevtModuleSw-LSB2SRP1N7                  OBJECT IDENTIFIER ::= { unisevtModuleSwitchType 369 } -- Switching and Route Process Unit, Clock module
unisevtModuleSw-SR02SRPUE                   OBJECT IDENTIFIER ::= { unisevtModuleSwitchType 370 } -- Switching and Route Process Unit, Clock module
unisevtModuleSw-SR01LN1BQH0                 OBJECT IDENTIFIER ::= { unisevtModuleSwitchType 371 } -- Single XG Service Board(BQH)
unisevtModuleSw-SR01DXP1L                   OBJECT IDENTIFIER ::= { unisevtModuleSwitchType 372 } -- 1-Port 10GBASE-R/W Ethernet Optical Interface Card,(XFP,LC)
unisevtModuleSw-SR01DGP10L                  OBJECT IDENTIFIER ::= { unisevtModuleSwitchType 373 } -- 10-Port 1000BASE-X Optical Interface Card,(SFP,LC)
unisevtModuleSw-SR01DRSP2L                  OBJECT IDENTIFIER ::= { unisevtModuleSwitchType 374 } -- 2-Port 2.5G RPR Optical Interface Card,(SFP,LC)
unisevtModuleSw-SR01DRUP1L                  OBJECT IDENTIFIER ::= { unisevtModuleSwitchType 375 } -- 1-Port 10G RPR Optical Interface Card,(XFP,LC)
unisevtModuleSw-SR01DGP20R                  OBJECT IDENTIFIER ::= { unisevtModuleSwitchType 376 } -- 20-Port 1000BASE-X Optical Interface Card,(SFP,LC)
unisevtModuleSw-SR01DPLP8L                  OBJECT IDENTIFIER ::= { unisevtModuleSwitchType 377 } -- 8-Port 155M POS Optical Interface Card,(SFP,LC)
unisevtModuleSw-SR01DXP2R                   OBJECT IDENTIFIER ::= { unisevtModuleSwitchType 378 } -- 2-Port 10GBASE-R/W Ethernet Optical Interface Card,(XFP,LC)
unisevtModuleSw-LSB1FW2A0                   OBJECT IDENTIFIER ::= { unisevtModuleSwitchType 379 } -- Gigabit Firewall Card, 4 Gigabit Port for Management
unisevtModuleSw-LSB1GP48LDB                 OBJECT IDENTIFIER ::= { unisevtModuleSwitchType 380 } -- 48-Port Line Rate Gigabit Ethernet Optical Interface Card(DB)
unisevtModuleSw-SR01LN1BNA0                 OBJECT IDENTIFIER ::= { unisevtModuleSwitchType 381 } -- Single XG Service Board(BNA)
unisevtModuleSw-SR01LN2BQH0                 OBJECT IDENTIFIER ::= { unisevtModuleSwitchType 382 } -- Dual XG Service Board(BQH)
unisevtModuleSw-SR01LN2BNA0                 OBJECT IDENTIFIER ::= { unisevtModuleSwitchType 383 } -- Dual XG Service Board(BNA)
unisevtModuleSw-SR01DGT20R                  OBJECT IDENTIFIER ::= { unisevtModuleSwitchType 384 } -- 20-Port 10/100/1000BASE-T Electrical Interface Card,(RJ45)
unisevtModuleSw-SR01DPSP4L                  OBJECT IDENTIFIER ::= { unisevtModuleSwitchType 385 } -- 4-Port 2.5G POS Optical Interface Card(SFP,LC)
unisevtModuleSw-SR01DPUP1L                  OBJECT IDENTIFIER ::= { unisevtModuleSwitchType 386 } -- 1-Port 10G POS Optical Interface Card,(XFP,LC)
unisevtModuleSw-SR01DPL2G6L                 OBJECT IDENTIFIER ::= { unisevtModuleSwitchType 387 } -- 2-Port 155M POS Optical Interface(SFP,LC)+6-Port 1000BASE-X Optical Interface Card(SFP,LC)
unisevtModuleSw-SR01DPH2G6L                 OBJECT IDENTIFIER ::= { unisevtModuleSwitchType 388 } -- 2-Port 622M POS Optical Interface(SFP,LC)+6-Port 1000BASE-X Optical Interface Card(SFP,LC)
unisevtModuleSw-SR01DPS2G4L                 OBJECT IDENTIFIER ::= { unisevtModuleSwitchType 389 } -- 2-Port 2.5G POS Optical Interface(SFP,LC)+4-Port 1000BASE-X Optical Interface Card(SFP,LC)
unisevtModuleSw-SR01DCL1G8L                 OBJECT IDENTIFIER ::= { unisevtModuleSwitchType 390 } -- 1-Port 155M CPOS Optical Interface(SFP,LC)+8-Port 1000BASE-X Optical Interface Card(SFP,LC)
unisevtModuleSw-SR01DCL2G8L                 OBJECT IDENTIFIER ::= { unisevtModuleSwitchType 391 } -- 2-Port 155M CPOS Optical Interface(SFP,LC)+8-Port 1000BASE-X Optical Interface Card(SFP,LC)
unisevtModuleSw-SR01DET8G8L                 OBJECT IDENTIFIER ::= { unisevtModuleSwitchType 392 } -- 8-Port E1/T1 Electrical Interface(RJ45)+8-Port 1000BASE-X Optical Interface Card(SFP,LC)
unisevtModuleSw-SR02SRP2E3                  OBJECT IDENTIFIER ::= { unisevtModuleSwitchType 393 } -- Switching and Route Process Unit, Clock module
unisevtModuleSw-SR02SRP1E3                  OBJECT IDENTIFIER ::= { unisevtModuleSwitchType 394 } -- Switching and Route Process Unit, Clock module
unisevtModuleSw-SR02SRP1M3                  OBJECT IDENTIFIER ::= { unisevtModuleSwitchType 395 } -- Switching and Route Process Unit, Clock module
unisevtModuleSw-SR01DQCP4L                  OBJECT IDENTIFIER ::= { unisevtModuleSwitchType 396 } -- 4-Port OC-3c/OC-12c/OC-48c POS/GE Optical Interface Card,(SFP,LC)
unisevtModuleSw-SR01DTCP8L                  OBJECT IDENTIFIER ::= { unisevtModuleSwitchType 397 } -- 8-Port OC-3c/OC-12c POS/GE Optical Interface Card,(SFP,LC)
unisevtModuleSw-LSB1AFC1A0                  OBJECT IDENTIFIER ::= { unisevtModuleSwitchType 398 } -- Anomaly Flow Cleaner Board
unisevtModuleSw-LSB1SSL1A0                  OBJECT IDENTIFIER ::= { unisevtModuleSwitchType 399 } -- SSL VPN High-end Board
unisevtModuleSw-IMNAM                       OBJECT IDENTIFIER ::= { unisevtModuleSwitchType 400 } -- Net Analysis Service Processing Board
unisevtModuleSw-IMNAT                       OBJECT IDENTIFIER ::= { unisevtModuleSwitchType 401 } -- Network Address Translation Service Processing Board
unisevtModuleSw-PICAHP1L                    OBJECT IDENTIFIER ::= { unisevtModuleSwitchType 402 } -- 1-Port OC-12c/STM-4c ATM Optical Interface Card,(SFP,LC)
unisevtModuleSw-PICALP4L                    OBJECT IDENTIFIER ::= { unisevtModuleSwitchType 403 } -- 4-Port OC-3c/STM-1c ATM Optical Interface Card,(SFP,LC)
unisevtModuleSw-PICCHP4L                    OBJECT IDENTIFIER ::= { unisevtModuleSwitchType 404 } -- 4-Port 622M CPOS Optical Interface Card(SFP,LC)
unisevtModuleSw-PICCHS1G4L                  OBJECT IDENTIFIER ::= { unisevtModuleSwitchType 405 } -- 1-Port 622M CPOS Optical Interface(Channelized to E3/T3)+4-Port 1000BASE-X Optical Interface Card(SFP,LC)
unisevtModuleSw-PICCLS4G4L                  OBJECT IDENTIFIER ::= { unisevtModuleSwitchType 406 } -- 4-Port 155M CPOS Optical Interface(Channelized to E3/T3)+4-Port 1000BASE-X Optical Interface Card(SFP,LC)
unisevtModuleSw-PICCSP1L                    OBJECT IDENTIFIER ::= { unisevtModuleSwitchType 407 } -- 1-Port 2.5G CPOS Optical Interface Card(SFP,LC)
unisevtModuleSw-LSB1ACG1A0                  OBJECT IDENTIFIER ::= { unisevtModuleSwitchType 408 } -- Application Control Gateway Board
unisevtModuleSw-LST1MRPNC1                  OBJECT IDENTIFIER ::= { unisevtModuleSwitchType 409 } -- Management and Route Process Unit
unisevtModuleSw-LST1SF18B1                  OBJECT IDENTIFIER ::= { unisevtModuleSwitchType 410 } -- S12518 Switch Fabric Card
unisevtModuleSw-LST1SF08B1                  OBJECT IDENTIFIER ::= { unisevtModuleSwitchType 411 } -- S12508 Switch Fabric Card
unisevtModuleSw-LST1GT48LEC1                OBJECT IDENTIFIER ::= { unisevtModuleSwitchType 412 } -- 48-Port 10/100/1000BASE-T Interface Module(LEC),(RJ45)
unisevtModuleSw-LST1GP48LEC1                OBJECT IDENTIFIER ::= { unisevtModuleSwitchType 413 } -- 48-Port 1000BASE-X Interface Module (LEC),(SFP,LC)
unisevtModuleSw-LST1XP4LEC1                 OBJECT IDENTIFIER ::= { unisevtModuleSwitchType 414 } -- 4-Port 10GBASE-R/W Interface Module (LEC),(XFP,LC)
unisevtModuleSw-LST1XP8LEC1                 OBJECT IDENTIFIER ::= { unisevtModuleSwitchType 415 } -- 8-Port 10GBASE-R/W Interface Module (LEC),(XFP,LC)
unisevtModuleSw-LSR1SRP2B1                  OBJECT IDENTIFIER ::= { unisevtModuleSwitchType 416 } -- Switching and Route Process Unit
unisevtModuleSw-LSR1SRP2C1                  OBJECT IDENTIFIER ::= { unisevtModuleSwitchType 417 } -- Switching and Route Process Unit
unisevtModuleSw-LSR1SRP2B2                  OBJECT IDENTIFIER ::= { unisevtModuleSwitchType 418 } -- Switching and Route Process Unit
unisevtModuleSw-LSR1SRP2C2                  OBJECT IDENTIFIER ::= { unisevtModuleSwitchType 419 } -- Switching and Route Process Unit
unisevtModuleSw-LSR1GT24LEC1                OBJECT IDENTIFIER ::= { unisevtModuleSwitchType 420 } -- 16-Port 10/100/1000BASE-T Interface and 8-port 1000BASE-T/1000BASE-X Combo Interface Service Card(LEC)
unisevtModuleSw-LSR1GP24LEB1                OBJECT IDENTIFIER ::= { unisevtModuleSwitchType 421 } -- 16-Port 1000BASE-X Interface and 8-port 1000BASE-T/1000BASE-X Combo Interface Service Card(LEB)
unisevtModuleSw-LSR1GP24LEC1                OBJECT IDENTIFIER ::= { unisevtModuleSwitchType 422 } -- 16-Port 1000BASE-X Interface and 8-port 1000BASE-T/1000BASE-X Combo Interface Service Card(LEC)
unisevtModuleSw-LSR1GT48LEB1                OBJECT IDENTIFIER ::= { unisevtModuleSwitchType 423 } -- 48-Port 10/100/1000BASE-T Interface Module(LEB),(RJ45)
unisevtModuleSw-LSR1GT48LEC1                OBJECT IDENTIFIER ::= { unisevtModuleSwitchType 424 } -- 48-Port 10/100/1000BASE-T Interface Module(LEC),(RJ45)
unisevtModuleSw-LSR1GP48LEB1                OBJECT IDENTIFIER ::= { unisevtModuleSwitchType 425 } -- 48-Port 1000BASE-X Interface Module(LEB),(SFP,LC)
unisevtModuleSw-LSR1GP48LEC1                OBJECT IDENTIFIER ::= { unisevtModuleSwitchType 426 } -- 48-Port 1000BASE-X Interface Module(LEC),(SFP,LC)
unisevtModuleSw-LSR2GV48REB1                OBJECT IDENTIFIER ::= { unisevtModuleSwitchType 427 } -- 48-Port 10/100/1000BASE-T Interface Module(REB),(PoE,RJ45)
unisevtModuleSw-LSR1XP2LEB1                 OBJECT IDENTIFIER ::= { unisevtModuleSwitchType 428 } -- 2-Port 10GBase-R/W Interface Module (LEB),(XFP,LC)
unisevtModuleSw-LSR1XP2LEC1                 OBJECT IDENTIFIER ::= { unisevtModuleSwitchType 429 } -- 2-Port 10GBase-R/W Interface Module (LEC),(XFP,LC)
unisevtModuleSw-LSR1XP4LEB1                 OBJECT IDENTIFIER ::= { unisevtModuleSwitchType 430 } -- 4-Port 10GBase-R/W Interface Module (LEB),(XFP,LC)
unisevtModuleSw-LSR1XP4LEC1                 OBJECT IDENTIFIER ::= { unisevtModuleSwitchType 431 } -- 4-Port 10GBase-R/W Interface Module (LEC),(XFP,LC)
unisevtModuleSw-IMFW                        OBJECT IDENTIFIER ::= { unisevtModuleSwitchType 432 } -- Firewall Service Processing Board
unisevtModuleSw-LSB1LB1A0                   OBJECT IDENTIFIER ::= { unisevtModuleSwitchType 433 } -- Load Balance Board
unisevtModuleSw-LSB1IPS1A0                  OBJECT IDENTIFIER ::= { unisevtModuleSwitchType 434 } -- Gigabit IPS Card
unisevtModuleSw-LST1GT48LEB1                OBJECT IDENTIFIER ::= { unisevtModuleSwitchType 435 } -- 48-Port 10/100/1000BASE-T Interface Module(LEB),(RJ45)
unisevtModuleSw-LST1GP48LEB1                OBJECT IDENTIFIER ::= { unisevtModuleSwitchType 436 } -- 48-Port 1000BASE-X Interface Module (LEB),(SFP,LC)
unisevtModuleSw-LST1XP4LEB1                 OBJECT IDENTIFIER ::= { unisevtModuleSwitchType 437 } -- 4-Port 10GBASE-R/W Interface Module (LEB),(XFP,LC)
unisevtModuleSw-LST1XP8LEB1                 OBJECT IDENTIFIER ::= { unisevtModuleSwitchType 438 } -- 8-Port 10GBASE-R/W Interface Module (LEB),(XFP,LC)
unisevtModuleSw-LST1XP32REB1                OBJECT IDENTIFIER ::= { unisevtModuleSwitchType 439 } -- 32-Port 10GBASE-R Interface Module (REB),(SFP+,LC)
unisevtModuleSw-LST1XP32REC1                OBJECT IDENTIFIER ::= { unisevtModuleSwitchType 440 } -- 32-Port 10GBASE-R Interface Module (REC),(SFP+,LC)
unisevtModuleSw-LSR1FW2A1                   OBJECT IDENTIFIER ::= { unisevtModuleSwitchType 441 } -- Firewall Service Module
unisevtModuleSw-LSR1SSL1A1                  OBJECT IDENTIFIER ::= { unisevtModuleSwitchType 442 } -- SSL VPN Service Module
unisevtModuleSw-SR01DET32G2L                OBJECT IDENTIFIER ::= { unisevtModuleSwitchType 443 } -- 32-Port E1/T1 75ohm Electrical Interface(DB56 Female Socket)+2-Port 1000BASE-X Optical Interface Card(SFP,LC)
unisevtModuleSw-LSR1GP24LEF1                OBJECT IDENTIFIER ::= { unisevtModuleSwitchType 444 } -- 16-Port 1000BASE-X Interface and 8-port 1000BASE-T/1000BASE-X Combo Interface Service Card(LEF)
unisevtModuleSw-LSR1XP4LEF1                 OBJECT IDENTIFIER ::= { unisevtModuleSwitchType 445 } -- 4-Port 10GBASE-R/W Interface Module (LEF),(XFP,LC)
unisevtModuleSw-LSR1LB1A1                   OBJECT IDENTIFIER ::= { unisevtModuleSwitchType 446 } -- Load Balance Module
unisevtModuleSw-LSR1NSM1A1                  OBJECT IDENTIFIER ::= { unisevtModuleSwitchType 447 } -- NetStream Module
unisevtModuleSw-LSR1ACG1A1                  OBJECT IDENTIFIER ::= { unisevtModuleSwitchType 448 } -- Application Control Gateway Service Module
unisevtModuleSw-LSR1IPS1A1                  OBJECT IDENTIFIER ::= { unisevtModuleSwitchType 449 } -- Intrusion Protection System Service Module
unisevtModuleSw-LSR2GP24LEB1                OBJECT IDENTIFIER ::= { unisevtModuleSwitchType 450 } -- 16-Port 1000BASE-X Interface and 8-port 1000BASE-T/1000BASE-X Combo Interface Service Card(LEB)
unisevtModuleSw-LSR2GT24LEB1                OBJECT IDENTIFIER ::= { unisevtModuleSwitchType 451 } -- 16-Port 10/100/1000BASE-T Interface and 8-port 1000BASE-T/1000BASE-X Combo Interface Service Card(LEB)
unisevtModuleSw-LSR2GT48LEB1                OBJECT IDENTIFIER ::= { unisevtModuleSwitchType 452 } -- 48-Port 10/100/1000BASE-T Interface Module(LEB),(RJ45)
unisevtModuleSw-SPC-GP24L                   OBJECT IDENTIFIER ::= { unisevtModuleSwitchType 453 } -- 24-Port 1000BASE-X Interface Service Card,(SFP,LC)
unisevtModuleSw-SPC-GT48L                   OBJECT IDENTIFIER ::= { unisevtModuleSwitchType 454 } -- 48-Port 10/100/1000BASE-T Interface Module,(RJ45)
unisevtModuleSw-SPC-GP48L                   OBJECT IDENTIFIER ::= { unisevtModuleSwitchType 455 } -- 48-Port 1000BASE-X Interface Module,(SFP,LC)
unisevtModuleSw-SPC-XP2L                    OBJECT IDENTIFIER ::= { unisevtModuleSwitchType 456 } -- 2-Port 10GBASE-R/W Interface Service Card,(XFP,LC)
unisevtModuleSw-SPC-XP4L                    OBJECT IDENTIFIER ::= { unisevtModuleSwitchType 457 } -- 4-Port 10GBase-R/W Interface Module,(XFP,LC)
unisevtModuleSw-SR06SRP2E3                  OBJECT IDENTIFIER ::= { unisevtModuleSwitchType 458 } -- SDI,Routing Switch Processing Board
unisevtModuleSw-SPE-2010-E                  OBJECT IDENTIFIER ::= { unisevtModuleSwitchType 459 } -- SDI,Single XG Service Board
unisevtModuleSw-SPE-2020-E                  OBJECT IDENTIFIER ::= { unisevtModuleSwitchType 460 } -- SDI,Dual XG Service Board
unisevtModuleSw-SPC-XP4L-S-SDI              OBJECT IDENTIFIER ::= { unisevtModuleSwitchType 461 } -- SDI 4-Port 10GBase-R/W Interface Module,(XFP,LC)
unisevtModuleSw-SPC-GT48L-SDI               OBJECT IDENTIFIER ::= { unisevtModuleSwitchType 462 } -- SDI 48-Port 10/100/1000BASE-T Interface Module,(RJ45)
unisevtModuleSw-SPC-GP48L-S-SDI             OBJECT IDENTIFIER ::= { unisevtModuleSwitchType 463 } -- SDI 48-Port 1000BASE-X Interface Module,(SFP,LC)
unisevtModuleSw-SPC-SR02OPMA0               OBJECT IDENTIFIER ::= { unisevtModuleSwitchType 464 } -- Single Mode 1310&1550nm Optical Protect Board(LC)
unisevtModuleSw-LSR1XP16REB1                OBJECT IDENTIFIER ::= { unisevtModuleSwitchType 465 } -- 16-Port 10GBASE-R Interface Module (REB),(SFP+,LC)
unisevtModuleSw-LSR1GP48LEF1                OBJECT IDENTIFIER ::= { unisevtModuleSwitchType 466 } -- 48-Port 1000BASE-X Interface Module (LEF),(SFP,LC)
unisevtModuleSw-LST1GP48LEF1                OBJECT IDENTIFIER ::= { unisevtModuleSwitchType 467 } -- 48-Port 1000BASE-X Interface Module (LEF),(SFP,LC)
unisevtModuleSw-LST1XP8LEF1                 OBJECT IDENTIFIER ::= { unisevtModuleSwitchType 468 } -- 8-Port 10GBASE-R/W Interface Module (LEF),(XFP,LC)
unisevtModuleSw-SPE-1010-II                 OBJECT IDENTIFIER ::= { unisevtModuleSwitchType 469 } -- Single XG Service Board-II
unisevtModuleSw-SPE-1010-E-II               OBJECT IDENTIFIER ::= { unisevtModuleSwitchType 470 } -- Enhanced Single XG Service Board-II
unisevtModuleSw-SPE-1020-II                 OBJECT IDENTIFIER ::= { unisevtModuleSwitchType 471 } -- Double XG Service Board-II
unisevtModuleSw-SPE-1020-E-II               OBJECT IDENTIFIER ::= { unisevtModuleSwitchType 472 } -- Enhanced Double XG Service Board-II
unisevtModuleSw-LST1FW2A1                   OBJECT IDENTIFIER ::= { unisevtModuleSwitchType 473 } -- Firewall Board (LEC)
unisevtModuleSw-LST1NSM1A1                  OBJECT IDENTIFIER ::= { unisevtModuleSwitchType 474 } -- NetStream Service Board (LEC)
unisevtModuleSw-LST1LB1A1                   OBJECT IDENTIFIER ::= { unisevtModuleSwitchType 475 } -- Load Balancing Board (LEC)
unisevtModuleSw-LST1ACG1A1                  OBJECT IDENTIFIER ::= { unisevtModuleSwitchType 476 } -- Application Control Gateway Board Module (LEC)
unisevtModuleSw-LST1IPS1A1                  OBJECT IDENTIFIER ::= { unisevtModuleSwitchType 477 } -- Gigabit Intrusion Prevention System Module (LEC)
unisevtModuleSw-LSR1DRUP1L1                 OBJECT IDENTIFIER ::= { unisevtModuleSwitchType 478 } -- 1-Port OC-192c/STM-64c RPR Optical Interface Card,(XFP,LC)
unisevtModuleSw-LSR1DPUP1L1                 OBJECT IDENTIFIER ::= { unisevtModuleSwitchType 479 } -- 1-Port OC-192c/STM-64c POS Optical Interface Card,(XFP,LC)
unisevtModuleSw-LSR1DPSP4L1                 OBJECT IDENTIFIER ::= { unisevtModuleSwitchType 480 } -- 4-Port OC-48c/STM-16c POS Optical Interface Card,(SFP,LC)
unisevtModuleSw-LSR1DTCP8L1                 OBJECT IDENTIFIER ::= { unisevtModuleSwitchType 481 } -- 8-Port OC-3c/OC-12c POS/GE Optical Interface Card,(SFP,LC)
unisevtModuleSw-LSR1DXP1L1                  OBJECT IDENTIFIER ::= { unisevtModuleSwitchType 482 } -- 1-Port 10GBASE-R/W Ethernet Optical Interface Card,(XPF,LC)
unisevtModuleSw-LSR1DGP10L1                 OBJECT IDENTIFIER ::= { unisevtModuleSwitchType 483 } -- 10-Port 1000BASE-X Optical Interface Card,(SFP,LC)
unisevtModuleSw-LSR1LN1BNL1                 OBJECT IDENTIFIER ::= { unisevtModuleSwitchType 484 } -- Single Service Processing Board
unisevtModuleSw-LSR1LN2BL1                  OBJECT IDENTIFIER ::= { unisevtModuleSwitchType 485 } -- Dual Serivice Processing Board
unisevtModuleSw-LSR1SRP2D1                  OBJECT IDENTIFIER ::= { unisevtModuleSwitchType 486 } -- Switching and Route Process Unit With Clock
unisevtModuleSw-IM-NAT-II                   OBJECT IDENTIFIER ::= { unisevtModuleSwitchType 487 } -- Network Address Translation Service Processing Board,II
unisevtModuleSw-IM-NAM-II                   OBJECT IDENTIFIER ::= { unisevtModuleSwitchType 488 } -- Net Analysis Service Processing Board,II
unisevtModuleSw-CR-MRP-I                    OBJECT IDENTIFIER ::= { unisevtModuleSwitchType 489 } -- Management and Route Unit With OAM Module and Clock Module
unisevtModuleSw-CR-SF18C                    OBJECT IDENTIFIER ::= { unisevtModuleSwitchType 490 } -- Switch Fabric Card
unisevtModuleSw-CR-SF08C                    OBJECT IDENTIFIER ::= { unisevtModuleSwitchType 491 } -- Switch Fabric Card
unisevtModuleSw-CR-SPC-XP8LEF               OBJECT IDENTIFIER ::= { unisevtModuleSwitchType 492 } -- 8-Port 10GBASE-R/W Interface Module,(XFP,LC)
unisevtModuleSw-CR-SPC-XP4LEF               OBJECT IDENTIFIER ::= { unisevtModuleSwitchType 493 } -- 4-Port 10GBASE-R/W Interface Module,(XFP,LC)
unisevtModuleSw-CR-SPC-GP48LEF              OBJECT IDENTIFIER ::= { unisevtModuleSwitchType 494 } -- 48-Port 1000BASE-X Interface Module,(SFP,LC)
unisevtModuleSw-CR-SPC-GT48LEF              OBJECT IDENTIFIER ::= { unisevtModuleSwitchType 495 } -- 48-Port 10/100/1000BASE-T Interface Module
unisevtModuleSw-CR-SPE-3020-E               OBJECT IDENTIFIER ::= { unisevtModuleSwitchType 496 } -- Double XG Service Board (Enhanced)
unisevtModuleSw-CR-SPC-PUP4L-E              OBJECT IDENTIFIER ::= { unisevtModuleSwitchType 497 } -- 4-Port 10G POS Optical Interface Module,(XFP,LC)
unisevtModuleSw-LST1SF08C1                  OBJECT IDENTIFIER ::= { unisevtModuleSwitchType 498 } -- Switch Fabric Card
unisevtModuleSw-LST1SF18C1                  OBJECT IDENTIFIER ::= { unisevtModuleSwitchType 499 } -- Switch Fabric Card

--
-- 500 to 699 reserved for secondary switches part I
--
unisevtModuleSw-LS81GP16TM                  OBJECT IDENTIFIER ::= { unisevtModuleSwitchType 500 } -- 12-port 1000BASE-X SFP Interface and 4-port 1000BASE-T/1000BASE-X Combo Interface Metro Switch and Route Processing Board
unisevtModuleSw-LS81VP4C                    OBJECT IDENTIFIER ::= { unisevtModuleSwitchType 501 } -- 4-port 1000BASE-X SFP Interface Virtual Daughter Card
unisevtModuleSw-LS8M1PT8P0                  OBJECT IDENTIFIER ::= { unisevtModuleSwitchType 502 } -- 8-Port 1000BASE-PX Optical Line Interface Board, SFP Req
unisevtModuleSw-LS8M1PT8GB0                 OBJECT IDENTIFIER ::= { unisevtModuleSwitchType 503 } -- 8-Port 1000BASE-PX20 Gigabit Passive Optical Line Interface Board B(20km, SFF), SC Connector
unisevtModuleSw-LS8M1PT4GB0                 OBJECT IDENTIFIER ::= { unisevtModuleSwitchType 504 } -- 4-Port 1000BASE-PX20 Gigabit Passive Optical Line Interface Board B(20km, SFF), SC Connector
unisevtModuleSw-LS81GP2R                    OBJECT IDENTIFIER ::= { unisevtModuleSwitchType 505 } -- 2-port 1000M Ethernet Optical Interface RPR Board
unisevtModuleSw-LS81GP4R                    OBJECT IDENTIFIER ::= { unisevtModuleSwitchType 506 } -- 4-port 1000M Ethernet Optical Interface RPR Board
unisevtModuleSw-LS81IPSECA                  OBJECT IDENTIFIER ::= { unisevtModuleSwitchType 507 } -- IPSec Service Board
unisevtModuleSw-LS81FWA                     OBJECT IDENTIFIER ::= { unisevtModuleSwitchType 508 } -- Firewall Service Board
unisevtModuleSw-LS82VSNP                    OBJECT IDENTIFIER ::= { unisevtModuleSwitchType 509 } -- Versatile Network Processing Service Module (PBR/NAT/NetStream) with 12-port 1000BASE-X SFP, XGBUS Uplink
unisevtModuleSw-LSQ1GV48SA                  OBJECT IDENTIFIER ::= { unisevtModuleSwitchType 510 } -- 48-Port 1000Base-T Gigabit Ethernet Interface Board(RJ45)
unisevtModuleSw-LSQ1SRPB                    OBJECT IDENTIFIER ::= { unisevtModuleSwitchType 511 } -- Salience VI
unisevtModuleSw-LSQ1SRP2XB                  OBJECT IDENTIFIER ::= { unisevtModuleSwitchType 512 } -- Salience VI-10GE
unisevtModuleSw-LSQ1SRP1CB                  OBJECT IDENTIFIER ::= { unisevtModuleSwitchType 513 } -- Salience VI-Turbo
unisevtModuleSw-LSQ1FV48SA                  OBJECT IDENTIFIER ::= { unisevtModuleSwitchType 514 } -- 48-Port 100M Ethernet Electrical Interface Switch Unit(RJ45)
unisevtModuleSw-LSD1MPUA                    OBJECT IDENTIFIER ::= { unisevtModuleSwitchType 515 } -- Main Control Unit
unisevtModuleSw-LSD1GP20A0                  OBJECT IDENTIFIER ::= { unisevtModuleSwitchType 516 } -- 16-port 1000BASE-X SFP Interface and 4-port 1000BASE-T/1000BASE-X Combo Interface Line Card
unisevtModuleSw-LSD1GP20TA0                 OBJECT IDENTIFIER ::= { unisevtModuleSwitchType 517 } -- 16-port 1000BASE-X SFP Interface and 4-port 1000BASE-T/1000BASE-X Combo Interface and 16 1000BASE-T Interface Line Card
unisevtModuleSw-LSD1GP36A0                  OBJECT IDENTIFIER ::= { unisevtModuleSwitchType 518 } -- 32-port 1000BASE-X SFP Interface and 4-port 1000BASE-T/1000BASE-X Combo Interface Line Card
unisevtModuleSw-LSD1GP20XA0                 OBJECT IDENTIFIER ::= { unisevtModuleSwitchType 519 } -- 16-port 1000BASE-X SFP Interface and 4-port 1000BASE-T/1000BASE-X Combo Interface and 2-port 10GBASE-X XFP Interface Line Card
unisevtModuleSw-LSD1GP20EA0                 OBJECT IDENTIFIER ::= { unisevtModuleSwitchType 520 } -- 16-port 1000BASE-X SFP Interface and 4-port 1000BASE-T/1000BASE-X Combo Interface and 2-port GE RPR Interface Line Card
unisevtModuleSw-LSD1GP20RA0                 OBJECT IDENTIFIER ::= { unisevtModuleSwitchType 521 } -- 16-port 1000BASE-X SFP Interface and 4-port 1000BASE-T/1000BASE-X Combo Interface and 2-port OC48 RPR Interface Line Card
unisevtModuleSw-LSD1GP16A0                  OBJECT IDENTIFIER ::= { unisevtModuleSwitchType 522 } -- 16-port 1000BASE-X SFP Ethernet Interface SubCard
unisevtModuleSw-LSD1GT16A0                  OBJECT IDENTIFIER ::= { unisevtModuleSwitchType 523 } -- 16-port 1000BASE-T Ethernet Interface SubCard
unisevtModuleSw-LSD1XP2A0                   OBJECT IDENTIFIER ::= { unisevtModuleSwitchType 524 } -- 2-port 10GBASE-X XFP Ethernet Interface SubCard
unisevtModuleSw-LSD1EP2A0                   OBJECT IDENTIFIER ::= { unisevtModuleSwitchType 525 } -- 2-port 1000BASE-T Ethernet RPR Interface SubCard
unisevtModuleSw-LSD1RP2A0                   OBJECT IDENTIFIER ::= { unisevtModuleSwitchType 526 } -- 2-port OC48 RPR Interface SubCard
unisevtModuleSw-LSQ1GV48SC                  OBJECT IDENTIFIER ::= { unisevtModuleSwitchType 527 } -- 48-Port 1000Base-T Gigabit Ethernet Interface Board(RJ45)-POE
unisevtModuleSw-LSQ1FP48SA                  OBJECT IDENTIFIER ::= { unisevtModuleSwitchType 528 } -- 48 Port 100M Ethernet Optical Interface Board(SFP,LC)
unisevtModuleSw-LSQ1GP24SC                  OBJECT IDENTIFIER ::= { unisevtModuleSwitchType 529 } -- 24 Port 1000BASE-X Ethernet Optical Interface Board(SFP,LC)
unisevtModuleSw-LSQ1GT24SC                  OBJECT IDENTIFIER ::= { unisevtModuleSwitchType 530 } -- 24-Port 1000BASE-T Ethernet Interface Board (RJ45)
unisevtModuleSw-LSQ1TGX2SC                  OBJECT IDENTIFIER ::= { unisevtModuleSwitchType 531 } -- 2-Port 10GBASE Ethernet Optical Interface Board(XFP,LC)
unisevtModuleSw-LSQ1GP12EA                  OBJECT IDENTIFIER ::= { unisevtModuleSwitchType 532 } -- 12-Port 1000BASE-X Ethernet Optical Interface Board(SFP,LC)
unisevtModuleSw-LSQ1TGX1EA                  OBJECT IDENTIFIER ::= { unisevtModuleSwitchType 533 } -- 1-Port 10GBASE Ethernet Optical Interface Module(XFP,LC)
unisevtModuleSw-LSQ1P24XGSC                 OBJECT IDENTIFIER ::= { unisevtModuleSwitchType 534 } -- 24-Port 1000BASE-X Gigabit Ethernet Optical Interface(SFP,LC)+2-Port 10GBASE Ethernet Optical Interface Board(XFP,LC)
unisevtModuleSw-LSQ1T24XGSC                 OBJECT IDENTIFIER ::= { unisevtModuleSwitchType 535 } -- 24-Port 1000BASE-T Gigabit Ethernet Interface(RJ45)+2-Port 10GBASE Ethernet Optical Interface Board(XFP,LC)
unisevtModuleSw-LS81TGX1B                   OBJECT IDENTIFIER ::= { unisevtModuleSwitchType 536 } -- 1 Port 10GBase-R Ethernet Interface Board(XENPAK,SC)
unisevtModuleSw-LSQ1PT4PSC0                 OBJECT IDENTIFIER ::= { unisevtModuleSwitchType 537 } -- 4-Port 1000Base-PX Optical Line Terminal(EPON OLT SFP,SC)+8-Port 1000BASE-X Optical Interface Board(SFP,LC)
unisevtModuleSw-LS81SRPG13                  OBJECT IDENTIFIER ::= { unisevtModuleSwitchType 538 } -- Salience V, Switch and Route Processing Board
unisevtModuleSw-LS81SRPG14                  OBJECT IDENTIFIER ::= { unisevtModuleSwitchType 539 } -- Salience V Edge
unisevtModuleSw-LS81SRPG15                  OBJECT IDENTIFIER ::= { unisevtModuleSwitchType 540 } -- Salience V Plus
unisevtModuleSw-LSQ1GP48SC0                 OBJECT IDENTIFIER ::= { unisevtModuleSwitchType 541 } -- 48-Port 1000BASE Ethernet Optical Interface Board(SFP,LC)
unisevtModuleSw-LSQ1GP12SC0                 OBJECT IDENTIFIER ::= { unisevtModuleSwitchType 542 } -- 12-Port 1000BASE-X Ethernet Optical Interface Board(SFP,LC)
unisevtModuleSw-LSD1SRPA                    OBJECT IDENTIFIER ::= { unisevtModuleSwitchType 543 } -- Salience VIII 160
unisevtModuleSw-LSD1SRPB                    OBJECT IDENTIFIER ::= { unisevtModuleSwitchType 544 } -- Salience VIII 480
unisevtModuleSw-LSD1SRPC                    OBJECT IDENTIFIER ::= { unisevtModuleSwitchType 545 } -- Salience VIII 800
unisevtModuleSw-LSD1GT16PES0                OBJECT IDENTIFIER ::= { unisevtModuleSwitchType 546 } -- 16-Port 10/100/1000BASE-T and 8-Port 100/1000BASE-X SFP Interface Card
unisevtModuleSw-LSD1GP24ES0                 OBJECT IDENTIFIER ::= { unisevtModuleSwitchType 547 } -- 24-Port 1000BASE-X Ethernet SFP Interface Card
unisevtModuleSw-LSD1GT24XES0                OBJECT IDENTIFIER ::= { unisevtModuleSwitchType 548 } -- 24-Port 10/100/1000BASE-T and 2-port 10GBASE-X Ethernet XFP Optical Interface Card
unisevtModuleSw-LSD1GP24XES0                OBJECT IDENTIFIER ::= { unisevtModuleSwitchType 549 } -- 24-Port 1000BASE-X Ethernet SFP interface and 2-port 10GBASE-X Ethernet XFP Optical Interface Card
unisevtModuleSw-LSD1XP2ES0                  OBJECT IDENTIFIER ::= { unisevtModuleSwitchType 550 } -- 2-Port 10GBASE-X Ethernet XFP Optical Interface Card
unisevtModuleSw-LSD1GP48ES0                 OBJECT IDENTIFIER ::= { unisevtModuleSwitchType 551 } -- 48-Port 1000BASE-X Ethernet SFP Interface Card
unisevtModuleSw-LSQ1MPUA0                   OBJECT IDENTIFIER ::= { unisevtModuleSwitchType 552 } -- Master Process Board
unisevtModuleSw-LSQ1MPUA1                   OBJECT IDENTIFIER ::= { unisevtModuleSwitchType 553 } -- Master Process Unit
unisevtModuleSw-LSQ1FWBSC0                  OBJECT IDENTIFIER ::= { unisevtModuleSwitchType 554 } -- Gigabit Firewall Card, 4 Gigabit Port for Management
unisevtModuleSw-LSQ1PT8PSC0                 OBJECT IDENTIFIER ::= { unisevtModuleSwitchType 555 } -- 8-Port 1000Base-PX Optical Line Terminal(EPON OLT SFP,SC)+8-Port 1000BASE-X Optical Interface Board(SFP,LC)
unisevtModuleSw-LSQ1PT16PSC0                OBJECT IDENTIFIER ::= { unisevtModuleSwitchType 556 } -- 16-Port 1000Base-PX Optical Line Terminal(EPON OLT SFP,SC)+8-Port 1000BASE-X Optical Interface Board(SFP,LC)
unisevtModuleSw-SA11MPUA0                   OBJECT IDENTIFIER ::= { unisevtModuleSwitchType 557 } -- SmartEngine I-Lite
unisevtModuleSw-SA11MPUB0                   OBJECT IDENTIFIER ::= { unisevtModuleSwitchType 558 } -- SmartEngine I
unisevtModuleSw-LSQ1AFCBSC0                 OBJECT IDENTIFIER ::= { unisevtModuleSwitchType 559 } -- Anomaly Flow Cleaner Board Interface Board(SFP,LC)
unisevtModuleSw-LSQ1MPUB0                   OBJECT IDENTIFIER ::= { unisevtModuleSwitchType 560 } -- Salience VI-Lite
unisevtModuleSw-LSQ1MPUB1                   OBJECT IDENTIFIER ::= { unisevtModuleSwitchType 561 } -- Salience VI-Lite
unisevtModuleSw-LSQ1PT4PSC1                 OBJECT IDENTIFIER ::= { unisevtModuleSwitchType 562 } -- 4-Port 1000Base-PX Optical Line Terminal(EPON OLT SFP,SC)+8-Port 1000BASE-X Optical Interface Board(SFP,LC)
unisevtModuleSw-LSQ1PT8PSC1                 OBJECT IDENTIFIER ::= { unisevtModuleSwitchType 563 } -- 8-Port 1000Base-PX Optical Line Terminal(EPON OLT SFP,SC)+8-Port 1000BASE-X Optical Interface Board(SFP,LC)
unisevtModuleSw-LSQ1PT16PSC1                OBJECT IDENTIFIER ::= { unisevtModuleSwitchType 564 } -- 16-Port 1000Base-PX Optical Line Terminal(EPON OLT SFP,SC)+8-Port 1000BASE-X Optical Interface Board(SFP,LC)
unisevtModuleSw-LSQ1FP48USA0                OBJECT IDENTIFIER ::= { unisevtModuleSwitchType 565 } -- 48-Port 100M Ethernet Optical Interface Switch Unit(SFP,LC)
unisevtModuleSw-LSQ1FP48USA1                OBJECT IDENTIFIER ::= { unisevtModuleSwitchType 566 } -- 48-Port 100M Ethernet Optical Interface Switch Unit(SFP,LC)
unisevtModuleSw-LSQ1FV48USA0                OBJECT IDENTIFIER ::= { unisevtModuleSwitchType 567 } -- 48-Port 100M Ethernet Electrical Interface Switch Unit(RJ45),PoE
unisevtModuleSw-LSQ1FV48USA1                OBJECT IDENTIFIER ::= { unisevtModuleSwitchType 568 } -- 48-Port 100M Ethernet Electrical Interface Switch Unit(RJ45),PoE
unisevtModuleSw-LSQ1SRPD0                   OBJECT IDENTIFIER ::= { unisevtModuleSwitchType 569 } -- Switch and Route Processing Unit, Salience VI-Plus
unisevtModuleSw-LSQ1CGP24TSC0               OBJECT IDENTIFIER ::= { unisevtModuleSwitchType 570 } -- Switching and Routing Processing Unit with 24 1000BASE-X Gigabit Ethernet Optical Ports,including 8 Combo Ports,SFP Req.
unisevtModuleSw-LSQ1GP24TSC0                OBJECT IDENTIFIER ::= { unisevtModuleSwitchType 571 } -- 16-Port 1000BASE-X Gigabit Ethernet Optical(SFP,LC) And 8-Port 10/100/1000BASE-T RJ45/1000BASE-X SFP Combo Interface Board
unisevtModuleSw-LSQ1ACGASC0                 OBJECT IDENTIFIER ::= { unisevtModuleSwitchType 572 } -- Application Control Gateway Board
unisevtModuleSw-LSD1XP1ES0                  OBJECT IDENTIFIER ::= { unisevtModuleSwitchType 573 } -- 1-Port 10GBASE-X Ethernet XFP Optical Interface Card
unisevtModuleSw-LSD1GP12ES0                 OBJECT IDENTIFIER ::= { unisevtModuleSwitchType 574 } -- 12-Port 1000BASE-X Ethernet SFP Interface Card
unisevtModuleSw-LSQ1SRP12GB0                OBJECT IDENTIFIER ::= { unisevtModuleSwitchType 575 } -- Switch And Route Processing Unit with 12 1000BASE Ethernet Optical Interfaces(SFP,LC),Salience VI-GE
unisevtModuleSw-LSQ1GV40PSC0                OBJECT IDENTIFIER ::= { unisevtModuleSwitchType 576 } -- 40-Port 10/100/1000BASE-T Electrical(RJ45) And 8-Port 1000BASE-X Optical Ethernet Interface Board(SFP,LC),PoE
unisevtModuleSw-LSQ1FWBSC1                  OBJECT IDENTIFIER ::= { unisevtModuleSwitchType 577 } -- Firewall Board
unisevtModuleSw-LSQ1NSMSC0                  OBJECT IDENTIFIER ::= { unisevtModuleSwitchType 578 } -- NetStream Board
unisevtModuleSw-LSQ1NSMSC1                  OBJECT IDENTIFIER ::= { unisevtModuleSwitchType 579 } -- NetStream Board
unisevtModuleSw-LSQ1AFDBSC0                 OBJECT IDENTIFIER ::= { unisevtModuleSwitchType 580 } -- Anomaly Flow Detector Board
unisevtModuleSw-LS81MPUB                    OBJECT IDENTIFIER ::= { unisevtModuleSwitchType 581 } -- Salience IV
unisevtModuleSw-LS81FP48XL                  OBJECT IDENTIFIER ::= { unisevtModuleSwitchType 582 } -- 48-Port 100M Ethernet Optical Interface Module,(SFP,LC)
unisevtModuleSw-LS81FT48XL                  OBJECT IDENTIFIER ::= { unisevtModuleSwitchType 583 } -- 48-Port 10/100M Ethernet Electrical Interface Module(RJ45)
unisevtModuleSw-LS81GP12XL                  OBJECT IDENTIFIER ::= { unisevtModuleSwitchType 584 } -- 12-Port 1000/100M Ethernet Optical Interface Module(SFP,LC)
unisevtModuleSw-LS81GP24XL                  OBJECT IDENTIFIER ::= { unisevtModuleSwitchType 585 } -- 24-Port 1000/100M Ethernet Optical Interface Module(SFP,LC)
unisevtModuleSw-LS81GP48XL                  OBJECT IDENTIFIER ::= { unisevtModuleSwitchType 586 } -- 48-Port 1000/100M Ethernet Optical Interface Module(SFP,LC)
unisevtModuleSw-LS81GT24XL                  OBJECT IDENTIFIER ::= { unisevtModuleSwitchType 587 } -- 24-Port 10/100/1000M Ethernet Electrical Interface Module(RJ45)
unisevtModuleSw-LS81GT48XL                  OBJECT IDENTIFIER ::= { unisevtModuleSwitchType 588 } -- 48-Port 10/100/1000M Ethernet Electrical Interface Module(RJ45)
unisevtModuleSw-LS81TGX2XL                  OBJECT IDENTIFIER ::= { unisevtModuleSwitchType 589 } -- 2-Port 10GBASE Ethernet Optical Interface Module(XFP,LC)
unisevtModuleSw-LSQ1GV48SD0                 OBJECT IDENTIFIER ::= { unisevtModuleSwitchType 590 } -- 48-Port 1000Base-T Gigabit Ethernet Interface Board(RJ45),PoE
unisevtModuleSw-LSQ1GP48EB0                 OBJECT IDENTIFIER ::= { unisevtModuleSwitchType 591 } -- 48-Port Enhanced 1000BASE-X Ethernet Optical Interface Board(SFP,LC)
unisevtModuleSw-LSQ1IPSSC0                  OBJECT IDENTIFIER ::= { unisevtModuleSwitchType 592 } -- Gigabit IPS Card
unisevtModuleSw-LSQ1GV48SD1                 OBJECT IDENTIFIER ::= { unisevtModuleSwitchType 593 } -- 48-Port 1000Base-T Gigabit Ethernet Interface Board(RJ45),PoE
unisevtModuleSw-LSQ1GP48SD0                 OBJECT IDENTIFIER ::= { unisevtModuleSwitchType 594 } -- 48-Port 1000BASE-X Gigabit Ethernet Optical Interface(SFP,LC) Interface Board
unisevtModuleSw-LSQ1GP48SD1                 OBJECT IDENTIFIER ::= { unisevtModuleSwitchType 595 } -- 48-Port 1000BASE-X Gigabit Ethernet Optical Interface(SFP,LC) Interface Board
unisevtModuleSw-LSQ1SRPA0                   OBJECT IDENTIFIER ::= { unisevtModuleSwitchType 596 } -- Salience VI-Smart
unisevtModuleSw-LSQ1SRPA1                   OBJECT IDENTIFIER ::= { unisevtModuleSwitchType 597 } -- Salience VI-Smart
unisevtModuleSw-LSQ2FP48SA0                 OBJECT IDENTIFIER ::= { unisevtModuleSwitchType 598 } -- 48 Port 100M Ethernet Optical Interface Board(SFP,LC)
unisevtModuleSw-LSQ2FP48SA1                 OBJECT IDENTIFIER ::= { unisevtModuleSwitchType 599 } -- 48 Port 100M Ethernet Optical Interface Board(SFP,LC)
unisevtModuleSw-LSQ2FT48SA0                 OBJECT IDENTIFIER ::= { unisevtModuleSwitchType 600 } -- 48-Port 100M Ethernet Electrical Interface Switch Unit(RJ45)
unisevtModuleSw-LSQ2FT48SA1                 OBJECT IDENTIFIER ::= { unisevtModuleSwitchType 601 } -- 48-Port 100M Ethernet Electrical Interface Switch Unit(RJ45)
unisevtModuleSw-LSQ1GV24PSC0                OBJECT IDENTIFIER ::= { unisevtModuleSwitchType 602 } -- 24-Port 10/100/1000BASE-T Electrical(RJ45) Interface Board,including 4 Combo Ports,SFP Req,PoE,No Spell
unisevtModuleSw-LSQ1GV24PSC1                OBJECT IDENTIFIER ::= { unisevtModuleSwitchType 603 } -- 24-Port 10/100/1000BASE-T Electrical(RJ45) Interface Board,including 4 Combo Ports,SFP Req,PoE,No Spell
unisevtModuleSw-LSQ1CGV24PSC0               OBJECT IDENTIFIER ::= { unisevtModuleSwitchType 604 } -- Switching and Routing Processing Unit with 24 10/100/1000BASE-T Electrical Ports(RJ45),including 4 Combo Ports,SFP Req,PoE,No Spell
unisevtModuleSw-LSQ1CGV24PSC1               OBJECT IDENTIFIER ::= { unisevtModuleSwitchType 605 } -- Switching and Routing Processing Unit with 24 10/100/1000BASE-T Electrical Ports(RJ45),including 4 Combo Ports,SFP Req,PoE,No Spell
unisevtModuleSw-LSQ1GP24TEB0                OBJECT IDENTIFIER ::= { unisevtModuleSwitchType 606 } -- 16-Port 1000BASE-X Gigabit Ethernet Optical Interface(SFP,LC)+8-Port Combo Interface Board
unisevtModuleSw-LSQ1GP24TEB1                OBJECT IDENTIFIER ::= { unisevtModuleSwitchType 607 } -- 16-Port 1000BASE-X Gigabit Ethernet Optical Interface(SFP,LC)+8-Port Combo Interface Board
unisevtModuleSw-LSQ1GP24TSD0                OBJECT IDENTIFIER ::= { unisevtModuleSwitchType 608 } -- 16-Port 1000BASE-X Gigabit Ethernet Optical Interface(SFP,LC)+8-Port Combo Interface Board
unisevtModuleSw-LSQ1GP24TSD1                OBJECT IDENTIFIER ::= { unisevtModuleSwitchType 609 } -- 16-Port 1000BASE-X Gigabit Ethernet Optical Interface(SFP,LC)+8-Port Combo Interface Board
unisevtModuleSw-LSQ1GP24TXSD0               OBJECT IDENTIFIER ::= { unisevtModuleSwitchType 610 } -- 16-Port GE Optical Interface(SFP,LC)+8-Port Combo Interface+2-Port 10GE Optical Interface Board(XFP,LC)
unisevtModuleSw-LSQ1GP24TXSD1               OBJECT IDENTIFIER ::= { unisevtModuleSwitchType 611 } -- 16-Port GE Optical Interface(SFP,LC)+8-Port Combo Interface+2-Port 10GE Optical Interface Board(XFP,LC)
unisevtModuleSw-LSQ1TGX2EB0                 OBJECT IDENTIFIER ::= { unisevtModuleSwitchType 612 } -- 2-Port 10GBASE Ethernet Optical Interface Board(XFP,LC)
unisevtModuleSw-LSQ1TGX2EB1                 OBJECT IDENTIFIER ::= { unisevtModuleSwitchType 613 } -- 2-Port 10GBASE Ethernet Optical Interface Board(XFP,LC)
unisevtModuleSw-LSQ1TGX2SD0                 OBJECT IDENTIFIER ::= { unisevtModuleSwitchType 614 } -- 2-Port 10GBASE Ethernet Optical Interface Board(XFP,LC)
unisevtModuleSw-LSQ1TGX2SD1                 OBJECT IDENTIFIER ::= { unisevtModuleSwitchType 615 } -- 2-Port 10GBASE Ethernet Optical Interface Board(XFP,LC)
unisevtModuleSw-LSQ1TGX4SD0                 OBJECT IDENTIFIER ::= { unisevtModuleSwitchType 616 } -- 4-Port 10GBASE Ethernet Optical Interface Board(XFP,LC)
unisevtModuleSw-LSQ1TGX4SD1                 OBJECT IDENTIFIER ::= { unisevtModuleSwitchType 617 } -- 4-Port 10GBASE Ethernet Optical Interface Board(XFP,LC)
unisevtModuleSw-LSQ1TGX8SD0                 OBJECT IDENTIFIER ::= { unisevtModuleSwitchType 618 } -- 8-Port 10GBASE Ethernet Optical Interface Board(XFP,LC)
unisevtModuleSw-LSQ1TGX8SD1                 OBJECT IDENTIFIER ::= { unisevtModuleSwitchType 619 } -- 8-Port 10GBASE Ethernet Optical Interface Board(XFP,LC)
unisevtModuleSw-LSQ1GP48EB1                 OBJECT IDENTIFIER ::= { unisevtModuleSwitchType 620 } -- 48-Port Enhanced 1000BASE-X Ethernet Optical Interface Board(SFP,LC)
unisevtModuleSw-LSQ1TGX4EB0                 OBJECT IDENTIFIER ::= { unisevtModuleSwitchType 621 } -- 4-Port 10GBASE Ethernet Optical Interface Board(XFP,LC)
unisevtModuleSw-LSQ1TGX4EB1                 OBJECT IDENTIFIER ::= { unisevtModuleSwitchType 622 } -- 4-Port 10GBASE Ethernet Optical Interface Board(XFP,LC)
unisevtModuleSw-LSQ1GP12SC3                 OBJECT IDENTIFIER ::= { unisevtModuleSwitchType 623 } -- 12-Port 1000BASE-X Ethernet Optical Interface Board(SFP,LC)
unisevtModuleSw-LSQ1GP24TSC3                OBJECT IDENTIFIER ::= { unisevtModuleSwitchType 624 } -- 16-Port 1000BASE-X Gigabit Ethernet Optical(SFP,LC) And 8-Port 10/100/1000BASE-T RJ45/1000BASE-X SFP Combo Interface Board
unisevtModuleSw-LSQ1GP48SC3                 OBJECT IDENTIFIER ::= { unisevtModuleSwitchType 625 } -- 48-Port 1000BASE Ethernet Optical Interface Board(SFP,LC)
unisevtModuleSw-LSQ1GV48SC3                 OBJECT IDENTIFIER ::= { unisevtModuleSwitchType 626 } -- 48-Port 1000Base-T Gigabit Ethernet Interface Board(RJ45),PoE
unisevtModuleSw-LSQ1MPUA3                   OBJECT IDENTIFIER ::= { unisevtModuleSwitchType 627 } -- Master Process Board
unisevtModuleSw-LSQ1SRP1CB3                 OBJECT IDENTIFIER ::= { unisevtModuleSwitchType 628 } -- Salience VI-Turbo
unisevtModuleSw-LSQ1SRPA3                   OBJECT IDENTIFIER ::= { unisevtModuleSwitchType 629 } -- Salience VI-Smart
unisevtModuleSw-LSQ2FP48SA3                 OBJECT IDENTIFIER ::= { unisevtModuleSwitchType 630 } -- 48 Port 100M Ethernet Optical Interface Board(SFP,LC)
unisevtModuleSw-LSQ2FT48SA3                 OBJECT IDENTIFIER ::= { unisevtModuleSwitchType 631 } -- 48-Port 100M Ethernet Electrical Interface Switch Unit(RJ45)
unisevtModuleSw-LSQ1MPUB3                   OBJECT IDENTIFIER ::= { unisevtModuleSwitchType 632 } -- Salience VI-Lite
unisevtModuleSw-LSQ1CGP24TSC3               OBJECT IDENTIFIER ::= { unisevtModuleSwitchType 633 } -- Switching and Routing Processing Unit with 24 1000BASE-X Gigabit Ethernet Optical Ports,including 8 Combo Ports,SFP Req.
unisevtModuleSw-LSQ1MPUB4                   OBJECT IDENTIFIER ::= { unisevtModuleSwitchType 634 } -- Salience VI-Lite
unisevtModuleSw-LSQ1SRPD4                   OBJECT IDENTIFIER ::= { unisevtModuleSwitchType 635 } -- Salience VI-Plus
unisevtModuleSw-LSQ1SSLSC0                  OBJECT IDENTIFIER ::= { unisevtModuleSwitchType 636 } -- SSL VPN Service Board(B)
unisevtModuleSw-LSQ1LBSC0                   OBJECT IDENTIFIER ::= { unisevtModuleSwitchType 637 } -- Gigabit Load Balancing Card
unisevtModuleSw-LSQ1NAT24SC0                OBJECT IDENTIFIER ::= { unisevtModuleSwitchType 638 } -- NAT/NetStream-Supported Line Processing Unit with 24 10/100/1000BASE-T Electrical Ports(RJ45),including Combo Ports,Upgradeable to PoE
unisevtModuleSw-LSQ1SRP12GB4                OBJECT IDENTIFIER ::= { unisevtModuleSwitchType 639 } -- Salience VI-GE
unisevtModuleSw-LSQ1TGS8SC0                 OBJECT IDENTIFIER ::= { unisevtModuleSwitchType 640 } -- 8-Port 10GBASE Ethernet SFP+ Optical Interface Board
unisevtModuleSw-LSQ3PT4PSC0                 OBJECT IDENTIFIER ::= { unisevtModuleSwitchType 641 } -- 4-Port 1000Base-PX Optical Line Terminal(EPON OLT SFP,SC)+8-Port 1000BASE-X Optical Interface Board(SFP,LC)
unisevtModuleSw-EWPXM2MPUB0                 OBJECT IDENTIFIER ::= { unisevtModuleSwitchType 642 } -- Salience VI-Lite
unisevtModuleSw-EWPXM2SRP12GB0              OBJECT IDENTIFIER ::= { unisevtModuleSwitchType 643 } -- Salience VI-GE
unisevtModuleSw-EWPXM2SRPD0                 OBJECT IDENTIFIER ::= { unisevtModuleSwitchType 644 } -- Salience VI-Plus
unisevtModuleSw-EWPXM2GP24TSD0              OBJECT IDENTIFIER ::= { unisevtModuleSwitchType 645 } -- 16-Port 1000BASE-X Ethernet Optical Interface(SFP Req.)+8-Port Combo Interface Module
unisevtModuleSw-EWPXM2GP24TXSD0             OBJECT IDENTIFIER ::= { unisevtModuleSwitchType 646 } -- 16-Port 1000BASE-X Ethernet Optical Interface(SFP Req.)+8-Port Combo Interface+2-Port 10GE Optical Interface(XFP Req.) Module
unisevtModuleSw-EWPXM2TGX4SD0               OBJECT IDENTIFIER ::= { unisevtModuleSwitchType 647 } -- 4-Port 10GBASE Ethernet Optical Interface Module,XFP Req
unisevtModuleSw-EWPXM2GP48SD0               OBJECT IDENTIFIER ::= { unisevtModuleSwitchType 648 } -- 48-Port 1000BASE-X Gigabit Ethernet Optical Interface Module,SFP Req
unisevtModuleSw-EWPXM2GP24TSC0              OBJECT IDENTIFIER ::= { unisevtModuleSwitchType 649 } -- 24-Port 1000BASE-X/100BASE-FX Optical  Interface Module,including 8 Combo Ports,SFP Req
unisevtModuleSw-EWPXM2TGX2SC0               OBJECT IDENTIFIER ::= { unisevtModuleSwitchType 650 } -- 2-Port 10GBASE Ethernet Optical Interface Module,XFP Req
unisevtModuleSw-EWPXM2GP48SC0               OBJECT IDENTIFIER ::= { unisevtModuleSwitchType 651 } -- 48-Port 1000BASE-X/100BASE-FX Ethernet Optical Interface Module,SFP Req
unisevtModuleSw-LS7500-GP48-SC              OBJECT IDENTIFIER ::= { unisevtModuleSwitchType 652 } -- 48-Port 1000BASE-X/100BASE-FX Ethernet Optical Interface Module(SFP,LC)
unisevtModuleSw-LS7500-GP48-SD              OBJECT IDENTIFIER ::= { unisevtModuleSwitchType 653 } -- 48-Port 1000BASE-X Gigabit Ethernet Optical Interface Module(SFP,LC)
unisevtModuleSw-LS7500-GT48-SC              OBJECT IDENTIFIER ::= { unisevtModuleSwitchType 654 } -- 48-Port 10/100/1000BASE-TX Ethernet Interface Module(RJ45)
unisevtModuleSw-LS7500-GT48-SD              OBJECT IDENTIFIER ::= { unisevtModuleSwitchType 655 } -- 48-Port 10/100/1000BASE-T Ethernet Interface Module(RJ45)
unisevtModuleSw-LS7500-SRPG1                OBJECT IDENTIFIER ::= { unisevtModuleSwitchType 656 } -- Main Control Unit
unisevtModuleSw-LS7500-SRPG2                OBJECT IDENTIFIER ::= { unisevtModuleSwitchType 657 } -- Salience VI-Lite
unisevtModuleSw-LS7500-XP4-SD               OBJECT IDENTIFIER ::= { unisevtModuleSwitchType 658 } -- 4-Port 10GBASE Ethernet Optical Interface Module(XFP,LC)
unisevtModuleSw-LS7500-XP8-SD               OBJECT IDENTIFIER ::= { unisevtModuleSwitchType 659 } -- 8-Port 10GBASE Ethernet Optical Interface Module(XFP,LC)
unisevtModuleSw-LSQ4PT4PSC0                 OBJECT IDENTIFIER ::= { unisevtModuleSwitchType 660 } -- 4-Port 1000Base-PX Optical Line Terminal(EPON OLT SFP,SC)+8-Port 1000BASE-X Optical Interface Board(SFP,LC)
unisevtModuleSw-LSQ4PT8PSC0                 OBJECT IDENTIFIER ::= { unisevtModuleSwitchType 661 } -- 8-Port 1000Base-PX Optical Line Terminal(EPON OLT SFP,SC)+8-Port 1000BASE-X Optical Interface Board(SFP,LC)
unisevtModuleSw-LSQ4PT16PSC0                OBJECT IDENTIFIER ::= { unisevtModuleSwitchType 662 } -- 16-Port 1000Base-PX Optical Line Terminal(EPON OLT SFP,SC)+8-Port 1000BASE-X Optical Interface Board(SFP,LC)
unisevtModuleSw-LSQ1GP24TSA0                OBJECT IDENTIFIER ::= { unisevtModuleSwitchType 663 } -- 16-Port 1000BASE-X Gigabit Ethernet Optical(SFP,LC) And 8-Port 10/100/1000BASE-T RJ45/1000BASE-X SFP Combo Interface Board
unisevtModuleSw-LSQ1GV24PSA0                OBJECT IDENTIFIER ::= { unisevtModuleSwitchType 664 } -- 24-Port 10/100/1000BASE-T Electrical(RJ45) Interface Board,including 4 Combo Ports,SFP Req,Upgradeable to PoE
unisevtModuleSw-LSQ1SRPD3                   OBJECT IDENTIFIER ::= { unisevtModuleSwitchType 665 } -- Salience VI-Plus
unisevtModuleSw-LSQ1SUPA0                   OBJECT IDENTIFIER ::= { unisevtModuleSwitchType 666 } -- Supervisor Engine Board
unisevtModuleSw-LSU1FAB04A0                 OBJECT IDENTIFIER ::= { unisevtModuleSwitchType 667 } -- Switch Fabric Board
unisevtModuleSw-LSU1FAB08A0                 OBJECT IDENTIFIER ::= { unisevtModuleSwitchType 668 } -- Switch Fabric Board
unisevtModuleSw-LSU1TGS8EA0                 OBJECT IDENTIFIER ::= { unisevtModuleSwitchType 669 } -- 8-Port 10GBASE Ethernet SFP+ Optical Interface Board(EA)
unisevtModuleSw-LSU1TGS8EB0                 OBJECT IDENTIFIER ::= { unisevtModuleSwitchType 670 } -- 8-Port 10GBASE Ethernet SFP+ Optical Interface Board
unisevtModuleSw-LSU1TGS8SE0                 OBJECT IDENTIFIER ::= { unisevtModuleSwitchType 671 } -- 8-Port 10GBASE Ethernet SFP+ Optical Interface Board(SE)
unisevtModuleSw-LSUTGS16SC0                 OBJECT IDENTIFIER ::= { unisevtModuleSwitchType 672 } -- 16-Port 10GBASE Ethernet SFP+ Optical Interface Board
unisevtModuleSw-LSU1SUPA0                   OBJECT IDENTIFIER ::= { unisevtModuleSwitchType 673 } -- Supervisor Engine Board
unisevtModuleSw-LSU1GP24TXEA0               OBJECT IDENTIFIER ::= { unisevtModuleSwitchType 674 } -- 16-Port 1000BASE-X Optical Interface(SFP,LC)+8-Port Combo Interface+2-Port 10GE Optical Interface Board(XFP,LC)(EA)
unisevtModuleSw-LSU1GP24TXEB0               OBJECT IDENTIFIER ::= { unisevtModuleSwitchType 675 } -- 16-Port 1000BASE-X Optical Interface(SFP,LC)+8-Port Combo Interface+2-Port 10GE Optical Interface Board(XFP,LC)(EB)
unisevtModuleSw-LSU1GP24TXSE0               OBJECT IDENTIFIER ::= { unisevtModuleSwitchType 676 } -- 16-Port 1000BASE-X Optical Interface(SFP,LC)+8-Port Combo Interface+2-Port 10GE Optical Interface Board(XFP,LC)(SE)
unisevtModuleSw-LSU1GP48EA0                 OBJECT IDENTIFIER ::= { unisevtModuleSwitchType 677 } -- 48-Port 1000BASE-X Gigabit Ethernet Optical Interface(SFP,LC) Interface Board(EA)
unisevtModuleSw-LSU1GP48EB0                 OBJECT IDENTIFIER ::= { unisevtModuleSwitchType 678 } -- 48-Port Enhanced 1000BASE-X Ethernet Optical Interface Board(SFP,LC)(EB)
unisevtModuleSw-LSU1GP48SE0                 OBJECT IDENTIFIER ::= { unisevtModuleSwitchType 679 } -- 48-Port 1000BASE Ethernet Optical Interface Board(SFP,LC)(SE)
unisevtModuleSw-LSU1GT48EA0                 OBJECT IDENTIFIER ::= { unisevtModuleSwitchType 680 } -- 48-Port 1000Base-T Gigabit Ethernet Interface Board(RJ45)(EA)
unisevtModuleSw-LSU1GT48SE0                 OBJECT IDENTIFIER ::= { unisevtModuleSwitchType 681 } -- 48-Port 1000Base-T Gigabit Ethernet Interface Board(RJ45)(SE)
unisevtModuleSw-LSU1TGX4EA0                 OBJECT IDENTIFIER ::= { unisevtModuleSwitchType 682 } -- 4-Port 10GBASE Ethernet Optical Interface Board(XFP,LC)(EA)
unisevtModuleSw-LSU1TGX4EB0                 OBJECT IDENTIFIER ::= { unisevtModuleSwitchType 683 } -- 4-Port 10GBASE Ethernet Optical Interface Board(XFP,LC)(EB)
unisevtModuleSw-LSU1TGX4SE0                 OBJECT IDENTIFIER ::= { unisevtModuleSwitchType 684 } -- 4-Port 10GBASE Ethernet Optical Interface Board(XFP,LC)(SE)
unisevtModuleSw-LSQ1FAB08A0                 OBJECT IDENTIFIER ::= { unisevtModuleSwitchType 685 } -- Switching Fabric Board
unisevtModuleSw-EWPX2WCMD0                  OBJECT IDENTIFIER ::= { unisevtModuleSwitchType 686 } -- Access Controller Card
unisevtModuleSw-LSQ1WCMD0                   OBJECT IDENTIFIER ::= { unisevtModuleSwitchType 687 } -- Access Controller Card
unisevtModuleSw-LSQ1IAGSC0                  OBJECT IDENTIFIER ::= { unisevtModuleSwitchType 688 } -- Wireless&IAG Service Card
unisevtModuleSw-LSU1GP24TSE0                OBJECT IDENTIFIER ::= { unisevtModuleSwitchType 689 } -- 16-Port 1000BASE-X Optical Interface(SFP,LC)+8-Port Combo Interface Board(SE)
unisevtModuleSw-LSQ1TGS16SC0                OBJECT IDENTIFIER ::= { unisevtModuleSwitchType 690 } -- 16-Port 10GBASE Ethernet SFP+ Optical Interface Board
unisevtModuleSw-EWPX2TGS16SC0               OBJECT IDENTIFIER ::= { unisevtModuleSwitchType 691 } -- 16-Port 10GBASE Ethernet SFP+ Optical Interface Board
unisevtModuleSw-LSQ1SUPA3                   OBJECT IDENTIFIER ::= { unisevtModuleSwitchType 692 } -- Supervisor Engine Board
unisevtModuleSw-LSQ1FAB04A3                 OBJECT IDENTIFIER ::= { unisevtModuleSwitchType 693 } -- 320G Switch Fabric Board
unisevtModuleSw-LSQ1FAB08A3                 OBJECT IDENTIFIER ::= { unisevtModuleSwitchType 694 } -- 640G Switch Fabric Board
unisevtModuleSw-LSQ1GT48SC0                 OBJECT IDENTIFIER ::= { unisevtModuleSwitchType 695 } -- 48-Port 1000Base-T Gigabit Ethernet Interface Board(RJ45)
unisevtModuleSw-LSR2SRP2C1                  OBJECT IDENTIFIER ::= { unisevtModuleSwitchType 696 } -- Management and Route Process Unit
unisevtModuleSw-LSR2SRP2C2                  OBJECT IDENTIFIER ::= { unisevtModuleSwitchType 697 } -- Management and Route Process Unit

--
-- 700 to 799 reserved for primary switches
--
unisevtModuleSw-1000BASE-X-COMBO            OBJECT IDENTIFIER ::= { unisevtModuleSwitchType 701 } -- Single port 10/100/1000BASE-T/1000BASE-X Combo Interface Board
unisevtModuleSw-EPON-1000M                  OBJECT IDENTIFIER ::= { unisevtModuleSwitchType 702 } -- Optical Network Unit Interface Board
unisevtModuleSw-1000BASE-FIXED-2SFP-T-2RJ45         OBJECT IDENTIFIER ::= { unisevtModuleSwitchType 703 } -- 2 port 10/100/1000BASE-T and 2 port 1000BASE-X Interface Board
unisevtModuleSw-100M-1550-BIDI              OBJECT IDENTIFIER ::= { unisevtModuleSwitchType 704 }  -- 100BASE-X BIDI Interface Board, Tx 1550nm, Rx 1310nm
unisevtModuleSw-100M-1310-BIDI              OBJECT IDENTIFIER ::= { unisevtModuleSwitchType 705 }  -- 100BASE-X reverse Interface Board, Tx 1310nm, Rx 1550nm
unisevtModuleSw-1000BASE-FIXED-4RJ45-4SFP-COMBO     OBJECT IDENTIFIER ::= { unisevtModuleSwitchType 706 } -- 4 port 10/100/1000BASE-T and 4 port 1000BASE-X COMBO Interface Board
unisevtModuleSw-LSH1PK2T                    OBJECT IDENTIFIER ::= { unisevtModuleSwitchType 707 } -- OSM Interface Board
unisevtModuleSw-LSPM2GP2P                   OBJECT IDENTIFIER ::= { unisevtModuleSwitchType 708 } -- 2-Port 1000BASE-X SFP Module
unisevtModuleSw-LSWM1GT16P                  OBJECT IDENTIFIER ::= { unisevtModuleSwitchType 709 } -- 16-Port 10/100/1000BASE-T Ethernet Electrical Interface Module
unisevtModuleSw-LSWM1GP16P                  OBJECT IDENTIFIER ::= { unisevtModuleSwitchType 710 } -- 16-Port 100/1000BASE-X Ethernet Optical Interface Module
unisevtModuleSw-LSWM1XP2P                   OBJECT IDENTIFIER ::= { unisevtModuleSwitchType 711 } -- 2-Port 10G Ethernet XFP Optical Interface Module
unisevtModuleSw-LSWM1XP4P                   OBJECT IDENTIFIER ::= { unisevtModuleSwitchType 712 } -- 4-Port 10G Ethernet XFP Optical Interface Module
unisevtModuleSw-LSWM1SP2P                   OBJECT IDENTIFIER ::= { unisevtModuleSwitchType 713 } -- 2-Port 10G Ethernet SFP PLUS Optical Interface Module
unisevtModuleSw-LSWM1SP4P                   OBJECT IDENTIFIER ::= { unisevtModuleSwitchType 714 } -- 4-Port 10G Ethernet SFP PLUS Optical Interface Module
unisevtModuleSw-LSWM148POEM                 OBJECT IDENTIFIER ::= { unisevtModuleSwitchType 715 } -- 48 Port Mid Power PoE Module
unisevtModuleSw-LSWM1FW10                   OBJECT IDENTIFIER ::= { unisevtModuleSwitchType 716 } -- RMI CPU XLR 732, with Firewall software
unisevtModuleSw-LSWM1WCM10                  OBJECT IDENTIFIER ::= { unisevtModuleSwitchType 717 } -- RMI CPU XLR 732, with Wireless Access Controller software
unisevtModuleSw-LSWM1IPS10                  OBJECT IDENTIFIER ::= { unisevtModuleSwitchType 718 } -- RMI CPU XLR 732, with IPS/AV software
unisevtModuleSw-LSWM1WCM20                  OBJECT IDENTIFIER ::= { unisevtModuleSwitchType 719 } -- RMI CPU XLR 408, with Wireless Access Controller software
unisevtModuleSw-IPS-T1000-M                 OBJECT IDENTIFIER ::= { unisevtModuleSwitchType 720 } -- IPS for T1000-M mainboard module
unisevtModuleSw-IPS-T1000-A                 OBJECT IDENTIFIER ::= { unisevtModuleSwitchType 721 } -- IPS for T1000-A mainboard module
unisevtModuleSw-IPS-T1000-S                 OBJECT IDENTIFIER ::= { unisevtModuleSwitchType 722 } -- IPS for T1000-S mainboard module
unisevtModuleSw-IPS-GX4C                    OBJECT IDENTIFIER ::= { unisevtModuleSwitchType 723 } -- four-port-gigabit-fiber-board－module
unisevtModuleSw-IPS-GT4C                    OBJECT IDENTIFIER ::= { unisevtModuleSwitchType 724 } -- four-port-1000BASET-board－module
unisevtModuleSw-LSPM2SP2P                   OBJECT IDENTIFIER ::= { unisevtModuleSwitchType 725 } -- 2-Port 10G Ethernet SFP PLUS Optical Interface Module
unisevtModuleSw-LSPM2SP2PA                  OBJECT IDENTIFIER ::= { unisevtModuleSwitchType 726 } -- 2-Port Second Version SFP+ Module
unisevtModuleSw-LSP5GP8P                    OBJECT IDENTIFIER ::= { unisevtModuleSwitchType 727 } -- 8-Port 1G Ethernet SFP Optical Interface Module
unisevtModuleSw-LSP5GT8P                    OBJECT IDENTIFIER ::= { unisevtModuleSwitchType 728 } -- 8-Port 10/100/1000BASE-T Ethernet Electrical Interface Module
unisevtModuleSw-LSWM1FC4P                   OBJECT IDENTIFIER ::= { unisevtModuleSwitchType 729 } -- 4-Port 8G Fibre Channel Interface Module
unisevtModuleSw-LSW1XGT4P0                  OBJECT IDENTIFIER ::= { unisevtModuleSwitchType 730 } -- 4-Port 10G Ethernet Copper Interface Module
unisevtModuleSw-LSW1XGT2P0                  OBJECT IDENTIFIER ::= { unisevtModuleSwitchType 731 } -- 2-Port 10G Ethernet Copper Interface Module
unisevtModuleSw-LSP1XGT2P                   OBJECT IDENTIFIER ::= { unisevtModuleSwitchType 732 } -- 2-Port 10G Ethernet Copper Interface Board
unisevtModuleSw-LSPM3XGT2P                  OBJECT IDENTIFIER ::= { unisevtModuleSwitchType 733 } -- 2-Port 1/10G BASE-T Ethernet Copper Interface Module
unisevtModuleSw-LSWM2QP2P                   OBJECT IDENTIFIER ::= { unisevtModuleSwitchType 734 } -- 2-Port QSFP+ Interface Module
unisevtModuleSw-LSWM2XGT2PM                 OBJECT IDENTIFIER ::= { unisevtModuleSwitchType 735 } -- 2-Port 10G Ethernet Copper Interface Module with MACsec
unisevtModuleSw-LSWM2SP2PM                  OBJECT IDENTIFIER ::= { unisevtModuleSwitchType 736 } -- 2-Port SFP+ Interface Module with MACsec
unisevtModuleSw-LSWM2SP8PM                  OBJECT IDENTIFIER ::= { unisevtModuleSwitchType 737 } -- 8-Port SFP+ Interface Module with MACsec
unisevtModuleSw-LSWM2SP8P                   OBJECT IDENTIFIER ::= { unisevtModuleSwitchType 738 } -- 8-Port SFP+ Interface Module
unisevtModuleSw-LSWM2XGT8PM                 OBJECT IDENTIFIER ::= { unisevtModuleSwitchType 739 } -- 8-Port 10G Ethernet Copper Interface Module with MACsec
unisevtModuleSw-LSWM18QC                    OBJECT IDENTIFIER ::= { unisevtModuleSwitchType 740 } -- 8-Port QSFP+ Module
unisevtModuleSw-LSWM124XG2Q                 OBJECT IDENTIFIER ::= { unisevtModuleSwitchType 741 } -- 24-Port SFP+ and 2-Port QSFP+ Module
unisevtModuleSw-LSWM124XGT2Q                OBJECT IDENTIFIER ::= { unisevtModuleSwitchType 742 } -- 24-Port 10G BASE-T and 2-Port QSFP+ Module
unisevtModuleSw-LSWM124XG2QL                OBJECT IDENTIFIER ::= { unisevtModuleSwitchType 743 } -- 24-Port SFP+ and 2-Port QSFP+ Module
unisevtModuleSw-LSWM124XG2QFC               OBJECT IDENTIFIER ::= { unisevtModuleSwitchType 744 } -- 24-Port 8G Fibre Channel Interface and 2-Port QSFP+ Module
unisevtModuleSw-LSWM18QC0                   OBJECT IDENTIFIER ::= { unisevtModuleSwitchType 745 } -- 8-Port QSFP+ Module
unisevtModuleSw-LSWM124XGT2Q0               OBJECT IDENTIFIER ::= { unisevtModuleSwitchType 746 } -- 24-Port 10G BASE-T and 2-Port QSFP+ Module
unisevtModuleSw-LSWM124XG2QL0               OBJECT IDENTIFIER ::= { unisevtModuleSwitchType 747 } -- 24-Port SFP+ and 2-Port QSFP+ Module
unisevtModuleSw-LSP6G4T6P                   OBJECT IDENTIFIER ::= { unisevtModuleSwitchType 748 } -- 6-Port SFP and 2-port 10/100/1000BASE-T COMBO and 2 port 10/100/1000BASE-T Interface Module
unisevtModuleSw-LSPM6QP2PS                  OBJECT IDENTIFIER ::= { unisevtModuleSwitchType 749 } -- 2-Port QSFP+ Stack Interface Module
unisevtModuleSw-LSWM12H2Q                   OBJECT IDENTIFIER ::= { unisevtModuleSwitchType 750 } -- 2-Port QSFP28 and 2-Port QSFP+ Module
unisevtModuleSw-LSWM18CQ                    OBJECT IDENTIFIER ::= { unisevtModuleSwitchType 751 } -- 8-Port QSFP28 Module
unisevtModuleSw-LSWM116Q                    OBJECT IDENTIFIER ::= { unisevtModuleSwitchType 752 } -- 16-Port QSFP+ Module
unisevtModuleSw-LSPM6FWD                    OBJECT IDENTIFIER ::= { unisevtModuleSwitchType 753 } -- Next Generation Firewall Module
unisevtModuleSw-DS-3E-2XT-H                 OBJECT IDENTIFIER ::= { unisevtModuleSwitchType 754 } -- 2-Port 10G Ethernet Copper Interface Module with MACsec
unisevtModuleSw-DS-3E-2XF-H                 OBJECT IDENTIFIER ::= { unisevtModuleSwitchType 755 } -- 2-Port SFP+ Interface Module with MACsec
unisevtModuleSw-DS-3E-2QX-H                 OBJECT IDENTIFIER ::= { unisevtModuleSwitchType 756 } -- 2-Port QSFP+ Stack Interface Module
unisevtModuleSw-LSPM4G4T6P                  OBJECT IDENTIFIER ::= { unisevtModuleSwitchType 757 } -- 6-Port SFP and 2-port 10/100/1000BASE-T COMBO and 2 port 10/100/1000BASE-T Interface Module
unisevtModuleSw-LSWM4SP8PM                  OBJECT IDENTIFIER ::= { unisevtModuleSwitchType 758 } -- 8-Port SFP+ Interface Module with MACsec
unisevtModuleSw-LSWM124TG2H                 OBJECT IDENTIFIER ::= { unisevtModuleSwitchType 759 } -- 24-Port SFP28 and 2-Port QSFP28 Module
unisevtModuleSw-LSWM18CQ0                   OBJECT IDENTIFIER ::= { unisevtModuleSwitchType 760 } -- 8-Port QSFP28 Module
unisevtModuleSw-LSWM116Q0                   OBJECT IDENTIFIER ::= { unisevtModuleSwitchType 761 } -- 16-Port QSFP+ Module
unisevtModuleSw-LSWM124TG2H0                OBJECT IDENTIFIER ::= { unisevtModuleSwitchType 762 } -- 24-Port SFP28 and 2-Port QSFP28 Module
unisevtModuleSw-LSWM2ZQP2P                  OBJECT IDENTIFIER ::= { unisevtModuleSwitchType 763 } -- 2-Port QSFP28 Module
unisevtModuleSw-LSWM2ZSP8P                  OBJECT IDENTIFIER ::= { unisevtModuleSwitchType 764 } -- 8-Port SFP28 Module
unisevtModuleSw-LSWM18CQMSEC                OBJECT IDENTIFIER ::= { unisevtModuleSwitchType 765 } -- 8-Port QSFP28 MACSEC Module
unisevtModuleSw-LSWM2MGT8P                  OBJECT IDENTIFIER ::= { unisevtModuleSwitchType 766 } -- 8-Port SmartGE (5/2.5/1G) Interface Module
unisevtModuleSw-LSWM2XMGT8P                 OBJECT IDENTIFIER ::= { unisevtModuleSwitchType 767 } -- 8-Port SmartGE (10/5/2.5/1G) Interface Module
unisevtModuleSw-LSWM2ZSP2P                  OBJECT IDENTIFIER ::= { unisevtModuleSwitchType 768 } -- 2-Port SFP28 Interface Module
unisevtModuleSw-LSWM116FC                   OBJECT IDENTIFIER ::= { unisevtModuleSwitchType 769 } -- 16-Ports SFP28 Ethernet Optical Interface Module with 16G/32G FC
unisevtModuleSw-LSWM216FC                   OBJECT IDENTIFIER ::= { unisevtModuleSwitchType 770 } -- 16-Ports SFP28 Ethernet Optical Interface Module with 16G/32G FC
unisevtModuleSw-LSWM2SP2PB                  OBJECT IDENTIFIER ::= { unisevtModuleSwitchType 771 } -- 2-Port SFP+ Interface Module
unisevtModuleSw-LSWM2SP4PB                  OBJECT IDENTIFIER ::= { unisevtModuleSwitchType 772 } -- 4-Port SFP+ Interface Module
unisevtModuleSw-LSWM2SP24P                  OBJECT IDENTIFIER ::= { unisevtModuleSwitchType 773 } -- 24-Port SFP+ Interface Module
unisevtModuleSw-LSWM2SP12P2Q                OBJECT IDENTIFIER ::= { unisevtModuleSwitchType 774 } -- 12-Port SFP+ and 2-Port QSFP+ Interface Module
unisevtModuleSw-LSWM2SP12P2QA               OBJECT IDENTIFIER ::= { unisevtModuleSwitchType 775 } -- 12-Port SFP+ and 2-Port QSFP+ Interface Module with wider size
unisevtModuleSw-DS-3E-2QX-HB                OBJECT IDENTIFIER ::= { unisevtModuleSwitchType 776 } -- 2-Port QSFP+ Interface Module
unisevtModuleSw-DS-3E-8XF-H                 OBJECT IDENTIFIER ::= { unisevtModuleSwitchType 777 } -- 8-Port SFP+ Interface Module
unisevtModuleSw-LSWM18CQMSEC-Z              OBJECT IDENTIFIER ::= { unisevtModuleSwitchType 778 } -- 8-Port QSFP28 MACSEC Module
unisevtModuleSw-LSWM124XG2QFC-Z             OBJECT IDENTIFIER ::= { unisevtModuleSwitchType 779 } -- 24-Port 8G Fibre Channel Interface and 2-Port QSFP+ Module
unisevtModuleSw-LSWM124TG2H-Z               OBJECT IDENTIFIER ::= { unisevtModuleSwitchType 780 } -- 24-Port SFP28 and 2-Port QSFP28 Module

--
-- 800 to 899 reserved for WLAN products
--
unisevtModuleSw-WX5002MPU                   OBJECT IDENTIFIER ::= { unisevtModuleSwitchType 800 } -- Wireless Lan Control Board with 2-port 1000BASE-T/1000BASE-X Combo Interface
unisevtModuleSw-LS8M1WCMA                   OBJECT IDENTIFIER ::= { unisevtModuleSwitchType 801 } -- Wireless Lan Service Board
unisevtModuleSw-EWPX1G24XA0                 OBJECT IDENTIFIER ::= { unisevtModuleSwitchType 802 } -- 24-Port 1000BASE-T Gigabit Ethernet Interface(RJ45) and 4-port 1000BASE-T/1000BASE-X Combo Interface and 2-port 10GBASE Interface Line Card
unisevtModuleSw-LSQ1WCMB0                   OBJECT IDENTIFIER ::= { unisevtModuleSwitchType 803 } -- 1 Port 10GBASE Interface Board
unisevtModuleSw-LSB1WCM2A0                  OBJECT IDENTIFIER ::= { unisevtModuleSwitchType 804 } -- Wireless Controller Module Board
unisevtModuleSw-EWPX1WCMB0                  OBJECT IDENTIFIER ::= { unisevtModuleSwitchType 805 } -- 1 Port 10GBASE Interface Board
unisevtModuleSw-EWPX1G24XC0                 OBJECT IDENTIFIER ::= { unisevtModuleSwitchType 806 } -- 24-Port 1000BASE-T Gigabit Ethernet Interface(RJ45) and 4-port 1000BASE-T/1000BASE-X Combo Interface Line Card
unisevtModuleSw-EWPX1WCMC0                  OBJECT IDENTIFIER ::= { unisevtModuleSwitchType 807 } -- 1-Port 1000BASE-T Gigabit Ethernet of wireless Lan Service Board
unisevtModuleSw-EWPX1FWA0                   OBJECT IDENTIFIER ::= { unisevtModuleSwitchType 808 } -- Firewall Service Board
unisevtModuleSw-EWPX1G10XC0                 OBJECT IDENTIFIER ::= { unisevtModuleSwitchType 809 } -- 8-Port 1000BASE-T Gigabit Ethernet Interface(RJ45) and 2-port 1000BASE-X SFP Interface Line Card
unisevtModuleSw-EWPX1WCM10C0                OBJECT IDENTIFIER ::= { unisevtModuleSwitchType 810 } -- 1-Port 1000BASE-T Gigabit Ethernet of wireless Lan Service Board
unisevtModuleSw-LSR1WCM2A1                  OBJECT IDENTIFIER ::= { unisevtModuleSwitchType 811 } -- 1-Port 1000BASE-T Gigabit Ethernet of wireless Lan Service Board
unisevtModuleSw-EWPX1WAP0                   OBJECT IDENTIFIER ::= { unisevtModuleSwitchType 812 } -- Encryption Card
unisevtModuleSw-EWPX1WCMD0                  OBJECT IDENTIFIER ::= { unisevtModuleSwitchType 813 } -- 2 Port 10GBASE Interface Board
unisevtModuleSw-EWPX1G24XCE0                OBJECT IDENTIFIER ::= { unisevtModuleSwitchType 814 } -- 24-Port 1000BASE-T Gigabit Ethernet Interface(RJ45) and 4-port 1000BASE-T/1000BASE-X Combo Interface Line Card
unisevtModuleSw-EWPX1WCMCE0                 OBJECT IDENTIFIER ::= { unisevtModuleSwitchType 815 } -- 2-Port 1000BASE-T Gigabit Ethernet of wireless Lan Service Board
unisevtModuleSw-EWPX1G24XD0                 OBJECT IDENTIFIER ::= { unisevtModuleSwitchType 816 } -- 4-Port 10GBASE-T and 24-Port 1000BASE-T Gigabit Ethernet of wireless Lan Service Board
unisevtModuleSw-EWPXM1XG03                  OBJECT IDENTIFIER ::= { unisevtModuleSwitchType 817 } -- 8GE and 2SFP Plus Interface Board  of wireless Lan Service Board
unisevtModuleSw-EWPXM2X                     OBJECT IDENTIFIER ::= { unisevtModuleSwitchType 818 } -- 2SFP Plus Interface Board  of wireless Lan Service Board
unisevtModuleSw-EWPXM8G                     OBJECT IDENTIFIER ::= { unisevtModuleSwitchType 819 } -- 8GE Interface Board  of wireless Lan Service Board
unisevtModuleSw-IOT-CARD-C1K                OBJECT IDENTIFIER ::= { unisevtModuleSwitchType 820 } -- IoT Service Board for Wireless Controller

--
-- 900 to 1199 reserved for advanced switches part II
--
unisevtModuleSw-LSR1DRSP2L1                 OBJECT IDENTIFIER ::= { unisevtModuleSwitchType 900 } -- 2-Port OC-48c/STM-16c RPR Optical Interface Card,(SFP,LC)
unisevtModuleSw-PIC-CLF2G8L                 OBJECT IDENTIFIER ::= { unisevtModuleSwitchType 901 } -- 2-Port 155M CPOS Optical Interface(SFP,LC)+8-Port 1000BASE-X Optical Interface Card(SFP,LC)
unisevtModuleSw-PIC-CLF4G8L                 OBJECT IDENTIFIER ::= { unisevtModuleSwitchType 902 } -- 4-Port 155M CPOS Optical Interface(SFP,LC)+8-Port 1000BASE-X Optical Interface Card(SFP,LC)
unisevtModuleSw-SR02SRP2F3                  OBJECT IDENTIFIER ::= { unisevtModuleSwitchType 903 } -- Routing Switch Processing Board(2F)
unisevtModuleSw-SR02SRP1F3                  OBJECT IDENTIFIER ::= { unisevtModuleSwitchType 904 } -- Routing Switch Processing Board(1F)
unisevtModuleSw-LST1GT48LEA1                OBJECT IDENTIFIER ::= { unisevtModuleSwitchType 905 } -- 48-Port 10/100/1000BASE-T Interface Module(LEA),(RJ45)
unisevtModuleSw-LST1GP48LEA1                OBJECT IDENTIFIER ::= { unisevtModuleSwitchType 906 } -- 48-Port 1000BASE-X Interface Module(LEA),(SFP,LC)
unisevtModuleSw-LST2XP8LEA1                 OBJECT IDENTIFIER ::= { unisevtModuleSwitchType 907 } -- 8-Port 10GBASE-R Interface Module(LEA),(SFP+,LC)
unisevtModuleSw-LST1GT48LEY1                OBJECT IDENTIFIER ::= { unisevtModuleSwitchType 908 } -- 48-Port 10/100/1000BASE-T Interface Module(LEY),(RJ45)
unisevtModuleSw-LST1GP48LEY1                OBJECT IDENTIFIER ::= { unisevtModuleSwitchType 909 } -- 48-Port 1000BASE-X Interface Module(LEY),(SFP,LC)
unisevtModuleSw-LST1XP32REY1                OBJECT IDENTIFIER ::= { unisevtModuleSwitchType 910 } -- 32-Port 10GBASE-R Interface Module(REY),(SFP+,LC)
unisevtModuleSw-LST1XP8LEY1                 OBJECT IDENTIFIER ::= { unisevtModuleSwitchType 911 } -- 8-Port 10GBASE-R/W Interface Module(LEY),(XFP,LC)
unisevtModuleSw-LST1GP48LEZ1                OBJECT IDENTIFIER ::= { unisevtModuleSwitchType 912 } -- 48-Port 1000BASE-X Interface Module(LEZ),(SFP,LC)
unisevtModuleSw-LST1XP8LEZ1                 OBJECT IDENTIFIER ::= { unisevtModuleSwitchType 913 } -- 8-Port 10GBASE-R/W Interface Module(LEZ),(XFP,LC)
unisevtModuleSw-IM-FW-II                    OBJECT IDENTIFIER ::= { unisevtModuleSwitchType 914 } -- Firewall Service Processing Board-II
unisevtModuleSw-IM-IPS                      OBJECT IDENTIFIER ::= { unisevtModuleSwitchType 915 } -- Intrusion Prevention System Service Processing Board
unisevtModuleSw-IM-SSL                      OBJECT IDENTIFIER ::= { unisevtModuleSwitchType 916 } -- SSL VPN Service Processing Board
unisevtModuleSw-IM-LB                       OBJECT IDENTIFIER ::= { unisevtModuleSwitchType 917 } -- Load Balance Service Processing Board
unisevtModuleSw-IM-ACG                      OBJECT IDENTIFIER ::= { unisevtModuleSwitchType 918 } -- Application Control Gateway Service Processing Board
unisevtModuleSw-LSR1XP16REC1                OBJECT IDENTIFIER ::= { unisevtModuleSwitchType 919 } -- 16-Port 10GBASE-R Interface Module(REC),(SFP+,LC)
unisevtModuleSw-LST2XP8LEB1                 OBJECT IDENTIFIER ::= { unisevtModuleSwitchType 920 } -- 8-Port 10GBASE-R/W Interface Module(LEB),(XFP,LC)
unisevtModuleSw-LST2XP8LEC1                 OBJECT IDENTIFIER ::= { unisevtModuleSwitchType 921 } -- 8-Port 10GBASE-R/W Interface Module(LEC),(XFP,LC)
unisevtModuleSw-LST2XP8LEF1                 OBJECT IDENTIFIER ::= { unisevtModuleSwitchType 922 } -- 8-Port 10GBASE-R/W Interface Module(LEF),(XFP,LC)
unisevtModuleSw-LSR2XP4LEB1                 OBJECT IDENTIFIER ::= { unisevtModuleSwitchType 923 } -- 4-Port 10GBase-R/W Interface Module(LEB),(XFP,LC)
unisevtModuleSw-LSR2XP4LEC1                 OBJECT IDENTIFIER ::= { unisevtModuleSwitchType 924 } -- 4-Port 10GBase-R/W Interface Module(LEC),(XFP,LC)
unisevtModuleSw-LST2XP32REB1                OBJECT IDENTIFIER ::= { unisevtModuleSwitchType 925 } -- 32-Port 10GBASE-R Interface Module(REB),(SFP+,LC)
unisevtModuleSw-LST2XP32REC1                OBJECT IDENTIFIER ::= { unisevtModuleSwitchType 926 } -- 32-Port 10GBASE-R Interface Module(REC),(SFP+,LC)
unisevtModuleSw-LSR1WCM3A1                  OBJECT IDENTIFIER ::= { unisevtModuleSwitchType 927 } -- Access Controller Module
unisevtModuleSw-LST1XP16LEB1                OBJECT IDENTIFIER ::= { unisevtModuleSwitchType 928 } -- 16-Port 10GBASE-R Interface Module (LEB),(SFP+,LC)
unisevtModuleSw-LST1XP16LEC1                OBJECT IDENTIFIER ::= { unisevtModuleSwitchType 929 } -- 16-Port 10GBASE-R Interface Module (LEC),(SFP+,LC)
unisevtModuleSw-CR-SPC-XP4L-E-I             OBJECT IDENTIFIER ::= { unisevtModuleSwitchType 930 } -- 4-Port 10GBASE-R/W Optical Interface Module,(XFP,LC)
unisevtModuleSw-LST2MRPNC1                  OBJECT IDENTIFIER ::= { unisevtModuleSwitchType 931 } -- Management and Route Process Unit
unisevtModuleSw-LST2SF08C1                  OBJECT IDENTIFIER ::= { unisevtModuleSwitchType 932 } -- Switch Fabric Card
unisevtModuleSw-LST2SF18C1                  OBJECT IDENTIFIER ::= { unisevtModuleSwitchType 933 } -- Switch Fabric Card
unisevtModuleSw-SR02SRP2G3                  OBJECT IDENTIFIER ::= { unisevtModuleSwitchType 934 } -- Routing Switch Processing Board(2G)
unisevtModuleSw-CR-SPE-3020-E-I             OBJECT IDENTIFIER ::= { unisevtModuleSwitchType 935 } -- CR15LN3CNA1, Dual Service Processing Board
unisevtModuleSw-CR-SPC-PUP4L-E-I            OBJECT IDENTIFIER ::= { unisevtModuleSwitchType 936 } -- 4-Port 10G POS Optical Interface Board(Enhanced),(XFP,LC)
unisevtModuleSw-CR-SPC-XP4LEF-I             OBJECT IDENTIFIER ::= { unisevtModuleSwitchType 937 } -- 4-Port 10GBASE-R/W Interface Module (LEF),(XFP,LC)
unisevtModuleSw-CR-SPC-XP8LEF-I             OBJECT IDENTIFIER ::= { unisevtModuleSwitchType 938 } -- 8-Port 10GBASE-R/W Interface Module (LEF),(XFP,LC)
unisevtModuleSw-LST3XP8LEB1                 OBJECT IDENTIFIER ::= { unisevtModuleSwitchType 939 } -- 8-Port 10GBASE-R Interface Module (LEB),(XFP,LC)
unisevtModuleSw-LST3XP8LEC1                 OBJECT IDENTIFIER ::= { unisevtModuleSwitchType 940 } -- 8-Port 10GBASE-R Interface Module (LEC),(XFP,LC)
unisevtModuleSw-LST1FW3A1                   OBJECT IDENTIFIER ::= { unisevtModuleSwitchType 941 } -- Firewall Board
unisevtModuleSw-CR-IM-NAM1A                 OBJECT IDENTIFIER ::= { unisevtModuleSwitchType 942 } -- CR1M1NAM1A1, Network Analysis Service Module, Domestic&Overseas Version
unisevtModuleSw-LSR2SRP2B1                  OBJECT IDENTIFIER ::= { unisevtModuleSwitchType 943 } -- Management and Route Process Unit
unisevtModuleSw-LSR2SRP2B2                  OBJECT IDENTIFIER ::= { unisevtModuleSwitchType 944 } -- Management and Route Process Unit
unisevtModuleSw-LSR2SRP2D1                  OBJECT IDENTIFIER ::= { unisevtModuleSwitchType 945 } -- Management and Route Process Unit
unisevtModuleSw-LST3XP8LEY1                 OBJECT IDENTIFIER ::= { unisevtModuleSwitchType 946 } -- 8-Port 10GBASE-R/W Interface Module (LEY),(XFP,LC)
unisevtModuleSw-LST2XP32REY1                OBJECT IDENTIFIER ::= { unisevtModuleSwitchType 947 } -- 32-Port 10GBASE-R Interface Module(REY),(SFP+,LC)
unisevtModuleSw-LST1XP16LEY1                OBJECT IDENTIFIER ::= { unisevtModuleSwitchType 948 } -- 16-Port 10GBASE-R Interface Module (LEY),(SFP+,LC)
unisevtModuleSw-SR0M2SRP2G3                 OBJECT IDENTIFIER ::= { unisevtModuleSwitchType 949 } -- Routing Switch Processing Board(2G)
unisevtModuleSw-SR0M2SRP1G3                 OBJECT IDENTIFIER ::= { unisevtModuleSwitchType 950 } -- Routing Switch Processing Board(1G)
unisevtModuleSw-SPC-GP48LA                  OBJECT IDENTIFIER ::= { unisevtModuleSwitchType 951 } -- 48-Port 1000BASE-X Interface Service Module,(SFP,LC)
unisevtModuleSw-SPC-GT48LA                  OBJECT IDENTIFIER ::= { unisevtModuleSwitchType 952 } -- 48-Port 10/100/1000BASE-T Interface Service Module,(RJ45)
unisevtModuleSw-SPC-XP4LA                   OBJECT IDENTIFIER ::= { unisevtModuleSwitchType 953 } -- 4-Port 10GBase-R/W Interface Service Module,(XFP,LC)
unisevtModuleSw-SPC-XP2LA                   OBJECT IDENTIFIER ::= { unisevtModuleSwitchType 954 } -- 2-Port 10GBASE-R/W Interface Service Module,(XFP,LC)
unisevtModuleSw-SPC-GP24LA                  OBJECT IDENTIFIER ::= { unisevtModuleSwitchType 955 } -- 16-Port 1000BASE-X Interface(SFP,LC)+8-Port Combo Interface Service Module
unisevtModuleSw-SPC-XP16RA                  OBJECT IDENTIFIER ::= { unisevtModuleSwitchType 956 } -- 16-Port 10GBASE-R Optical Interface Service Module(RA),(SFP+,LC)
unisevtModuleSw-CR-IM-FW1A                  OBJECT IDENTIFIER ::= { unisevtModuleSwitchType 957 } -- Firewall Service Processing Board
unisevtModuleSw-SPC-XP16R                   OBJECT IDENTIFIER ::= { unisevtModuleSwitchType 958 } -- 16-Port 10GBASE-R Optical Interface Service Module(R),(SFP+,LC)
unisevtModuleSw-CR-IM-LB1A                  OBJECT IDENTIFIER ::= { unisevtModuleSwitchType 959 } -- Load Balancing Service Processing Board
unisevtModuleSw-LST1GT48LEC2                OBJECT IDENTIFIER ::= { unisevtModuleSwitchType 960 } -- 48-Port 10/100/1000BASE-T Interface Module(LEC),(RJ45)
unisevtModuleSw-LST1GP48LEC2                OBJECT IDENTIFIER ::= { unisevtModuleSwitchType 961 } -- 48-Port 1000BASE-X Interface Module (LEC),(SFP,LC)
unisevtModuleSw-LST1XP16LEC2                OBJECT IDENTIFIER ::= { unisevtModuleSwitchType 962 } -- 16-Port 10GBASE-R Interface Module (LEC),(SFP+,LC)
unisevtModuleSw-LST2XP8LEC2                 OBJECT IDENTIFIER ::= { unisevtModuleSwitchType 963 } -- 8-Port 10GBASE-R/W Interface Module(LEC),(XFP,LC)
unisevtModuleSw-LST2XP32REC2                OBJECT IDENTIFIER ::= { unisevtModuleSwitchType 964 } -- 32-Port 10GBASE-R Interface Module(REC),(SFP+,LC)
unisevtModuleSw-CR-IM-MAC1A                 OBJECT IDENTIFIER ::= { unisevtModuleSwitchType 965 } -- Master Access Control Service Module
unisevtModuleSw-LST1XP48LFD1                OBJECT IDENTIFIER ::= { unisevtModuleSwitchType 966 } -- 48-Port 10GBASE-R Interface Module (LFD),(SFP+,LC)
unisevtModuleSw-LST1XP40RFD1                OBJECT IDENTIFIER ::= { unisevtModuleSwitchType 967 } -- 40-Port 10GBASE-R Interface Module (RFD),(SFP+,LC)
unisevtModuleSw-LST1XP40RFG1                OBJECT IDENTIFIER ::= { unisevtModuleSwitchType 968 } -- 40-Port 10GBASE-R/W Interface Module (RFG),(SFP+,LC)
unisevtModuleSw-LST1XLP16RFD1               OBJECT IDENTIFIER ::= { unisevtModuleSwitchType 969 } -- 16-Port 40GBASE-R Interface Module (RFD),(QSFP+,LC)
unisevtModuleSw-LST1CP4RFD1                 OBJECT IDENTIFIER ::= { unisevtModuleSwitchType 970 } -- 4-Port 100GBASE-R Interface Module (RFD),(CFP,LC)
unisevtModuleSw-LST1CP4RFG1                 OBJECT IDENTIFIER ::= { unisevtModuleSwitchType 971 } -- 4-Port 100GBASE-R Interface Module (RFG),(CFP,LC)
unisevtModuleSw-LST1SF08E1                  OBJECT IDENTIFIER ::= { unisevtModuleSwitchType 972 } -- Switch Fabric Card
unisevtModuleSw-LST1SF18E1                  OBJECT IDENTIFIER ::= { unisevtModuleSwitchType 973 } -- Switch Fabric Card
unisevtModuleSw-LST1MRPNE1                  OBJECT IDENTIFIER ::= { unisevtModuleSwitchType 974 } -- Management and Route Process Unit
unisevtModuleSw-LSX1CGX8FC0                 OBJECT IDENTIFIER ::= { unisevtModuleSwitchType 975 } -- 8-Port 100GBASE-R Interface Module (FC),(CXP,MPO)
unisevtModuleSw-LSX1CGX8FC1                 OBJECT IDENTIFIER ::= { unisevtModuleSwitchType 976 } -- 8-Port 100GBASE-R Interface Module (FC),(CXP,MPO)
unisevtModuleSw-LSX1QGS24FC0                OBJECT IDENTIFIER ::= { unisevtModuleSwitchType 977 } -- 24-Port 40GBASE-R Interface Module (FC),(QSFP+)
unisevtModuleSw-LSX1QGS24FC1                OBJECT IDENTIFIER ::= { unisevtModuleSwitchType 978 } -- 24-Port 40GBASE-R Interface Module (FC),(QSFP+)
unisevtModuleSw-LSX1TGS24FC0                OBJECT IDENTIFIER ::= { unisevtModuleSwitchType 979 } -- 24-Port 10GBASE-R Interface Module (FC),(SFP+,LC)
unisevtModuleSw-LSX1TGS24FC1                OBJECT IDENTIFIER ::= { unisevtModuleSwitchType 980 } -- 24-Port 10GBASE-R Interface Module (FC),(SFP+,LC)
unisevtModuleSw-LSX1TGS48FC0                OBJECT IDENTIFIER ::= { unisevtModuleSwitchType 981 } -- 48-Port 10GBASE-R Interface Module (FC),(SFP+,LC)
unisevtModuleSw-LSX1TGS48FC1                OBJECT IDENTIFIER ::= { unisevtModuleSwitchType 982 } -- 48-Port 10GBASE-R Interface Module (FC),(SFP+,LC)
unisevtModuleSw-LST1XP48LFD2                OBJECT IDENTIFIER ::= { unisevtModuleSwitchType 983 } -- 48-Port 10GBASE-R Interface Module (LFD),(SFP+,LC)
unisevtModuleSw-LST1XP40RFD2                OBJECT IDENTIFIER ::= { unisevtModuleSwitchType 984 } -- 40-Port 10GBASE-R Interface Module (RFD),(SFP+,LC)
unisevtModuleSw-LST1XP40RFG2                OBJECT IDENTIFIER ::= { unisevtModuleSwitchType 985 } -- 40-Port 10GBASE-R/W Interface Module (RFG),(SFP+,LC)
unisevtModuleSw-LST1XLP16RFD2               OBJECT IDENTIFIER ::= { unisevtModuleSwitchType 986 } -- 16-Port 40GBASE-R Interface Module (RFD),(QSFP+)
unisevtModuleSw-LST1CP4RFD2                 OBJECT IDENTIFIER ::= { unisevtModuleSwitchType 987 } -- 4-Port 100GBASE-R Interface Module (RFD),(CFP)
unisevtModuleSw-LST1CP4RFG2                 OBJECT IDENTIFIER ::= { unisevtModuleSwitchType 988 } -- 4-Port 100GBASE-R Interface Module (RFG),(CFP)
unisevtModuleSw-MPE-1004                    OBJECT IDENTIFIER ::= { unisevtModuleSwitchType 989 } -- Multi-Service Processing Engine
unisevtModuleSw-MIC-GP4L                    OBJECT IDENTIFIER ::= { unisevtModuleSwitchType 990 } -- 4-Port 1000BASE-X COMBO Interface Card,(SFP,LC)
unisevtModuleSw-MIC-GP8L                    OBJECT IDENTIFIER ::= { unisevtModuleSwitchType 991 } -- 8-Port 1000BASE-X Optical Interface Card,(SFP,LC)
unisevtModuleSw-MIC-SP4L                    OBJECT IDENTIFIER ::= { unisevtModuleSwitchType 992 } -- 4-Port OC-3/STM-1 POS/CPOS/ATM or 1-Port OC-12/STM-4 POS/ATM Optical Interface Card,(SFP,LC)
unisevtModuleSw-MIC-ET16L                   OBJECT IDENTIFIER ::= { unisevtModuleSwitchType 993 } -- 16-Port E1/T1 Electrical Interface Card
unisevtModuleSw-MIC-CLP4L                   OBJECT IDENTIFIER ::= { unisevtModuleSwitchType 994 } -- 4-Port OC-3/STM-1 CPOS/POS Optical Interface Card,(SFP,LC)
unisevtModuleSw-MIC-CLP2L                   OBJECT IDENTIFIER ::= { unisevtModuleSwitchType 995 } -- 2-Port OC-3/STM-1 CPOS/POS Optical Interface Card,(SFP,LC)
unisevtModuleSw-LST1IPS2A1                  OBJECT IDENTIFIER ::= { unisevtModuleSwitchType 996 } -- Intrusion Prevention System Module
unisevtModuleSw-SFC-04B                     OBJECT IDENTIFIER ::= { unisevtModuleSwitchType 997 } -- Switch Fabric Card(B Type)
unisevtModuleSw-SFC-04D                     OBJECT IDENTIFIER ::= { unisevtModuleSwitchType 998 } -- Switch Fabric Card(D Type)
unisevtModuleSw-SFC-08B                     OBJECT IDENTIFIER ::= { unisevtModuleSwitchType 999 } -- Switch Fabric Card(B Type)
unisevtModuleSw-SFC-08D                     OBJECT IDENTIFIER ::= { unisevtModuleSwitchType 1000 } -- Switch Fabric Card(D Type)
unisevtModuleSw-SFC-12B                     OBJECT IDENTIFIER ::= { unisevtModuleSwitchType 1001 } -- Switch Fabric Card(B Type)
unisevtModuleSw-SFC-12D                     OBJECT IDENTIFIER ::= { unisevtModuleSwitchType 1002 } -- Switch Fabric Card(D Type)
unisevtModuleSw-SR05SRP1H1                  OBJECT IDENTIFIER ::= { unisevtModuleSwitchType 1003 } -- Routing Switch Processing Unit(1H)
unisevtModuleSw-SPC-GP24LA1                 OBJECT IDENTIFIER ::= { unisevtModuleSwitchType 1004 } -- 16-Port 1000BASE-X Ethernet Optical Interface(SFP,LC)+8-Port Combo Interface Module(A Type)
unisevtModuleSw-SPC-GP24XP2LA               OBJECT IDENTIFIER ::= { unisevtModuleSwitchType 1005 } -- 16-Port 1000BASE-X Ethernet Optical Interface(SFP,LC)+8-Port Combo Interface+2-Port 10GE Optical Interface Module(XFP,LC)(A Type)
unisevtModuleSw-SPC-GP48LA1                 OBJECT IDENTIFIER ::= { unisevtModuleSwitchType 1006 } -- 48-Port 1000BASE-X Ethernet Optical Interface Module(SFP,LC)(A Type)
unisevtModuleSw-SPC-GP48LB                  OBJECT IDENTIFIER ::= { unisevtModuleSwitchType 1007 } -- 48-Port Enhanced 1000BASE-X Ethernet Optical Interface Module(SFP,LC)(B Type)
unisevtModuleSw-SPC-XP2LA1                  OBJECT IDENTIFIER ::= { unisevtModuleSwitchType 1008 } -- 2-Port 10GBASE Ethernet Optical Interface Module(XFP,LC)(A Type)
unisevtModuleSw-SPC-XP4LA1                  OBJECT IDENTIFIER ::= { unisevtModuleSwitchType 1009 } -- 4-Port 10GBASE Ethernet Optical Interface Module(XFP,LC)(A Type)
unisevtModuleSw-SPC-XP4LB                   OBJECT IDENTIFIER ::= { unisevtModuleSwitchType 1010 } -- 4-Port Enhanced 10GBASE Ethernet Optical Interface Module(XFP,LC)(B Type)
unisevtModuleSw-SPC-XP8LA                   OBJECT IDENTIFIER ::= { unisevtModuleSwitchType 1011 } -- 8-Port 10GBASE Ethernet Optical Interface Module(SFP+,LC)(A Type)
unisevtModuleSw-SPC-XP8LB                   OBJECT IDENTIFIER ::= { unisevtModuleSwitchType 1012 } -- 8-Port Enhanced 10GBASE Ethernet Optical Interface Module(SFP+,LC)(B Type)
unisevtModuleSw-SPC-XP48LA                  OBJECT IDENTIFIER ::= { unisevtModuleSwitchType 1013 } -- 48-Port 10GBASE Ethernet Optical Interface Module(SFP+,LC)(A Type)
unisevtModuleSw-SPC-XLP8LA                  OBJECT IDENTIFIER ::= { unisevtModuleSwitchType 1014 } -- 8-Port 40GBASE Ethernet Optical Interface Module(QSFP+,MPO)(A Type)
unisevtModuleSw-SPC-GP24XP2LB               OBJECT IDENTIFIER ::= { unisevtModuleSwitchType 1015 } -- 16-Port 1000BASE-X Optical Interface(SFP,LC)+8-Port Combo Interface+2-Port 10GE Optical Interface Module(XFP,LC)(B Type)
unisevtModuleSw-LST1MRPNE2                  OBJECT IDENTIFIER ::= { unisevtModuleSwitchType 1016 } -- Management and Route Process Unit
unisevtModuleSw-LST2FW3A1                   OBJECT IDENTIFIER ::= { unisevtModuleSwitchType 1017 } -- Firewall Board
unisevtModuleSw-LST1ADE1A1                  OBJECT IDENTIFIER ::= { unisevtModuleSwitchType 1018 } -- Load Balancing Board
unisevtModuleSw-CR-MRP-II                   OBJECT IDENTIFIER ::= { unisevtModuleSwitchType 1019 } -- Management and Route Unit-II
unisevtModuleSw-CR-SF08E                    OBJECT IDENTIFIER ::= { unisevtModuleSwitchType 1020 } -- Switch Fabric Module(E)
unisevtModuleSw-CR-SF18E                    OBJECT IDENTIFIER ::= { unisevtModuleSwitchType 1021 } -- Switch Fabric Module(E)
unisevtModuleSw-CR-SPC-XP40RC               OBJECT IDENTIFIER ::= { unisevtModuleSwitchType 1022 } -- 40-Port 10GBASE-R/W Optical Interface Module(RC),(SFP+,LC)
unisevtModuleSw-CR-SPC-XP40RB               OBJECT IDENTIFIER ::= { unisevtModuleSwitchType 1023 } -- 40-Port 10GBASE-R Ethernet Optical Interface Module(RB),(SFP+,LC)
unisevtModuleSw-CR-SPC-CP4RC                OBJECT IDENTIFIER ::= { unisevtModuleSwitchType 1024 } -- 4-Port 100GBASE Ethernet Optical Interface Module(RC),(CFP)
unisevtModuleSw-LST1FW3C1                   OBJECT IDENTIFIER ::= { unisevtModuleSwitchType 1025 } -- Firewall Board
unisevtModuleSw-LSU1FWCEA0                  OBJECT IDENTIFIER ::= { unisevtModuleSwitchType 1026 } -- Firewall Board
unisevtModuleSw-SPC-GT48LA1                 OBJECT IDENTIFIER ::= { unisevtModuleSwitchType 1027 } -- 48-Port 10/100/1000BASE-T Ethernet Interface Module(RJ45)(A Type)
unisevtModuleSw-LST1XP20RFD1                OBJECT IDENTIFIER ::= { unisevtModuleSwitchType 1028 } -- 20-Port 10GBASE-R Interface Module (RFD),(SFP+,LC)
unisevtModuleSw-LST1XP20RFD2                OBJECT IDENTIFIER ::= { unisevtModuleSwitchType 1029 } -- 20-Port 10GBASE-R Interface Module (RFD),(SFP+,LC)
unisevtModuleSw-MPE-1104                    OBJECT IDENTIFIER ::= { unisevtModuleSwitchType 1030 } -- 4-Port Multiservice Processing Engine
unisevtModuleSw-SPEX-1204                   OBJECT IDENTIFIER ::= { unisevtModuleSwitchType 1031 } -- 4-Port 10G Processing Engine
unisevtModuleSw-SPC-GP44XP4LCX              OBJECT IDENTIFIER ::= { unisevtModuleSwitchType 1032 } -- 44-Port 100/1000BASE-X Ethernet Optical Interface Module(SFP,LC)+4-Port 10GBASE Ethernet Optical Interface Module(SFP+,LC)(C Type)
unisevtModuleSw-SPC-GP44XP4LAX              OBJECT IDENTIFIER ::= { unisevtModuleSwitchType 1033 } -- 44-Port 100/1000BASE-X Ethernet Optical Interface Module(SFP,LC)+4-Port 10GBASE Ethernet Optical Interface Module(SFP+,LC)(A Type)
unisevtModuleSw-SPC-XP24LCX                 OBJECT IDENTIFIER ::= { unisevtModuleSwitchType 1034 } -- 24-Port 10GBASE Ethernet Optical Interface Module(SFP+,LC)(C Type)
unisevtModuleSw-SPC-XP24LAX                 OBJECT IDENTIFIER ::= { unisevtModuleSwitchType 1035 } -- 24-Port 10GBASE Ethernet Optical Interface Module(SFP+,LC)(A Type)
unisevtModuleSw-SPC-XP12LCX                 OBJECT IDENTIFIER ::= { unisevtModuleSwitchType 1036 } -- 12-Port 10GBASE Ethernet Optical Interface Module(SFP+,LC)(C Type)
unisevtModuleSw-SPC-XP12LAX                 OBJECT IDENTIFIER ::= { unisevtModuleSwitchType 1037 } -- 12-Port 10GBASE Ethernet Optical Interface Module(SFP+,LC)(A Type)
unisevtModuleSw-SPC-XLP6LCX                 OBJECT IDENTIFIER ::= { unisevtModuleSwitchType 1038 } -- 6-Port 40GBASE Ethernet Optical Interface Module(QSFP+,MPO)(C Type)
unisevtModuleSw-SPC-XLP6LAX                 OBJECT IDENTIFIER ::= { unisevtModuleSwitchType 1039 } -- 6-Port 40GBASE Ethernet Optical Interface Module(QSFP+,MPO)(A Type)
unisevtModuleSw-SPC-CP1LCX                  OBJECT IDENTIFIER ::= { unisevtModuleSwitchType 1040 } -- 1-Port 100GBASE Ethernet Optical Interface Module(CFP,LC)(C Type)
unisevtModuleSw-SPC-CP1LAX                  OBJECT IDENTIFIER ::= { unisevtModuleSwitchType 1041 } -- 1-Port 100GBASE Ethernet Optical Interface Module(CFP,LC)(A Type)
unisevtModuleSw-SPC-CP2LB                   OBJECT IDENTIFIER ::= { unisevtModuleSwitchType 1042 } -- 2-Port 100GBASE Ethernet Optical Interface Module(CFP,LC)(B Type)
unisevtModuleSw-SPC-CP2LA                   OBJECT IDENTIFIER ::= { unisevtModuleSwitchType 1043 } -- 2-Port 100GBASE Ethernet Optical Interface Module(CFP,LC)(A Type)
unisevtModuleSw-SR05SRP1L1                  OBJECT IDENTIFIER ::= { unisevtModuleSwitchType 1044 } -- Management and Route Process Unit(1L1)
unisevtModuleSw-SR05SRP1L3                  OBJECT IDENTIFIER ::= { unisevtModuleSwitchType 1045 } -- Management and Route Process Unit(1L3)
unisevtModuleSw-SFC-04-4                    OBJECT IDENTIFIER ::= { unisevtModuleSwitchType 1046 } -- Short-circuit Card Slot 4
unisevtModuleSw-SFC-04-3                    OBJECT IDENTIFIER ::= { unisevtModuleSwitchType 1047 } -- Short-circuit Card Slot 3
unisevtModuleSw-SFC-04-2                    OBJECT IDENTIFIER ::= { unisevtModuleSwitchType 1048 } -- Short-circuit Card Slot 2
unisevtModuleSw-SFC-04-1                    OBJECT IDENTIFIER ::= { unisevtModuleSwitchType 1049 } -- Short-circuit Card Slot 1
unisevtModuleSw-LST1NSM2C1                  OBJECT IDENTIFIER ::= { unisevtModuleSwitchType 1050 } -- NetStream Service Board
unisevtModuleSw-CR-SPC-XP20RB               OBJECT IDENTIFIER ::= { unisevtModuleSwitchType 1051 } -- 20-Port 10GBASE-R Ethernet Optical Interface Module(RB),(SFP+,LC)
unisevtModuleSw-SR07SRPUA1                  OBJECT IDENTIFIER ::= { unisevtModuleSwitchType 1052 } -- Management and Route Process Unit(UA1)
unisevtModuleSw-SR07SRPUB3                  OBJECT IDENTIFIER ::= { unisevtModuleSwitchType 1053 } -- Management and Route Process Unit(UB1)
unisevtModuleSw-SR07SRPUC3                  OBJECT IDENTIFIER ::= { unisevtModuleSwitchType 1054 } -- Management and Route Process Unit
unisevtModuleSw-SR07MPUA1                   OBJECT IDENTIFIER ::= { unisevtModuleSwitchType 1055 } -- Management and Route Process Unit
unisevtModuleSw-SR07SRPUB1                  OBJECT IDENTIFIER ::= { unisevtModuleSwitchType 1056 } -- Management and Route Process Unit(UB1)
unisevtModuleSw-SR07SRPUC1                  OBJECT IDENTIFIER ::= { unisevtModuleSwitchType 1057 } -- Management and Route Process Unit
unisevtModuleSw-MIC-MS4L                    OBJECT IDENTIFIER ::= { unisevtModuleSwitchType 1058 } -- 4-Port Multi-Service Optical Interface Card,Domestic&Overseas Version
unisevtModuleSw-SPC-GP44XP4LC               OBJECT IDENTIFIER ::= { unisevtModuleSwitchType 1059 } -- 44-Port 100/1000BASE-X Ethernet Optical Interface Board(SFP,LC)+4-Port 10GBASE Ethernet Optical Interface Board(SFP+,LC)(C Type)
unisevtModuleSw-SPC-GP44XP4LA               OBJECT IDENTIFIER ::= { unisevtModuleSwitchType 1060 } -- 44-Port 100/1000BASE-X Ethernet Optical Interface Board(SFP,LC)+4-Port 10GBASE Ethernet Optical Interface Board(SFP+,LC)(A Type)
unisevtModuleSw-SPC-XLP2XP4LC               OBJECT IDENTIFIER ::= { unisevtModuleSwitchType 1061 } -- 2-Port 40GBASE Ethernet Optical Interface Board(QSFP+,MPO)+4-Port 10GBASE Ethernet Optical Interface Board(SFP+,LC)(C Type)
unisevtModuleSw-SPC-XP12LC                  OBJECT IDENTIFIER ::= { unisevtModuleSwitchType 1062 } -- 12-Port 10GBASE Ethernet Optical Interface Board(SFP+,LC)(C Type)
unisevtModuleSw-SPC-CP1LC                   OBJECT IDENTIFIER ::= { unisevtModuleSwitchType 1063 } -- 1-Port 100GBASE Ethernet Optical Interface Module(CFP,LC)(C Type)
unisevtModuleSw-SPC-XP24LC                  OBJECT IDENTIFIER ::= { unisevtModuleSwitchType 1064 } -- 24-Port 10GBASE Ethernet Optical Interface Board(SFP+,LC)(C Type)
unisevtModuleSw-SR07SRPUD3                  OBJECT IDENTIFIER ::= { unisevtModuleSwitchType 1065 } -- Management and Route Process Unit(UD1)
unisevtModuleSw-SR07MPUA3                   OBJECT IDENTIFIER ::= { unisevtModuleSwitchType 1066 } -- Management and Route Process Unit(For 02 Chassis)
unisevtModuleSw-MPEX-1304                   OBJECT IDENTIFIER ::= { unisevtModuleSwitchType 1067 } -- 4-Port Multiservice Processing Engine
unisevtModuleSw-MIC-GP10L1                  OBJECT IDENTIFIER ::= { unisevtModuleSwitchType 1068 } -- 6-Port 1000BASE-X Optical Interface Card(SFP,LC)+4-Port 1000BASE-X/10GBASE Optical Interface Card(SFP+,LC)
unisevtModuleSw-SR07SRPUB                   OBJECT IDENTIFIER ::= { unisevtModuleSwitchType 1069 } -- Management and Route Processing Unit(UB3)
unisevtModuleSw-CMPE-1104                   OBJECT IDENTIFIER ::= { unisevtModuleSwitchType 1070 } -- 4-Port Multiservice Processing Engine
unisevtModuleSw-CSFC-04-1                   OBJECT IDENTIFIER ::= { unisevtModuleSwitchType 1071 } -- Fabric Card Slot 1
unisevtModuleSw-CSFC-04-2                   OBJECT IDENTIFIER ::= { unisevtModuleSwitchType 1072 } -- Fabric Card Slot 2
unisevtModuleSw-CSFC-04-3                   OBJECT IDENTIFIER ::= { unisevtModuleSwitchType 1073 } -- Fabric Card Slot 3
unisevtModuleSw-CSFC-04-4                   OBJECT IDENTIFIER ::= { unisevtModuleSwitchType 1074 } -- Fabric Card Slot 4
unisevtModuleSw-CSFC-04B                    OBJECT IDENTIFIER ::= { unisevtModuleSwitchType 1075 } -- Switch Fabric Card(B Type)
unisevtModuleSw-CSFC-04D                    OBJECT IDENTIFIER ::= { unisevtModuleSwitchType 1076 } -- Switch Fabric Card(D Type)
unisevtModuleSw-CSFC-08B                    OBJECT IDENTIFIER ::= { unisevtModuleSwitchType 1077 } -- Switch Fabric Card(B Type)
unisevtModuleSw-CSFC-08D                    OBJECT IDENTIFIER ::= { unisevtModuleSwitchType 1078 } -- Switch Fabric Card(D Type)
unisevtModuleSw-CSFC-12B                    OBJECT IDENTIFIER ::= { unisevtModuleSwitchType 1079 } -- Switch Fabric Card(B Type)
unisevtModuleSw-CSFC-12D                    OBJECT IDENTIFIER ::= { unisevtModuleSwitchType 1080 } -- Switch Fabric Card(D Type)
unisevtModuleSw-CSPC-CP1LCX                 OBJECT IDENTIFIER ::= { unisevtModuleSwitchType 1081 } -- 1-Port 100GBASE Ethernet Optical Interface Module(CFP,LC)(C Type)
unisevtModuleSw-CSPC-CP2LB                  OBJECT IDENTIFIER ::= { unisevtModuleSwitchType 1082 } -- 2-Port 100GBASE Ethernet Optical Interface Module(CFP,LC)(B Type)
unisevtModuleSw-CSPC-GP24LA1                OBJECT IDENTIFIER ::= { unisevtModuleSwitchType 1083 } -- 16-Port 1000BASE-X Ethernet Optical Interface(SFP,LC)+8-Port Combo Interface Module(A Type)
unisevtModuleSw-CSPC-GP24XP2LB              OBJECT IDENTIFIER ::= { unisevtModuleSwitchType 1084 } -- 16-Port 1000BASE-X Optical Interface(SFP,LC)+8-Port Combo Interface+2-Port 10GE Optical Interface Module(XFP,LC)(B Type)
unisevtModuleSw-CSPC-GP44XP4LCX             OBJECT IDENTIFIER ::= { unisevtModuleSwitchType 1085 } -- 44-Port 1000BASE-X Ethernet Optical Interface Module(SFP,LC)+4-Port 10GBASE Ethernet Optical Interface Module(SFP+,LC)(C Type)
unisevtModuleSw-CSPC-GP48LB                 OBJECT IDENTIFIER ::= { unisevtModuleSwitchType 1086 } -- 48-Port Enhanced 1000BASE-X Ethernet Optical Interface Module(SFP,LC)(B Type)
unisevtModuleSw-CSPC-GT48LA1                OBJECT IDENTIFIER ::= { unisevtModuleSwitchType 1087 } -- 48-Port 10/100/1000BASE-T Ethernet Interface Module(RJ45)(A Type)
unisevtModuleSw-CSPC-XLP6LCX                OBJECT IDENTIFIER ::= { unisevtModuleSwitchType 1088 } -- 6-Port 40GBASE Ethernet Optical Interface Module(QSFP+,MPO)(C Type)
unisevtModuleSw-CSPC-XP2LA1                 OBJECT IDENTIFIER ::= { unisevtModuleSwitchType 1089 } -- 2-Port 10GBASE Ethernet Optical Interface Module(XFP,LC)(A Type)
unisevtModuleSw-CSPC-XP4LB                  OBJECT IDENTIFIER ::= { unisevtModuleSwitchType 1090 } -- 4-Port Enhanced 10GBASE Ethernet Optical Interface Module(XFP,LC)(B Type)
unisevtModuleSw-CSPC-XP8LB                  OBJECT IDENTIFIER ::= { unisevtModuleSwitchType 1091 } -- 8-Port Enhanced 10GBASE Ethernet Optical Interface Module(SFP+,LC)(B Type)
unisevtModuleSw-CSPC-XP12LAX                OBJECT IDENTIFIER ::= { unisevtModuleSwitchType 1092 } -- 12-Port 10GBASE Ethernet Optical Interface Module(SFP+,LC)(A Type)
unisevtModuleSw-CSPC-XP12LCX                OBJECT IDENTIFIER ::= { unisevtModuleSwitchType 1093 } -- 12-Port 10GBASE Ethernet Optical Interface Module(SFP+,LC)(C Type)
unisevtModuleSw-CSPC-XP24LAX                OBJECT IDENTIFIER ::= { unisevtModuleSwitchType 1094 } -- 24-Port 10GBASE Ethernet Optical Interface Module(SFP+,LC)(A Type)
unisevtModuleSw-CSPC-XP24LCX                OBJECT IDENTIFIER ::= { unisevtModuleSwitchType 1095 } -- 24-Port 10GBASE Ethernet Optical Interface Module(SFP+,LC)(C Type)
unisevtModuleSw-CSPC-CSPEX-1204             OBJECT IDENTIFIER ::= { unisevtModuleSwitchType 1096 } -- 4-Port 10G Processing Engine
unisevtModuleSw-CSR05SRP1L1                 OBJECT IDENTIFIER ::= { unisevtModuleSwitchType 1097 } -- Management and Route Process Unit(1L1)
unisevtModuleSw-CSR05SRP1L3                 OBJECT IDENTIFIER ::= { unisevtModuleSwitchType 1098 } -- Management and Route Process Unit(1L3)
unisevtModuleSw-CSR07MPUA1                  OBJECT IDENTIFIER ::= { unisevtModuleSwitchType 1099 } -- Management and Route Processing Unit
unisevtModuleSw-CSR07SRPUA1                 OBJECT IDENTIFIER ::= { unisevtModuleSwitchType 1100 } -- Management and Route Processing Unit(UA1)
unisevtModuleSw-CSR07SRPUB1                 OBJECT IDENTIFIER ::= { unisevtModuleSwitchType 1101 } -- Management and Route Processing Unit(UB1)
unisevtModuleSw-CSR07SRPUC1                 OBJECT IDENTIFIER ::= { unisevtModuleSwitchType 1102 } -- Management and Route Processing Unit
unisevtModuleSw-LSXM1CGX8FX1                OBJECT IDENTIFIER ::= { unisevtModuleSwitchType 1103 } -- 8-Port 100GBASE Ethernet Optical Interface Module(CXP)(FX)
unisevtModuleSw-LSXM1QGS24FX1               OBJECT IDENTIFIER ::= { unisevtModuleSwitchType 1104 } -- 24-Port 40GBASE Ethernet Optical Interface Module(QSFP+)(FX)
unisevtModuleSw-LSXM1TGS48FX1               OBJECT IDENTIFIER ::= { unisevtModuleSwitchType 1105 } -- 48-Port 10GBASE Ethernet Optical Interface Module(SFP+,LC)(FX)
unisevtModuleSw-LSXM1QGS12FX1               OBJECT IDENTIFIER ::= { unisevtModuleSwitchType 1106 } -- 12-Port 40GBASE Ethernet Optical Interface Module(QSFP+)(FX)
unisevtModuleSw-LSXM1TGT48FX1               OBJECT IDENTIFIER ::= { unisevtModuleSwitchType 1107 } -- 48-Port 10GBASE-T Ethernet Electrical Interface Module(RJ45)(FX)
unisevtModuleSw-LSU1IPSBEA0                 OBJECT IDENTIFIER ::= { unisevtModuleSwitchType 1108 } -- Intrusion Prevention System Module
unisevtModuleSw-PIC-GP10L                   OBJECT IDENTIFIER ::= { unisevtModuleSwitchType 1109 } -- 10-Port 1000BASE-X Optical Interface Card,(SFP,LC)
unisevtModuleSw-PIC-XP1L                    OBJECT IDENTIFIER ::= { unisevtModuleSwitchType 1110 } -- 1-Port 10GBASE-R/W Ethernet Optical Interface Card,(XFP,LC)
unisevtModuleSw-PIC-PUP1L                   OBJECT IDENTIFIER ::= { unisevtModuleSwitchType 1111 } -- 1-Port 10G POS Optical Interface Card,(XFP,LC)
unisevtModuleSw-PIC-PSP4L                   OBJECT IDENTIFIER ::= { unisevtModuleSwitchType 1112 } -- 4-Port 2.5G POS Optical Interface Card(SFP,LC)
unisevtModuleSw-PIC-PS2G4L                  OBJECT IDENTIFIER ::= { unisevtModuleSwitchType 1113 } -- 2-Port 2.5G POS Optical Interface(SFP,LC)+4-Port 1000BASE-X Optical Interface Card(SFP,LC)
unisevtModuleSw-PIC-PL2G6L                  OBJECT IDENTIFIER ::= { unisevtModuleSwitchType 1114 } -- 2-Port 155M POS Optical Interface(SFP,LC)+6-Port 1000BASE-X Optical Interface Card(SFP,LC)
unisevtModuleSw-PIC-TCP8L                   OBJECT IDENTIFIER ::= { unisevtModuleSwitchType 1115 } -- 8-Port OC-3c/OC-12c POS/GE Optical Interface Card,(SFP,LC)
unisevtModuleSw-PIC-CSP1L                   OBJECT IDENTIFIER ::= { unisevtModuleSwitchType 1116 } -- 1-Port 2.5G CPOS Optical Interface Card(SFP,LC)
unisevtModuleSw-PIC-PH2G6L                  OBJECT IDENTIFIER ::= { unisevtModuleSwitchType 1117 } -- 2-Port 622M POS Optical Interface(SFP,LC)+6-Port 1000BASE-X Optical Interface Card(SFP,LC)
unisevtModuleSw-LSXM1CGP12FX1               OBJECT IDENTIFIER ::= { unisevtModuleSwitchType 1118 } -- 12-Port 100GBASE Ethernet Optical Interface Module(CFP2)(FX)
unisevtModuleSw-LSXM1CGP8FX1                OBJECT IDENTIFIER ::= { unisevtModuleSwitchType 1119 } -- 8-Port 100GBASE Ethernet Optical Interface Module(CFP2)(FX)
unisevtModuleSw-LSXM1GT48FX1                OBJECT IDENTIFIER ::= { unisevtModuleSwitchType 1120 } -- 48-Port 1000Base-T Gigabit Ethernet Interface Board(RJ45)
unisevtModuleSw-LSXM1GT48FX0                OBJECT IDENTIFIER ::= { unisevtModuleSwitchType 1121 } -- 48-Port 1000Base-T Gigabit Ethernet Interface Board(RJ45)
unisevtModuleSw-LSXM1GP48FX1                OBJECT IDENTIFIER ::= { unisevtModuleSwitchType 1122 } -- 48-Port 1000BASE Ethernet SFP Optical Interface Board
unisevtModuleSw-LSXM1GP48FX0                OBJECT IDENTIFIER ::= { unisevtModuleSwitchType 1123 } -- 48-Port 1000BASE Ethernet SFP Optical Interface Board
unisevtModuleSw-LSXM1TGS24FX0               OBJECT IDENTIFIER ::= { unisevtModuleSwitchType 1124 } -- 24-Port 10GBASE Ethernet SFP+ Optical Interface Board
unisevtModuleSw-LSXM1TGS24FX1               OBJECT IDENTIFIER ::= { unisevtModuleSwitchType 1125 } -- 24-Port 10GBASE Ethernet SFP+ Optical Interface Board
unisevtModuleSw-MIC-SP8L                    OBJECT IDENTIFIER ::= { unisevtModuleSwitchType 1126 } -- 8-Port OC-3c/STM-1c POS Optical Interface Card
unisevtModuleSw-LSXM1TGS48FE1               OBJECT IDENTIFIER ::= { unisevtModuleSwitchType 1127 } -- 48-Port 10GBASE Ethernet SFP+ Optical Interface Board(FE)
unisevtModuleSw-LSXM1QGS24FE1               OBJECT IDENTIFIER ::= { unisevtModuleSwitchType 1128 } -- 24-Port 40GBASE Ethernet Optical Interface Board(QSFP+)
unisevtModuleSw-CSPEX-1504S                 OBJECT IDENTIFIER ::= { unisevtModuleSwitchType 1129 } -- Multi-Service Processing Board
unisevtModuleSw-CSPEX-1504X                 OBJECT IDENTIFIER ::= { unisevtModuleSwitchType 1130 } -- Multi-Service Processing Board
unisevtModuleSw-CSPEX-1404S                 OBJECT IDENTIFIER ::= { unisevtModuleSwitchType 1131 } -- Multi-Service Processing Board
unisevtModuleSw-CSPEX-1304S                 OBJECT IDENTIFIER ::= { unisevtModuleSwitchType 1132 } -- Multi-Service Processing Board
unisevtModuleSw-CSPEX-1404X                 OBJECT IDENTIFIER ::= { unisevtModuleSwitchType 1133 } -- Multi-Service Processing Board
unisevtModuleSw-CSPEX-1304X                 OBJECT IDENTIFIER ::= { unisevtModuleSwitchType 1134 } -- Multi-Service Processing Board
unisevtModuleSw-MIC-XP5L                    OBJECT IDENTIFIER ::= { unisevtModuleSwitchType 1135 } -- 5-Port 10GBASE-R/W Ethernet Optical Interface Card,(SFP+,LC)
unisevtModuleSw-MIC-XP2L                    OBJECT IDENTIFIER ::= { unisevtModuleSwitchType 1136 } -- 2-Port 10GBASE-R/W Ethernet Optical Interface Card,(SFP+,LC)
unisevtModuleSw-MIC-CP1L                    OBJECT IDENTIFIER ::= { unisevtModuleSwitchType 1137 } -- 1-Port 100G Optical Interface Card,(CFP,LC)
unisevtModuleSw-MIC-GP20L                   OBJECT IDENTIFIER ::= { unisevtModuleSwitchType 1138 } -- 20-Port 1000BASE-X Ethernet Optical Interface Card,(SFP,LC),Monolithic
unisevtModuleSw-MIC-GT20L                   OBJECT IDENTIFIER ::= { unisevtModuleSwitchType 1139 } -- 20-Port 1000BASE-X Ethernet Electrical Interface Card,(RJ45,LC),Monolithic
unisevtModuleSw-CEPC-XP48RX                 OBJECT IDENTIFIER ::= { unisevtModuleSwitchType 1140 } -- 48-Port 10GBASE-R/W Interface Module,(SFP+,LC)
unisevtModuleSw-CEPC-CP4RX                  OBJECT IDENTIFIER ::= { unisevtModuleSwitchType 1141 } -- 4-Port 100GBASE Ethernet Optical Interface Board(CFP2)
unisevtModuleSw-MIC-GP10L-V2                OBJECT IDENTIFIER ::= { unisevtModuleSwitchType 1142 } -- 10-Port 1000BASE-X Optical Interface Card,(SFP,LC)
unisevtModuleSw-CSR07SRPUD3                 OBJECT IDENTIFIER ::= { unisevtModuleSwitchType 1143 } -- Management and Route Process Board(UD3)
unisevtModuleSw-MIC-XP1L                    OBJECT IDENTIFIER ::= { unisevtModuleSwitchType 1144 } -- 1-Port 10GBASE-R/W Ethernet Optical Interface Card,(SFP+,LC)
unisevtModuleSw-CSFC-12E                    OBJECT IDENTIFIER ::= { unisevtModuleSwitchType 1145 } -- Switch Fabric Board
unisevtModuleSw-CEPC-XP24LX                 OBJECT IDENTIFIER ::= { unisevtModuleSwitchType 1146 } -- 24-Port 10GBASE-R/W Interface Module,(SFP+,LC)
unisevtModuleSw-IM-MSUX                     OBJECT IDENTIFIER ::= { unisevtModuleSwitchType 1147 } -- Multi-Service Processing Board,Monolithic
unisevtModuleSw-CSFC-12F                    OBJECT IDENTIFIER ::= { unisevtModuleSwitchType 1148 } -- Switch Fabric Board, Monolithic
unisevtModuleSw-CSR05SRP1N3                 OBJECT IDENTIFIER ::= { unisevtModuleSwitchType 1149 } -- Main Processing Unit(1N3)
unisevtModuleSw-CSPEX-1602X                 OBJECT IDENTIFIER ::= { unisevtModuleSwitchType 1150 } -- Service Processing Unit(1602X)
unisevtModuleSw-MIC-XP20L                   OBJECT IDENTIFIER ::= { unisevtModuleSwitchType 1151 } -- 20-port 10GBASE-R/W Ethernet Optical Interface Card(SFP+,LC)
unisevtModuleSw-MIC-CP2L                    OBJECT IDENTIFIER ::= { unisevtModuleSwitchType 1152 } -- 2-port 100G Ethernet Optical Interface Card(CFP2,LC)
unisevtModuleSw-IM-NGFWX-IV                 OBJECT IDENTIFIER ::= { unisevtModuleSwitchType 1153 } -- Next Generation Firewall Module
unisevtModuleSw-SFC-12E                     OBJECT IDENTIFIER ::= { unisevtModuleSwitchType 1154 } -- Switch Fabric Board

unisevtModuleSw-SPEX-1602X-E                OBJECT IDENTIFIER ::= { unisevtModuleSwitchType 1155 } -- Service Processing Unit(1602X)-E
unisevtModuleSw-SPEX-1602X-L                OBJECT IDENTIFIER ::= { unisevtModuleSwitchType 1156 } -- Service Processing Unit(1602X)-L
unisevtModuleSw-EPC-XP24LX-E                OBJECT IDENTIFIER ::= { unisevtModuleSwitchType 1157 } -- 24-Port 10GBASE-R/W Ethernet Optical Interface Line Processing Unit (SFP+,LC)-E
unisevtModuleSw-EPC-XP24LX-L                OBJECT IDENTIFIER ::= { unisevtModuleSwitchType 1158 } -- 24-Port 10GBASE-R/W Ethernet Optical Interface Line Processing Unit (SFP+,LC)-L
unisevtModuleSw-EPC-CP4RX-L                 OBJECT IDENTIFIER ::= { unisevtModuleSwitchType 1159 } -- 4-Port 100GBASE Ethernet Optical Interface Line Processing Unit (CFP2)-L
unisevtModuleSw-SPEX-1504X-E                OBJECT IDENTIFIER ::= { unisevtModuleSwitchType 1160 } -- Service Processing Unit(1504X)-E
unisevtModuleSw-SPEX-1504X-L                OBJECT IDENTIFIER ::= { unisevtModuleSwitchType 1161 } -- Service Processing Unit(1504X)-L
unisevtModuleSw-CSPEX-1602X-L               OBJECT IDENTIFIER ::= { unisevtModuleSwitchType 1162 } -- Service Processing Unit(1602X)-L
unisevtModuleSw-CEPC-XP24LX-L               OBJECT IDENTIFIER ::= { unisevtModuleSwitchType 1163 } -- 24-Port 10GBASE-R/W Ethernet Optical Interface Line Processing Unit (SFP+,LC)-L
unisevtModuleSw-CEPC-CP4RX-L                OBJECT IDENTIFIER ::= { unisevtModuleSwitchType 1164 } -- 4-port 100G Ethernet Optical Interface Line Processing Unit(QSFP28)
unisevtModuleSw-MIC-CP1L-E                  OBJECT IDENTIFIER ::= { unisevtModuleSwitchType 1165 } -- 1-port 100G Ethernet Optical Interface Card(CFP,LC)-E
unisevtModuleSw-MIC-XP4L-E                  OBJECT IDENTIFIER ::= { unisevtModuleSwitchType 1166 } -- 4-Port 10GBASE-R/W Ethernet Optical Interface Card,(SFP+,LC)-E
unisevtModuleSw-MIC-XP16L-E                 OBJECT IDENTIFIER ::= { unisevtModuleSwitchType 1167 } -- 16-port 10GBASE-R/W Ethernet Optical Interface Card(SFP+,LC)-E
unisevtModuleSw-MIC-GP20L-E                 OBJECT IDENTIFIER ::= { unisevtModuleSwitchType 1168 } -- 20-Port 1000BASE-X Ethernet Optical Interface Card,(SFP,LC)-E
unisevtModuleSw-MIC-GP10L-V2-E              OBJECT IDENTIFIER ::= { unisevtModuleSwitchType 1169 } -- 10-Port 1000BASE-X Ethernet Optical Interface Card(SFP,LC)-E
unisevtModuleSw-MIC-GT20L-E                 OBJECT IDENTIFIER ::= { unisevtModuleSwitchType 1170 } -- 20-Port 1000BASE-X Ethernet Electrical Interface Card,(RJ45,LC)-E
unisevtModuleSw-CSR05SRP1P3                 OBJECT IDENTIFIER ::= { unisevtModuleSwitchType 1171 } -- CR16018-F Main Processing Unit(1P3)
unisevtModuleSw-SR05SRP1P3                  OBJECT IDENTIFIER ::= { unisevtModuleSwitchType 1172 } -- SR8816-X Main Processing Unit(1P3)
unisevtModuleSw-CSFC-16E                    OBJECT IDENTIFIER ::= { unisevtModuleSwitchType 1173 } -- CR16018-F Fabric Module(E Type)
unisevtModuleSw-SFC-16E                     OBJECT IDENTIFIER ::= { unisevtModuleSwitchType 1174 } -- SR8816-X Fabric Module(E Type)
unisevtModuleSw-CSFC-08E                    OBJECT IDENTIFIER ::= { unisevtModuleSwitchType 1175 } -- CR16010-F Fabric Module(E Type)
unisevtModuleSw-SFC-08E                     OBJECT IDENTIFIER ::= { unisevtModuleSwitchType 1176 } -- SR8808-X Fabric Module(E Type)
unisevtModuleSw-IM-SMUX                     OBJECT IDENTIFIER ::= { unisevtModuleSwitchType 1177 } -- Security Monitor Unit (IM-SMUX)
unisevtModuleSw-IM-IPSX-IV                  OBJECT IDENTIFIER ::= { unisevtModuleSwitchType 1178 } -- Intrusion Prevention System Module
unisevtModuleSw-IM-ACGX-IV                  OBJECT IDENTIFIER ::= { unisevtModuleSwitchType 1179 } -- Application Control Gateway Module
unisevtModuleSw-SFC-08E1                    OBJECT IDENTIFIER ::= { unisevtModuleSwitchType 1180 } -- SR8808H-X Fabric Module(E Type)
unisevtModuleSw-CSFC-08E1                   OBJECT IDENTIFIER ::= { unisevtModuleSwitchType 1181 } -- CR16010H-F Fabric Module(E Type)
unisevtModuleSw-IM-ACG1000X-IV              OBJECT IDENTIFIER ::= { unisevtModuleSwitchType 1182 } -- SecPath ACG1000-Blade-X Application Control Module(SR88-X SecBladeIV)
unisevtModuleSw-MIC-QP1L                    OBJECT IDENTIFIER ::= { unisevtModuleSwitchType 1183 } -- 1-port 40G Ethernet Optical Interface Card(QSFP+,LC)
unisevtModuleSw-CSPEX-1804X                 OBJECT IDENTIFIER ::= { unisevtModuleSwitchType 1184 } -- Service Processing Unit(1804X)
unisevtModuleSw-MIC-CP2L-V2                 OBJECT IDENTIFIER ::= { unisevtModuleSwitchType 1185 } -- 2-port 100G Ethernet Optical Interface Card(QSFP28)
unisevtModuleSw-MIC-XP4L1                   OBJECT IDENTIFIER ::= { unisevtModuleSwitchType 1186 } -- 4-port 10GBASE-R/W Ethernet Optical Interface Card 1(SFP+,LC)
unisevtModuleSw-SFC-16T                     OBJECT IDENTIFIER ::= { unisevtModuleSwitchType 1187 } -- SR8816-X Fabric Module(T Type)
unisevtModuleSw-CSFC-16T                    OBJECT IDENTIFIER ::= { unisevtModuleSwitchType 1188 } -- CR16018-F Fabric Module(T Type)
unisevtModuleSw-SFC-08T                     OBJECT IDENTIFIER ::= { unisevtModuleSwitchType 1189 } -- SR8808H-X Fabric Module(T Type)
unisevtModuleSw-CSFC-08T                    OBJECT IDENTIFIER ::= { unisevtModuleSwitchType 1190 } -- CR16010H-F Fabric Module(T Type)
unisevtModuleSw-MIC-XP2L-LAN                OBJECT IDENTIFIER ::= { unisevtModuleSwitchType 1191 } -- 2-port 10GBASE-R Ethernet Optical Interface Card(SFP+,LC)-LAN
unisevtModuleSw-MIC-XP5L1                   OBJECT IDENTIFIER ::= { unisevtModuleSwitchType 1192 } -- 5-port 10GBASE-R/W Ethernet Optical Interface Card(SFP+,LC)
unisevtModuleSw-MIC-CP1L-V2                 OBJECT IDENTIFIER ::= { unisevtModuleSwitchType 1193 } -- 1-port 100G Ethernet Optical Interface Card(CFP2,LC)
unisevtModuleSw-CEPC-XP40LX                 OBJECT IDENTIFIER ::= { unisevtModuleSwitchType 1194 } -- 40-port 10GBASE-R/W Ethernet Optical Interface Line Processing Unit Module(SFP+,LC)
unisevtModuleSw-CEPC-CQ4LX                  OBJECT IDENTIFIER ::= { unisevtModuleSwitchType 1195 } -- 4-port 100G Ethernet Optical Interface Line Processing Unit Module(QSFP28,LC)


--
-- 1200 to 1399 reserved for secondary switches part II
--
unisevtModuleSw-LSU1QGC4SF0                 OBJECT IDENTIFIER ::= { unisevtModuleSwitchType 1201 } -- 4 Port 40G BASE Ethernet Optical Interface Board(CFP,SC)(SF)
unisevtModuleSw-LSU1QGS8SF0                 OBJECT IDENTIFIER ::= { unisevtModuleSwitchType 1202 } -- 8-Port 40G BASE Ethernet Optical Interface Board(QSFP,MPO)(SF)
unisevtModuleSw-LSU1TGS48SF0                OBJECT IDENTIFIER ::= { unisevtModuleSwitchType 1203 } -- 48-Port 10GBASE Ethernet SFP+ Optical Interface Board
unisevtModuleSw-LSU1QGS4SF0                 OBJECT IDENTIFIER ::= { unisevtModuleSwitchType 1204 } -- 4-Port 40G BASE Ethernet Optical Interface Board(QSFP,MPO)(SF)
unisevtModuleSw-LSU1TGS32SF0                OBJECT IDENTIFIER ::= { unisevtModuleSwitchType 1205 } -- 32-Port 10GBASE Ethernet SFP+ Optical Interface Board
unisevtModuleSw-LSU1FAB08D0                 OBJECT IDENTIFIER ::= { unisevtModuleSwitchType 1206 } -- Switching Fabric Module
unisevtModuleSw-LSU1FAB04B0                 OBJECT IDENTIFIER ::= { unisevtModuleSwitchType 1207 } -- Switching Fabric Module
unisevtModuleSw-LSU1FAB08B0                 OBJECT IDENTIFIER ::= { unisevtModuleSwitchType 1208 } -- Switching Fabric Module
unisevtModuleSw-LSU1FAB12D0                 OBJECT IDENTIFIER ::= { unisevtModuleSwitchType 1209 } -- Switching Fabric Module
unisevtModuleSw-LSU1FAB12B0                 OBJECT IDENTIFIER ::= { unisevtModuleSwitchType 1210 } -- Switching Fabric Module
unisevtModuleSw-LSU1FAB04D0                 OBJECT IDENTIFIER ::= { unisevtModuleSwitchType 1211 } -- Switching Fabric Module
unisevtModuleSw-LSQ1CTGS16SC0               OBJECT IDENTIFIER ::= { unisevtModuleSwitchType 1212 } -- Supervisor Engine Board With 16-Port 10GBASE Ethernet SFP+ Optical Interfaces
unisevtModuleSw-EWPX2CTGS16SC0              OBJECT IDENTIFIER ::= { unisevtModuleSwitchType 1213 } -- Supervisor Engine Board With 16-Port 10GBASE Ethernet SFP+ Optical Interfaces
unisevtModuleSw-LSU3WCMD0                   OBJECT IDENTIFIER ::= { unisevtModuleSwitchType 1214 } -- Access Controller Card
unisevtModuleSw-EWPX3WCMD0                  OBJECT IDENTIFIER ::= { unisevtModuleSwitchType 1215 } -- Access Controller Card
unisevtModuleSw-LSQ1QGS4SC0                 OBJECT IDENTIFIER ::= { unisevtModuleSwitchType 1216 } -- 4-Port 40G BASE Ethernet Optical Interface Board(QSFP+,MPO)(SC)
unisevtModuleSw-LSQ1QGC4SC0                 OBJECT IDENTIFIER ::= { unisevtModuleSwitchType 1217 } -- 4 Port 40GBASE Ethernet Optical Interface Board(CFP)(SC)
unisevtModuleSw-LSU1TGT24SF0                OBJECT IDENTIFIER ::= { unisevtModuleSwitchType 1218 } -- 24-Port 10GBASE-T Ethernet Electrical Interface Board(RJ45)(SF)
unisevtModuleSw-LSQ1QGS8SC3                 OBJECT IDENTIFIER ::= { unisevtModuleSwitchType 1219 } -- 8-Port 40G BASE Ethernet Optical Interface Board(QSFP+,MPO)
unisevtModuleSw-LSQ1TGS32SC3                OBJECT IDENTIFIER ::= { unisevtModuleSwitchType 1220 } -- 32-Port 10GBASE Ethernet SFP+ Optical Interface Board
unisevtModuleSw-LSQ1QGS4SC3                 OBJECT IDENTIFIER ::= { unisevtModuleSwitchType 1221 } -- 4-Port 40GBASE Ethernet Optical Interface Board(QSFP+,MPO)(SC)
unisevtModuleSw-LSQ1TGS48SC3                OBJECT IDENTIFIER ::= { unisevtModuleSwitchType 1222 } -- 48-Port 10GBASE Ethernet SFP+ Optical Interface Board
unisevtModuleSw-LSQ1QGC4SC3                 OBJECT IDENTIFIER ::= { unisevtModuleSwitchType 1223 } -- 4-Port 40GBASE Ethernet Optical Interface Board(CFP)(SC)
unisevtModuleSw-LSQ1FAB12D3                 OBJECT IDENTIFIER ::= { unisevtModuleSwitchType 1224 } -- Switch Fabric Board
unisevtModuleSw-LSQ1FAB08D3                 OBJECT IDENTIFIER ::= { unisevtModuleSwitchType 1225 } -- Switching Fabric Module
unisevtModuleSw-LSQ1FAB04D3                 OBJECT IDENTIFIER ::= { unisevtModuleSwitchType 1226 } -- Switching Fabric Module
unisevtModuleSw-LSQ1TGS8EB3                 OBJECT IDENTIFIER ::= { unisevtModuleSwitchType 1227 } -- 8-Port 10GBASE Ethernet SFP+ Optical Interface Board
unisevtModuleSw-LSQ1TGT24SC3                OBJECT IDENTIFIER ::= { unisevtModuleSwitchType 1228 } -- 24-Port 10GBASE-T Ethernet Electrical Interface Board(RJ45)(SC)
unisevtModuleSw-LSQ1FAB08B0                 OBJECT IDENTIFIER ::= { unisevtModuleSwitchType 1229 } -- Switching Fabric Module
unisevtModuleSw-EWPX2CTGS16SC               OBJECT IDENTIFIER ::= { unisevtModuleSwitchType 1230 } -- Supervisor Engine Board With 16-Port 10GBASE Ethernet SFP+ Optical Interfaces
unisevtModuleSw-LSU1SUPB0                   OBJECT IDENTIFIER ::= { unisevtModuleSwitchType 1231 } -- Supervisor Engine Board
unisevtModuleSw-LSQ1GP48SA0                 OBJECT IDENTIFIER ::= { unisevtModuleSwitchType 1232 } -- 48-Port 1000BASE-X Ethernet Optical Interface Board(SFP,LC)
unisevtModuleSw-LSQ1TGX2SA0                 OBJECT IDENTIFIER ::= { unisevtModuleSwitchType 1233 } -- 2-Port 10GBASE Ethernet Optical Interface Board(XFP,LC)
unisevtModuleSw-LSV1SRPUA1                  OBJECT IDENTIFIER ::= { unisevtModuleSwitchType 1234 } -- Supervisor Engine Board
unisevtModuleSw-LSV1QGS12SA1                OBJECT IDENTIFIER ::= { unisevtModuleSwitchType 1235 } -- 12-Port 40G BASE Ethernet Optical Interface Board(QSFP+)
unisevtModuleSw-LSV1MPUA1                   OBJECT IDENTIFIER ::= { unisevtModuleSwitchType 1236 } -- Supervisor Engine Board
unisevtModuleSw-LSX1SUP10A0                 OBJECT IDENTIFIER ::= { unisevtModuleSwitchType 1237 } -- Supervisor Engine Board
unisevtModuleSw-LSX1SUP16A0                 OBJECT IDENTIFIER ::= { unisevtModuleSwitchType 1238 } -- Supervisor Engine Board
unisevtModuleSw-LSX1SUP10A1                 OBJECT IDENTIFIER ::= { unisevtModuleSwitchType 1239 } -- Supervisor Engine Board
unisevtModuleSw-LSX1SUP16A1                 OBJECT IDENTIFIER ::= { unisevtModuleSwitchType 1240 } -- Supervisor Engine Board
unisevtModuleSw-LSX1FAB10B0                 OBJECT IDENTIFIER ::= { unisevtModuleSwitchType 1241 } -- Switch Fabric Board
unisevtModuleSw-LSX1FAB16B0                 OBJECT IDENTIFIER ::= { unisevtModuleSwitchType 1242 } -- Switch Fabric Board
unisevtModuleSw-LSX1FAB10B1                 OBJECT IDENTIFIER ::= { unisevtModuleSwitchType 1243 } -- Switch Fabric Board
unisevtModuleSw-LSX1FAB16B1                 OBJECT IDENTIFIER ::= { unisevtModuleSwitchType 1244 } -- Switch Fabric Board
unisevtModuleSw-LSX1QGS16EA0                OBJECT IDENTIFIER ::= { unisevtModuleSwitchType 1245 } -- Switch Fabric Board16-Port 40G BASE Ethernet Optical Interface Board(QSFP+,MPO)
unisevtModuleSw-LSX1TGS48EA0                OBJECT IDENTIFIER ::= { unisevtModuleSwitchType 1246 } -- 48-Port 10GBASE Ethernet SFP+ Optical Interface Board
unisevtModuleSw-LSX1QGS16EA1                OBJECT IDENTIFIER ::= { unisevtModuleSwitchType 1247 } -- Switch Fabric Board16-Port 40G BASE Ethernet Optical Interface Board(QSFP+,MPO)
unisevtModuleSw-LSX1TGS48EA1                OBJECT IDENTIFIER ::= { unisevtModuleSwitchType 1248 } -- 48-Port 10GBASE Ethernet SFP+ Optical Interface Board
unisevtModuleSw-LSU1TGT24SF9                OBJECT IDENTIFIER ::= { unisevtModuleSwitchType 1249 } -- 24-Port 10GBASE-T Ethernet Electrical Interface Board(RJ45)(SF)
unisevtModuleSw-LSU1QGS8SF9                 OBJECT IDENTIFIER ::= { unisevtModuleSwitchType 1250 } -- 8-Port 40G BASE Ethernet Optical Interface Board(QSFP+,MPO)(SF)
unisevtModuleSw-LSU1QGS4SF9                 OBJECT IDENTIFIER ::= { unisevtModuleSwitchType 1251 } -- 4-Port 40GBASE Ethernet QSFP+ Optical Interface Board(QSFP+,MPO)(SF)
unisevtModuleSw-LSU1TGS48SF9                OBJECT IDENTIFIER ::= { unisevtModuleSwitchType 1252 } -- 48-Port 10GBASE Ethernet SFP+ Optical Interface Board
unisevtModuleSw-LSU1TGS32SF9                OBJECT IDENTIFIER ::= { unisevtModuleSwitchType 1253 } -- 32-Port 10GBASE Ethernet SFP+ Optical Interface Board
unisevtModuleSw-LSU1FAB08D9                 OBJECT IDENTIFIER ::= { unisevtModuleSwitchType 1254 } -- Switching Fabric Module
unisevtModuleSw-LSU1SUPB9                   OBJECT IDENTIFIER ::= { unisevtModuleSwitchType 1255 } -- Supervisor Engine Board
unisevtModuleSw-LSQ3GV48SC0                 OBJECT IDENTIFIER ::= { unisevtModuleSwitchType 1256 } -- 48-Port 1000Base-T Gigabit Ethernet Interface Board(RJ45), PoE Plus
unisevtModuleSw-LSX1QGS12EC1                OBJECT IDENTIFIER ::= { unisevtModuleSwitchType 1257 } -- 12-Port 40GBASE Ethernet Optical Interface Board(QSFP+)
unisevtModuleSw-LSX1QGS12EC0                OBJECT IDENTIFIER ::= { unisevtModuleSwitchType 1258 } -- 12-Port 40GBASE Ethernet Optical Interface Board(QSFP+)
unisevtModuleSw-LSX1TGS48EC0                OBJECT IDENTIFIER ::= { unisevtModuleSwitchType 1259 } -- 48-Port 10GBASE Ethernet SFP+ Optical Interface Board
unisevtModuleSw-LSX1TGS48EC1                OBJECT IDENTIFIER ::= { unisevtModuleSwitchType 1260 } -- 48-Port 10GBASE Ethernet SFP+ Optical Interface Board
unisevtModuleSw-LSX1TGS24EC0                OBJECT IDENTIFIER ::= { unisevtModuleSwitchType 1261 } -- 24-Port 10GBASE Ethernet SFP+ Optical Interface Board(EC)
unisevtModuleSw-LSX1TGS24EC1                OBJECT IDENTIFIER ::= { unisevtModuleSwitchType 1262 } -- 24-Port 10GBASE Ethernet SFP+ Optical Interface Board(EC)
unisevtModuleSw-LSX1FAB10A0                 OBJECT IDENTIFIER ::= { unisevtModuleSwitchType 1263 } -- Switch Fabric Board,For 10 Slots Chassis
unisevtModuleSw-LSX1FAB16A1                 OBJECT IDENTIFIER ::= { unisevtModuleSwitchType 1264 } -- Switch Fabric Board,For 16 Slots Chassis
unisevtModuleSw-LSX1QGS12FB0                OBJECT IDENTIFIER ::= { unisevtModuleSwitchType 1265 } -- 12-Port 40GBASE Ethernet Optical Interface Board(QSFP+)
unisevtModuleSw-LSX1TGS24FB0                OBJECT IDENTIFIER ::= { unisevtModuleSwitchType 1266 } -- 24-Port 10GBASE Ethernet SFP+ Optical Interface Board(FB)
unisevtModuleSw-LSX1TGS48FB0                OBJECT IDENTIFIER ::= { unisevtModuleSwitchType 1267 } -- 48-Port 10GBASE Ethernet SFP+ Optical Interface Board(FB)
unisevtModuleSw-LSX1QGS12EB1                OBJECT IDENTIFIER ::= { unisevtModuleSwitchType 1268 } -- 12-Port 40GBASE Ethernet Optical Interface Board(QSFP+)
unisevtModuleSw-LSX1TGS24EB1                OBJECT IDENTIFIER ::= { unisevtModuleSwitchType 1269 } -- 24-Port 10GBASE Ethernet SFP+ Optical Interface Board(EB)
unisevtModuleSw-LSX1FAB10A1                 OBJECT IDENTIFIER ::= { unisevtModuleSwitchType 1270 } -- Switch Fabric Board,For 10 Slots Chassis
unisevtModuleSw-LSX1TGS48EB1                OBJECT IDENTIFIER ::= { unisevtModuleSwitchType 1271 } -- 48-Port 10GBASE Ethernet SFP+ Optical Interface Board(EB)
unisevtModuleSw-LSX1GP48EB1                 OBJECT IDENTIFIER ::= { unisevtModuleSwitchType 1272 } -- 44-Port GE Optical Interface(SFP,LC)+4-Port 10GE Optical Interface Board(SFP+,LC)
unisevtModuleSw-LSX1GP48FB0                 OBJECT IDENTIFIER ::= { unisevtModuleSwitchType 1273 } -- 44-Port GE Optical Interface(SFP,LC)+4-Port 10GE Optical Interface Board(SFP+,LC)
unisevtModuleSw-LSX1GT48FC0                 OBJECT IDENTIFIER ::= { unisevtModuleSwitchType 1274 } -- 48-Port 1000Base-T Gigabit Ethernet Interface Module(RJ45)(FC)
unisevtModuleSw-LSX1GT48FC1                 OBJECT IDENTIFIER ::= { unisevtModuleSwitchType 1275 } -- 48-Port 1000Base-T Gigabit Ethernet Interface Module(RJ45)(FC)
unisevtModuleSw-LSX1GP48FC0                 OBJECT IDENTIFIER ::= { unisevtModuleSwitchType 1276 } -- 48-Port 1000BASE-X Gigabit Ethernet Optical Interface Module(SFP,LC)(FC)
unisevtModuleSw-LSX1GP48FC1                 OBJECT IDENTIFIER ::= { unisevtModuleSwitchType 1277 } -- 48-Port 1000BASE-X Gigabit Ethernet Optical Interface Module(SFP,LC)(FC)
unisevtModuleSw-LSX1QGS12FC0                OBJECT IDENTIFIER ::= { unisevtModuleSwitchType 1278 } -- 12-Port 40GBASE Ethernet Optical Interface Module(QSFP+)(FC)
unisevtModuleSw-LSX1QGS12FC1                OBJECT IDENTIFIER ::= { unisevtModuleSwitchType 1279 } -- 12-Port 40GBASE Ethernet Optical Interface Module(QSFP+)(FC)
unisevtModuleSw-LSX2TGS48EA1                OBJECT IDENTIFIER ::= { unisevtModuleSwitchType 1280 } -- 48-Port 10GBASE Ethernet SFP+ Optical Interface Board(EA)
unisevtModuleSw-LSX1CGC4EB1                 OBJECT IDENTIFIER ::= { unisevtModuleSwitchType 1281 } -- 4-Port 100GBASE Ethernet Optical Interface Board(CFP),Monolithic
unisevtModuleSw-LSX1CGC4EC0                 OBJECT IDENTIFIER ::= { unisevtModuleSwitchType 1282 } -- 4-Port 100GBASE Ethernet Optical Interface Board(CFP),Monolithic
unisevtModuleSw-LSX1GT48EB1                 OBJECT IDENTIFIER ::= { unisevtModuleSwitchType 1283 } -- 48-Port 1000Base-T Gigabit Ethernet Interface Board(RJ45)
unisevtModuleSw-LSX1GT48FB0                 OBJECT IDENTIFIER ::= { unisevtModuleSwitchType 1284 } -- 48-Port 1000Base-T Gigabit Ethernet Interface Board(RJ45)
unisevtModuleSw-LSX1FAB16S1                 OBJECT IDENTIFIER ::= { unisevtModuleSwitchType 1285 } -- Switch Fabric Board,For 16 Slots Chassis
unisevtModuleSw-LSQ1SUPB3                   OBJECT IDENTIFIER ::= { unisevtModuleSwitchType 1286 } -- Supervisor Engine Board
unisevtModuleSw-LSU1CGC2SE0                 OBJECT IDENTIFIER ::= { unisevtModuleSwitchType 1287 } -- 2 Port 100GBASE Ethernet Optical Interface Board(CFP)(SE)
unisevtModuleSw-LSU1TGS16SF0                OBJECT IDENTIFIER ::= { unisevtModuleSwitchType 1288 } -- 16-Port 10GBASE Ethernet SFP+ Optical Interface Board
unisevtModuleSw-LSU1TGS8SF0                 OBJECT IDENTIFIER ::= { unisevtModuleSwitchType 1289 } -- 8-Port 10GBASE Ethernet SFP+ Optical Interface Board
unisevtModuleSw-LSQ1TGS4SC0                 OBJECT IDENTIFIER ::= { unisevtModuleSwitchType 1290 } -- 4-Port 10GBASE Ethernet SFP+ Optical Interface Board
unisevtModuleSw-LSU1GT48SE3                 OBJECT IDENTIFIER ::= { unisevtModuleSwitchType 1291 } -- 48-Port 1000Base-T Gigabit Ethernet Interface Board(RJ45)
unisevtModuleSw-LSU1GP48SE3                 OBJECT IDENTIFIER ::= { unisevtModuleSwitchType 1292 } -- 48-Port 1000BASE Ethernet Optical Interface Board(SFP,LC)
unisevtModuleSw-LSX1SUP10B0                 OBJECT IDENTIFIER ::= { unisevtModuleSwitchType 1293 } -- Supervisor Engine Board
unisevtModuleSw-LSX1SUP16B0                 OBJECT IDENTIFIER ::= { unisevtModuleSwitchType 1294 } -- Supervisor Engine Board
unisevtModuleSw-LSX1SUP10B1                 OBJECT IDENTIFIER ::= { unisevtModuleSwitchType 1295 } -- Supervisor Engine Board
unisevtModuleSw-LSX1SUP16B1                 OBJECT IDENTIFIER ::= { unisevtModuleSwitchType 1296 } -- Supervisor Engine Board
unisevtModuleSw-LSQ1CGV24PSC3               OBJECT IDENTIFIER ::= { unisevtModuleSwitchType 1297 } -- Switching and Routing Processing Unit with 24 10/100/1000BASE-T Electrical Ports(RJ45),including 4 Combo Ports,SFP Req,PoE,No Spell
unisevtModuleSw-LSQ1SRPA8                   OBJECT IDENTIFIER ::= { unisevtModuleSwitchType 1298 } -- Supervisor Engine Board
unisevtModuleSw-LSQ1CGP24TSC8               OBJECT IDENTIFIER ::= { unisevtModuleSwitchType 1299 } -- Supervisor Engine Board
unisevtModuleSw-LSQ1CGT24PSC8               OBJECT IDENTIFIER ::= { unisevtModuleSwitchType 1300 } -- Supervisor Engine Board
unisevtModuleSw-LSQ1GT24PSA8                OBJECT IDENTIFIER ::= { unisevtModuleSwitchType 1301 } -- 24-Port 10/100/1000BASE-T Electrical(RJ45) Interface Board,including 4 Combo Ports,SFP Req,Upgradeable to PoE
unisevtModuleSw-LSQ1GP24TSA8                OBJECT IDENTIFIER ::= { unisevtModuleSwitchType 1302 } -- 16-Port 1000BASE-X Gigabit Ethernet Optical(SFP,LC) And 8-Port 10/100/1000BASE-T RJ45/1000BASE-X SFP Combo Interface Board
unisevtModuleSw-LSQ1GT48SA8                 OBJECT IDENTIFIER ::= { unisevtModuleSwitchType 1303 } -- 48-Port 1000Base-T Gigabit Ethernet Interface Board(RJ45)
unisevtModuleSw-LSQ1GP48SA8                 OBJECT IDENTIFIER ::= { unisevtModuleSwitchType 1304 } -- 48-Port 1000BASE-X Ethernet Optical Interface Board(SFP,LC)
unisevtModuleSw-LSQ1TGS4SC8                 OBJECT IDENTIFIER ::= { unisevtModuleSwitchType 1305 } -- 4-Port 10GBASE Ethernet SFP+ Optical Interface Board
unisevtModuleSw-LSQ1TGS8SC8                 OBJECT IDENTIFIER ::= { unisevtModuleSwitchType 1306 } -- 8-Port 10GBASE Ethernet SFP+ Optical Interface Board
unisevtModuleSw-LSU1GT24SE3                 OBJECT IDENTIFIER ::= { unisevtModuleSwitchType 1307 } -- 24-Port 1000BASE-T Ethernet Interface Board (RJ45)
unisevtModuleSw-LSU1GP12SE3                 OBJECT IDENTIFIER ::= { unisevtModuleSwitchType 1308 } -- 12-Port 1000BASE-X Ethernet Optical Interface Board(SFP,LC)
unisevtModuleSw-LSU1GP24SE3                 OBJECT IDENTIFIER ::= { unisevtModuleSwitchType 1309 } -- 24 Port 1000BASE-X Ethernet Optical Interface Board(SFP,LC)
unisevtModuleSw-LSU1T24XGSE3                OBJECT IDENTIFIER ::= { unisevtModuleSwitchType 1310 } -- 24-Port 1000BASE-T Gigabit Ethernet Interface(RJ45)+2-Port 10GBASE Ethernet Optical Interface Board(XFP,LC)
unisevtModuleSw-LSU1P24XGSE3                OBJECT IDENTIFIER ::= { unisevtModuleSwitchType 1311 } -- 24-Port 1000BASE-X Gigabit Ethernet Optical Interface(SFP,LC)+2-Port 10GBASE Ethernet Optical Interface Board(XFP,LC)
unisevtModuleSw-LSU1GP24TSE3                OBJECT IDENTIFIER ::= { unisevtModuleSwitchType 1312 } -- 16-Port 1000BASE-X Gigabit Ethernet Optical(SFP,LC) And 8-Port 10/100/1000BASE-T RJ45/1000BASE-X SFP Combo Interface Board
unisevtModuleSw-LSU1GT40PSE3                OBJECT IDENTIFIER ::= { unisevtModuleSwitchType 1313 } -- 40-Port 10/100/1000BASE-T Electrical(RJ45) And 8-Port 1000BASE-X Optical Ethernet Interface Board(SFP,LC),PoE
unisevtModuleSw-LSV1TGS24SA1                OBJECT IDENTIFIER ::= { unisevtModuleSwitchType 1314 } -- 24-Port 10G BASE Ethernet Optical Interface Board(SFP+)
unisevtModuleSw-LSVM1SRPA1                  OBJECT IDENTIFIER ::= { unisevtModuleSwitchType 1315 } -- Switching Fabric Module
unisevtModuleSw-LSVM1SRPC1                  OBJECT IDENTIFIER ::= { unisevtModuleSwitchType 1316 } -- Switching Fabric Module
unisevtModuleSw-LSX1FAB16S0                 OBJECT IDENTIFIER ::= { unisevtModuleSwitchType 1317 } -- Switch Fabric Board,For 16 Slots Chassis
unisevtModuleSw-LSU1WCME0                   OBJECT IDENTIFIER ::= { unisevtModuleSwitchType 1318 } -- Access Controller Service Board
unisevtModuleSw-EWPX1WCME0                  OBJECT IDENTIFIER ::= { unisevtModuleSwitchType 1319 } -- Access Controller Service Board
unisevtModuleSw-LSUM1TGS48SG0               OBJECT IDENTIFIER ::= { unisevtModuleSwitchType 1320 } -- 48-Port 10GBASE-R Ethernet SFP+ Optical Interface Board(SG)
unisevtModuleSw-LSUM1QGS12SG0               OBJECT IDENTIFIER ::= { unisevtModuleSwitchType 1321 } -- 12-Port 40GBASE-R Ethernet QSFP+ Optical Interface Board(SG)
unisevtModuleSw-LSUM1GP44TSEC0              OBJECT IDENTIFIER ::= { unisevtModuleSwitchType 1322 } -- 44-Port 1000BASE-R Ethernet SFP Optical Interface Board(EC)+4-Port 10GBASE-R Ethernet SFP+ Optical Interface Board(EC)
unisevtModuleSw-LSUM1TGS24EC0               OBJECT IDENTIFIER ::= { unisevtModuleSwitchType 1323 } -- 24-Port 10GBASE-R Ethernet SFP+ Optical Interface Board(EC)
unisevtModuleSw-LSUM1QGS6EC0                OBJECT IDENTIFIER ::= { unisevtModuleSwitchType 1324 } -- 6-Port 40GBASE-R Ethernet QSFP+ Optical Interface Board(EC)
unisevtModuleSw-LSUM1CGC2EC0                OBJECT IDENTIFIER ::= { unisevtModuleSwitchType 1325 } -- 2-Port 100GBASE-R Ethernet CFP Optical Interface Board(EC)
unisevtModuleSw-LSU1CGC2SE9                 OBJECT IDENTIFIER ::= { unisevtModuleSwitchType 1326 } -- 2 Port 100GBASE Ethernet Optical Interface Board(CFP)(SE)
unisevtModuleSw-LSXM1QGS24EX1               OBJECT IDENTIFIER ::= { unisevtModuleSwitchType 1327 } -- 24 Ports 40G BASE Ethernet Optical Interface Board(QSFP+,MPO),No Spell
unisevtModuleSw-LSXM1QGS24FB0               OBJECT IDENTIFIER ::= { unisevtModuleSwitchType 1328 } -- 24 Ports 40G BASE Ethernet Optical Interface Board(QSFP+,MPO),No Spell
unisevtModuleSw-LSVM1QGS12FX1               OBJECT IDENTIFIER ::= { unisevtModuleSwitchType 1329 } -- 12-Port 40G BASE Ethernet Optical Interface Module(QSFP+,MPO/LC)
unisevtModuleSw-LSVM1TGS24FX1               OBJECT IDENTIFIER ::= { unisevtModuleSwitchType 1330 } -- 24-Port 10G BASE Ethernet Optical Interface Module(SFP+,LC)
unisevtModuleSw-LSVM1QGS6C2FX1              OBJECT IDENTIFIER ::= { unisevtModuleSwitchType 1331 } -- 2-Port 100GBASE Ethernet Optical Interface(CXP,MPO)+6-Port 40GBASE Ethernet Optical Interface(QSFP+,MPO/LC)+4-Port 10G BASE Ethernet Optical Interface Module(SFP+,LC)
unisevtModuleSw-LSQM2GP44TSSC0              OBJECT IDENTIFIER ::= { unisevtModuleSwitchType 1332 } -- 44-Port GE Optical Interface(SFP,LC)+4-Port 10GE Optical Interface Board(SFP+,LC)(SC)
unisevtModuleSw-LSQM2GP44TSSC3              OBJECT IDENTIFIER ::= { unisevtModuleSwitchType 1333 } -- 44-Port GE Optical Interface(SFP,LC)+4-Port 10GE Optical Interface Board(SFP+,LC)(SC)
unisevtModuleSw-LSQM2GP24TSSC0              OBJECT IDENTIFIER ::= { unisevtModuleSwitchType 1334 } -- 24-Port GE Optical Interface(SFP,LC)+4-Port 10GE Optical Interface Board(SFP+,LC)(SC)
unisevtModuleSw-LSQM2GP24TSSC3              OBJECT IDENTIFIER ::= { unisevtModuleSwitchType 1335 } -- 24-Port GE Optical Interface(SFP,LC)+4-Port 10GE Optical Interface Board(SFP+,LC)(SC)
unisevtModuleSw-LSQM2GT24PTSSC0             OBJECT IDENTIFIER ::= { unisevtModuleSwitchType 1336 } -- 24-Port 1000Base-T Gigabit Ethernet Interface Board(RJ45)+20-Port GE Optical Interface(SFP,LC)+4-Port 10GE Optical Interface Board(SFP+,LC)(SC)
unisevtModuleSw-LSQM2GT24PTSSC3             OBJECT IDENTIFIER ::= { unisevtModuleSwitchType 1337 } -- 24-Port 1000Base-T Gigabit Ethernet Interface Board(RJ45)+20-Port GE Optical Interface(SFP,LC)+4-Port 10GE Optical Interface Board(SFP+,LC)(SC)
unisevtModuleSw-LSQM2GT24TSSC0              OBJECT IDENTIFIER ::= { unisevtModuleSwitchType 1338 } -- 24-Port 1000Base-T Gigabit Ethernet Interface Board(RJ45)+4-Port 10GE Optical Interface Board(SFP+,LC)(SC)
unisevtModuleSw-LSQM2GT24TSSC3              OBJECT IDENTIFIER ::= { unisevtModuleSwitchType 1339 } -- 24-Port 1000Base-T Gigabit Ethernet Interface Board(RJ45)+4-Port 10GE Optical Interface Board(SFP+,LC)(SC)
unisevtModuleSw-LSQM2GT48SC0                OBJECT IDENTIFIER ::= { unisevtModuleSwitchType 1340 } -- 48-Port 1000Base-T Gigabit Ethernet Interface Board(RJ45)(SC)
unisevtModuleSw-LSQM2GT48SC3                OBJECT IDENTIFIER ::= { unisevtModuleSwitchType 1341 } -- 48-Port 1000Base-T Gigabit Ethernet Interface Board(RJ45)(SC)
unisevtModuleSw-LSQM4GV48SC0                OBJECT IDENTIFIER ::= { unisevtModuleSwitchType 1342 } -- 48-Port 1000Base-T Gigabit Ethernet Interface Board(RJ45)(SC)-POE
unisevtModuleSw-LSQM4GV48SC3                OBJECT IDENTIFIER ::= { unisevtModuleSwitchType 1343 } -- 48-Port 1000Base-T Gigabit Ethernet Interface Board(RJ45)(SC)-POE
unisevtModuleSw-LSQM2TGS16SF0               OBJECT IDENTIFIER ::= { unisevtModuleSwitchType 1344 } -- 16-Port 10GE Optical Interface Board(SFP+,LC)(SF)
unisevtModuleSw-LSQM2TGS16SF3               OBJECT IDENTIFIER ::= { unisevtModuleSwitchType 1345 } -- 16-Port 10GE Optical Interface Board(SFP+,LC)(SF)
unisevtModuleSw-LSQM2MPUD0                  OBJECT IDENTIFIER ::= { unisevtModuleSwitchType 1346 } -- Supervisor Engine Board
unisevtModuleSw-LSQM2MPUD3                  OBJECT IDENTIFIER ::= { unisevtModuleSwitchType 1347 } -- Supervisor Engine Board
unisevtModuleSw-LSQM3MPUA0                  OBJECT IDENTIFIER ::= { unisevtModuleSwitchType 1348 } -- Supervisor Engine Board
unisevtModuleSw-LSQM3MPUA3                  OBJECT IDENTIFIER ::= { unisevtModuleSwitchType 1349 } -- Supervisor Engine Board
unisevtModuleSw-LSUM2GP44TSSE0              OBJECT IDENTIFIER ::= { unisevtModuleSwitchType 1350 } -- 44-Port GE Optical Interface(SFP,LC)+4-Port 10GE Optical Interface Board(SFP+,LC)(SE)
unisevtModuleSw-LSUM2GP44TSSC3              OBJECT IDENTIFIER ::= { unisevtModuleSwitchType 1351 } -- 44-Port GE Optical Interface(SFP,LC)+4-Port 10GE Optical Interface Board(SFP+,LC)(SC)
unisevtModuleSw-LSUM2GP24TSSE0              OBJECT IDENTIFIER ::= { unisevtModuleSwitchType 1352 } -- 24-Port GE Optical Interface(SFP,LC)+4-Port 10GE Optical Interface Board(SFP+,LC)(SE)
unisevtModuleSw-LSUM2GP24TSSC3              OBJECT IDENTIFIER ::= { unisevtModuleSwitchType 1353 } -- 24-Port GE Optical Interface(SFP,LC)+4-Port 10GE Optical Interface Board(SFP+,LC)(SC)
unisevtModuleSw-LSUM2GT24PTSSE0             OBJECT IDENTIFIER ::= { unisevtModuleSwitchType 1354 } -- 24-Port 1000Base-T Gigabit Ethernet Interface Board(RJ45)+20-Port GE Optical Interface(SFP,LC)+4-Port 10GE Optical Interface Board(SFP+,LC)(SE)
unisevtModuleSw-LSUM2GT24PTSSC3             OBJECT IDENTIFIER ::= { unisevtModuleSwitchType 1355 } -- 24-Port 1000Base-T Gigabit Ethernet Interface Board(RJ45)+20-Port GE Optical Interface(SFP,LC)+4-Port 10GE Optical Interface Board(SFP+,LC)(SC)
unisevtModuleSw-LSUM2GT24TSSE0              OBJECT IDENTIFIER ::= { unisevtModuleSwitchType 1356 } -- 24-Port 1000Base-T Gigabit Ethernet Interface Board(RJ45)+4-Port 10GE Optical Interface Board(SFP+,LC)(SE)
unisevtModuleSw-LSUM2GT24TSSC3              OBJECT IDENTIFIER ::= { unisevtModuleSwitchType 1357 } -- 24-Port 1000Base-T Gigabit Ethernet Interface Board(RJ45)+4-Port 10GE Optical Interface Board(SFP+,LC)(SC)
unisevtModuleSw-LSUM2GT48SE0                OBJECT IDENTIFIER ::= { unisevtModuleSwitchType 1358 } -- 48-Port 1000Base-T Gigabit Ethernet Interface Board(RJ45)(SE)
unisevtModuleSw-LSUM2GT48SC3                OBJECT IDENTIFIER ::= { unisevtModuleSwitchType 1359 } -- 48-Port 1000Base-T Gigabit Ethernet Interface Board(RJ45)(SC)
unisevtModuleSw-LSUM2GV48SE0                OBJECT IDENTIFIER ::= { unisevtModuleSwitchType 1360 } -- 48-Port 1000Base-T Gigabit Ethernet Interface Board(RJ45)(SE)-POE
unisevtModuleSw-LSUM2GV48SC3                OBJECT IDENTIFIER ::= { unisevtModuleSwitchType 1361 } -- 48-Port 1000Base-T Gigabit Ethernet Interface Board(RJ45)(SC)-POE
unisevtModuleSw-LSUM2TGS16SF0               OBJECT IDENTIFIER ::= { unisevtModuleSwitchType 1362 } -- 16-Port 10GE Optical Interface Board(SFP+,LC)(SF)
unisevtModuleSw-LSUM2TGS16SF3               OBJECT IDENTIFIER ::= { unisevtModuleSwitchType 1363 } -- 16-Port 10GE Optical Interface Board(SFP+,LC)(SF)
unisevtModuleSw-LSUM1MPU06B0                OBJECT IDENTIFIER ::= { unisevtModuleSwitchType 1364 } -- Supervisor Engine Board
unisevtModuleSw-LSUM1MPU06B3                OBJECT IDENTIFIER ::= { unisevtModuleSwitchType 1365 } -- Supervisor Engine Board
unisevtModuleSw-LSUM1MPU10C0                OBJECT IDENTIFIER ::= { unisevtModuleSwitchType 1366 } -- Supervisor Engine Board
unisevtModuleSw-LSUM1MPU10C3                OBJECT IDENTIFIER ::= { unisevtModuleSwitchType 1367 } -- Supervisor Engine Board
unisevtModuleSw-LSUM1FAB06C0                OBJECT IDENTIFIER ::= { unisevtModuleSwitchType 1368 } -- Switching Fabric Module
unisevtModuleSw-LSUM1FAB06C3                OBJECT IDENTIFIER ::= { unisevtModuleSwitchType 1369 } -- Switching Fabric Module
unisevtModuleSw-LSUM1FAB10C0                OBJECT IDENTIFIER ::= { unisevtModuleSwitchType 1370 } -- Switching Fabric Module
unisevtModuleSw-LSUM1FAB10C3                OBJECT IDENTIFIER ::= { unisevtModuleSwitchType 1371 } -- Switching Fabric Module
unisevtModuleSw-LSXM1SUPA1                  OBJECT IDENTIFIER ::= { unisevtModuleSwitchType 1372 } -- Supervisor Engine Module
unisevtModuleSw-LSXM1SFF16B1                OBJECT IDENTIFIER ::= { unisevtModuleSwitchType 1373 } -- Switch Fabric Board
unisevtModuleSw-LSUM1SPMAEC0                OBJECT IDENTIFIER ::= { unisevtModuleSwitchType 1374 } -- 4-Port Multiservice Processing Engine
unisevtModuleSw-LSXM1SUPB1                  OBJECT IDENTIFIER ::= { unisevtModuleSwitchType 1375 } -- Supervisor Engine Module
unisevtModuleSw-LSXM1SFF08B1                OBJECT IDENTIFIER ::= { unisevtModuleSwitchType 1376 } -- Switching Fabric Module,Type B(F1)
unisevtModuleSw-LSXM1TGS4GPEB1              OBJECT IDENTIFIER ::= { unisevtModuleSwitchType 1377 } -- 44-Port GE Optical Interface(SFP,LC)+4-Port 10GE Optical Interface Module(SFP+,LC)(EB)
unisevtModuleSw-LSXM1TGS16EA1               OBJECT IDENTIFIER ::= { unisevtModuleSwitchType 1378 } -- 16-Port 10GBASE Ethernet Optical Interface Module(SFP+,LC)(EA)
unisevtModuleSw-LSXM1TGS8EA1                OBJECT IDENTIFIER ::= { unisevtModuleSwitchType 1379 } -- 8-Port 10GBASE Ethernet Optical Interface Module(SFP+,LC)(EA)
unisevtModuleSw-LSXM1QGS36FX1               OBJECT IDENTIFIER ::= { unisevtModuleSwitchType 1380 } -- 36-Port 40GBASE Ethernet Optical Interface Module(QSFP+)(FX)
unisevtModuleSw-LSXM1SFF16C1                OBJECT IDENTIFIER ::= { unisevtModuleSwitchType 1381 } -- Switching Fabric Module
unisevtModuleSw-LSQM3MPUB0                  OBJECT IDENTIFIER ::= { unisevtModuleSwitchType 1382 } -- Supervisor Engine Board
unisevtModuleSw-LSQM3MPUB3                  OBJECT IDENTIFIER ::= { unisevtModuleSwitchType 1383 } -- Supervisor Engine Board
unisevtModuleSw-LSQM2MPUC0                  OBJECT IDENTIFIER ::= { unisevtModuleSwitchType 1384 } -- Supervisor Engine Board
unisevtModuleSw-LSQM2MPUC3                  OBJECT IDENTIFIER ::= { unisevtModuleSwitchType 1385 } -- Supervisor Engine Board
unisevtModuleSw-LST1FW3B1                   OBJECT IDENTIFIER ::= { unisevtModuleSwitchType 1386 } -- Firewall Board
unisevtModuleSw-LSX1NSCEA1                  OBJECT IDENTIFIER ::= { unisevtModuleSwitchType 1387 } -- NetStream Service Board
unisevtModuleSw-LSX1FWCEA1                  OBJECT IDENTIFIER ::= { unisevtModuleSwitchType 1388 } -- Firewall Service Board
unisevtModuleSw-LSXM1ADECEA1                OBJECT IDENTIFIER ::= { unisevtModuleSwitchType 1389 } -- Application Dilevery Engine Module,Domestic&Overseas Version
unisevtModuleSw-LSXM1SFF16A1                OBJECT IDENTIFIER ::= { unisevtModuleSwitchType 1390 } -- Switching Fabric Module
unisevtModuleSw-LSV1MPUA0                   OBJECT IDENTIFIER ::= { unisevtModuleSwitchType 1391 } -- Supervisor Engine Board
unisevtModuleSw-LSVM1SRPA0                  OBJECT IDENTIFIER ::= { unisevtModuleSwitchType 1392 } -- Switching Fabric Module
unisevtModuleSw-LSVM1SRPC0                  OBJECT IDENTIFIER ::= { unisevtModuleSwitchType 1393 } -- Switching Fabric Module
unisevtModuleSw-LSV1QGS12SA0                OBJECT IDENTIFIER ::= { unisevtModuleSwitchType 1394 } -- 12-Port 40G BASE Ethernet Optical Interface Board(QSFP+)
unisevtModuleSw-LSVM1QGS12FX0               OBJECT IDENTIFIER ::= { unisevtModuleSwitchType 1395 } -- 12-Port 40G BASE Ethernet Optical Interface Module(QSFP+,MPO/LC)
unisevtModuleSw-LSVM1TGS24FX0               OBJECT IDENTIFIER ::= { unisevtModuleSwitchType 1396 } -- 24-Port 10G BASE Ethernet Optical Interface Module(SFP+,LC)
unisevtModuleSw-LSVM1QGS6C2FX0              OBJECT IDENTIFIER ::= { unisevtModuleSwitchType 1397 } -- 2-Port 100GBASE Ethernet Optical Interface(CXP,MPO)+6-Port 40GBASE Ethernet Optical Interface(QSFP+,MPO/LC)+4-Port 10G BASE Ethernet Optical Interface Module(SFP+,LC)
unisevtModuleSw-LSQ2FWBSC0                  OBJECT IDENTIFIER ::= { unisevtModuleSwitchType 1398 } -- Gigabit Firewall Card, 4 Gigabit Port for Management
unisevtModuleSw-LSQM1SRP8X2QE0              OBJECT IDENTIFIER ::= { unisevtModuleSwitchType 1399 } -- Supervisor Engine Board With 8-Port 10GBASE Ethernet SFP+ Optical Interfaces+2-Port 40GBASE-R Ethernet QSFP+ Optical Interfaces

--
-- 1400 to 1599 reserved for switche RPU logical modules
--
unisevtModulesw-PEX-Common                  OBJECT IDENTIFIER ::= { unisevtModuleSwitchType 1400 } -- The general logical module type for PEX
unisevtModuleSw-CSPEX-1812X                 OBJECT IDENTIFIER ::= { unisevtModuleSwitchType 1401 } -- Service Processing Unit Module(1812X)
unisevtModuleSw-CSPEX-1612X                 OBJECT IDENTIFIER ::= { unisevtModuleSwitchType 1402 } -- Service Processing Unit Module(1612X)
unisevtModuleSw-CSPEX-1512X                 OBJECT IDENTIFIER ::= { unisevtModuleSwitchType 1403 } -- Service Processing Unit Module(1512X)
unisevtModuleSw-NIC-XP20L                   OBJECT IDENTIFIER ::= { unisevtModuleSwitchType 1404 } -- 20-port 10GBASE-R/W Ethernet Optical Interface Card Module(SFP+,LC)(NIC)
unisevtModuleSw-NIC-XP10L                   OBJECT IDENTIFIER ::= { unisevtModuleSwitchType 1405 } -- 10-port 10GBASE-R/W Ethernet Optical Interface Card Module(SFP+,LC)(NIC)
unisevtModuleSw-NIC-CC2L                    OBJECT IDENTIFIER ::= { unisevtModuleSwitchType 1406 } -- 2-port 100G Ethernet Optical Interface Card Module(CFP2,LC)(NIC)
unisevtModuleSw-NIC-CC1L                    OBJECT IDENTIFIER ::= { unisevtModuleSwitchType 1407 } -- 1-port 100G Ethernet Optical Interface Card Module(CFP2,LC)(NIC)
unisevtModuleSw-NIC-XP5L                    OBJECT IDENTIFIER ::= { unisevtModuleSwitchType 1408 } -- 5-port 10GBASE-R/W Ethernet Optical Interface Card Module(SFP+,LC)(NIC)
unisevtModuleSw-NIC-GP20L                   OBJECT IDENTIFIER ::= { unisevtModuleSwitchType 1409 } -- 20-port 1000BASE-X Ethernet Optical Interface Card Module(SFP,LC)(NIC)
unisevtModuleSw-NIC-GT20L                   OBJECT IDENTIFIER ::= { unisevtModuleSwitchType 1410 } -- 20-port 1000BASE-T Ethernet Copper Interface Card Module(RJ45)(NIC)
unisevtModuleSw-MIC-CQ1L                    OBJECT IDENTIFIER ::= { unisevtModuleSwitchType 1411 } -- 1-port 100G Ethernet Optical Interface Card Module(QSFP28,LC)
unisevtModuleSw-MIC-XP10CQ1L                OBJECT IDENTIFIER ::= { unisevtModuleSwitchType 1412 } -- 10-port 10GBASE-R/W Ethernet Optical Interface(SFP+,LC)+1-port 100G Ethernet Optical Interface Card Module(QSFP28,LC)
unisevtModuleSw-CSPEX-1502X                 OBJECT IDENTIFIER ::= { unisevtModuleSwitchType 1413 } -- Service Processing Unit(1502X)
unisevtModuleSw-EPC-CP4RX                   OBJECT IDENTIFIER ::= { unisevtModuleSwitchType 1414 } -- 4-port 100GBASE Ethernet Optical Line Processing Unit(CFP2)
unisevtModuleSw-EPC-CQ4LX                   OBJECT IDENTIFIER ::= { unisevtModuleSwitchType 1415 } -- 4-port 100GBASE Ethernet Optical Line Processing Unit(QSFP28)
unisevtModuleSw-MIC-XP4L1-E                 OBJECT IDENTIFIER ::= { unisevtModuleSwitchType 1416 } -- 4-port 10GBASE-R/W Ethernet Optical Interface Card 1(SFP+,LC)
unisevtModuleSw-MIC-CQ1L-E                  OBJECT IDENTIFIER ::= { unisevtModuleSwitchType 1417 } -- 1-port 100G Ethernet Optical Interface Card 1(QSFP28)
unisevtModuleSw-MIC-XP8L                    OBJECT IDENTIFIER ::= { unisevtModuleSwitchType 1418 } -- 8-port 10GBASE-R/W Ethernet Optical Interface Card (SFP+,LC)
unisevtModuleSw-IM-OAPX                     OBJECT IDENTIFIER ::= { unisevtModuleSwitchType 1419 } -- Universal Open Platform(IM-OAPX)
unisevtModuleSw-MIC-GP20L1                  OBJECT IDENTIFIER ::= { unisevtModuleSwitchType 1420 } -- 20-port 1000BASE-X Ethernet Optical Interface Card(SFP,LC)
unisevtModuleSw-CSPEX-1802X                 OBJECT IDENTIFIER ::= { unisevtModuleSwitchType 1421 } -- Service Processing Unit(1802X)
unisevtModuleSw-MIC-CQ2L                    OBJECT IDENTIFIER ::= { unisevtModuleSwitchType 1422 } -- 2-port 100G Ethernet Optical Interface Card(QSFP28,LC)
unisevtModuleSw-IMMSUX                      OBJECT IDENTIFIER ::= { unisevtModuleSwitchType 1423 } -- Universal Line Processing Unit(IM-MSUX)(China Telecom)
unisevtModuleSw-CSPEX-1104-E                OBJECT IDENTIFIER ::= { unisevtModuleSwitchType 1424 } -- Service Processing Unit(1104E)
unisevtModuleSw-IMSMUX                      OBJECT IDENTIFIER ::= { unisevtModuleSwitchType 1425 } -- Security Monitor Unit(IM-SMUX)
unisevtModuleSw-MIC-XP10L                   OBJECT IDENTIFIER ::= { unisevtModuleSwitchType 1426 } -- 10-port 10GBASE-R/W Ethernet Optical Interface Card(SFP+,LC)
unisevtModuleSw-RX-SRP1P3                   OBJECT IDENTIFIER ::= { unisevtModuleSwitchType 1427 } -- RX8800 Main Processing Unit(1P3)
unisevtModuleSw-RX-SFC-08T                  OBJECT IDENTIFIER ::= { unisevtModuleSwitchType 1428 } -- 1Tbps Fabric Module(08)
unisevtModuleSw-RX-SFC-16T                  OBJECT IDENTIFIER ::= { unisevtModuleSwitchType 1429 } -- 1Tbps Fabric Module(16)
unisevtModuleSw-RX-SPE100                   OBJECT IDENTIFIER ::= { unisevtModuleSwitchType 1430 } -- 100G Service Processing Unit(SPE100)
unisevtModuleSw-RX-SPE200                   OBJECT IDENTIFIER ::= { unisevtModuleSwitchType 1431 } -- 200G Service Processing Unit(SPE200)
unisevtModuleSw-RX-SPE400                   OBJECT IDENTIFIER ::= { unisevtModuleSwitchType 1432 } -- 400G Service Processing Unit(SPE400)
unisevtModuleSw-RX-NIC-GP20L                OBJECT IDENTIFIER ::= { unisevtModuleSwitchType 1433 } -- 20-port 1000BASE-X Ethernet Optical Interface Card(SFP,LC)(RX-NIC,SPE100)
unisevtModuleSw-RX-NIC-XP5L                 OBJECT IDENTIFIER ::= { unisevtModuleSwitchType 1434 } -- 5-port 10GBASE-R/W Ethernet Optical Interface Card(SFP+,LC)(RX-NIC,SPE100)
unisevtModuleSw-RX-NIC-XP10L                OBJECT IDENTIFIER ::= { unisevtModuleSwitchType 1435 } -- 10-port 10GBASE-R/W Ethernet Optical Interface Card(SFP+,LC)(RX-NIC,SPE200)
unisevtModuleSw-RX-NIC-CC1L                 OBJECT IDENTIFIER ::= { unisevtModuleSwitchType 1436 } -- 1-port 100G Ethernet Optical Interface Card(CFP2,LC)(RX-NIC,SPE200)
unisevtModuleSw-RX-NIC-CC2L                 OBJECT IDENTIFIER ::= { unisevtModuleSwitchType 1437 } -- 2-port 100G Ethernet Optical Interface Card(CFP2,LC)(RX-NIC,SPE400)
unisevtModuleSw-RX-NIC-XP20L                OBJECT IDENTIFIER ::= { unisevtModuleSwitchType 1438 } -- 20-port 10GBASE-R/W Ethernet Optical Interface Card(SFP+,LC)(RX-NIC,SPE400)
unisevtModuleSw-CSPC-GE24L-E                OBJECT IDENTIFIER ::= { unisevtModuleSwitchType 1439 } -- 24-port 1000BASE-X Ethernet Combo Interface Line Processing Unit(E Type)
unisevtModuleSw-CSPC-GP24GE8XP2L-E          OBJECT IDENTIFIER ::= { unisevtModuleSwitchType 1440 } -- 24-port 1000BASE-X Ethernet Optical Interface(SFP,LC)+ 8-port 1000BASE-X Ethernet Combo Interface+2-port 10GBASE-R/W Ethernet Optical Interface Line Processing Unit(SFP+,LC)(E Type)
unisevtModuleSw-CSPC-GE16XP4L-E             OBJECT IDENTIFIER ::= { unisevtModuleSwitchType 1441 } -- 16-port 1000BASE-X Ethernet Combo Interface+4-port 10GBASE-R/W Ethernet Optical Interface Line Processing Unit(SFP+,LC)(E Type)
unisevtModuleSw-CSFC-04E                    OBJECT IDENTIFIER ::= { unisevtModuleSwitchType 1442 } -- CR16006-F Fabric Module(E Type)
unisevtModuleSw-SFC-04E                     OBJECT IDENTIFIER ::= { unisevtModuleSwitchType 1443 } -- SR8804-X Fabric Module(E Type)
unisevtModuleSw-IM-MSUX-II                  OBJECT IDENTIFIER ::= { unisevtModuleSwitchType 1444 } -- Universal Line Processing Unit(IM-MSUX-II)
unisevtModuleSw-RX-NIC-YGS4L                OBJECT IDENTIFIER ::= { unisevtModuleSwitchType 1445 } -- 4-port 25G Ethernet Optical Interface Card(SFP28,LC)
unisevtModuleSw-RX-NIC-CQ2LF                OBJECT IDENTIFIER ::= { unisevtModuleSwitchType 1446 } -- 2-port 100G Flexible Ethernet Optical Interface Card(QSFP28,LC)
unisevtModuleSw-RX-SRP1Q3                   OBJECT IDENTIFIER ::= { unisevtModuleSwitchType 1447 } -- RX8800 Main Processing Unit(1Q3)
unisevtModuleSw-RX-SFC-08E                  OBJECT IDENTIFIER ::= { unisevtModuleSwitchType 1448 } -- 400Gbps Fabric Module(08)
unisevtModuleSw-RX-SFC-16E                  OBJECT IDENTIFIER ::= { unisevtModuleSwitchType 1449 } -- 400Gbps Fabric Module(16)
unisevtModuleSw-RX-NIC-LGQ2L                OBJECT IDENTIFIER ::= { unisevtModuleSwitchType 1450 } -- 2-port 50G Ethernet Optical Interface Card(QSFP28,LC)(RX-NIC)

unisevtModuleSw-RX-NIC-CQ1LF                OBJECT IDENTIFIER ::= { unisevtModuleSwitchType 1452 } -- 1-port 100G Flexible Ethernet Optical Interface Card(QSFP28,LC)(RX-NIC)
unisevtModuleSw-IM-SFMX                     OBJECT IDENTIFIER ::= { unisevtModuleSwitchType 1453 } -- Network Data Encryption Service Processing Unit(IM-SFMX)
unisevtModuleSw-MIC-SM                      OBJECT IDENTIFIER ::= { unisevtModuleSwitchType 1454 } -- Network Data Encryption Interface Card(MIC-SM)
unisevtModuleSw-RX-NIC-CQ1L                 OBJECT IDENTIFIER ::= { unisevtModuleSwitchType 1455 } -- 1-port 100G Ethernet Optical Interface Card(QSFP28,LC)(RX-NIC)
unisevtModuleSw-RX-NIC-CQ2L                 OBJECT IDENTIFIER ::= { unisevtModuleSwitchType 1456 } -- 2-port 100G Ethernet Optical Interface Card(QSFP28,LC)(RX-NIC)
unisevtModuleSw-NIC-GP24L                   OBJECT IDENTIFIER ::= { unisevtModuleSwitchType 1457 } -- 24-port 1000BASE-X Ethernet Optical Interface Card(SFP,LC)(NIC)
unisevtModuleSw-NIC-CQ1L                    OBJECT IDENTIFIER ::= { unisevtModuleSwitchType 1458 } -- 1-port 100G Ethernet Optical Interface Card(QSFP28,LC)(NIC)
unisevtModuleSw-NIC-CQ2L                    OBJECT IDENTIFIER ::= { unisevtModuleSwitchType 1459 } -- 2-port 100G Ethernet Optical Interface Card(QSFP28,LC)(NIC)
-- 1600 to 1799 reserved for secondary switches part III
--
unisevtModuleSw-LSUM2GP44TSSE9              OBJECT IDENTIFIER ::= { unisevtModuleSwitchType 1600 } -- 44-Port GE Optical Interface(SFP,LC)+4-Port 10GE Optical Interface Board(SFP+,LC)(SE)
unisevtModuleSw-LSUM2GP24TSSE9              OBJECT IDENTIFIER ::= { unisevtModuleSwitchType 1601 } -- 24-Port GE Optical Interface(SFP,LC)+4-Port 10GE Optical Interface Board(SFP+,LC)(SE)
unisevtModuleSw-LSUM2GT24TSSE9              OBJECT IDENTIFIER ::= { unisevtModuleSwitchType 1602 } -- 24-Port 1000Base-T Gigabit Ethernet Interface Board(RJ45)+4-Port 10GE Optical Interface Board(SFP+,LC)(SE)
unisevtModuleSw-LSUM2GT48SE9                OBJECT IDENTIFIER ::= { unisevtModuleSwitchType 1603 } -- 48-Port 1000Base-T Gigabit Ethernet Interface Board(RJ45)(SE)
unisevtModuleSw-LSUM1SUPD0                  OBJECT IDENTIFIER ::= { unisevtModuleSwitchType 1604 } -- Supervisor Engine Board
unisevtModuleSw-LSUM1SUPD9                  OBJECT IDENTIFIER ::= { unisevtModuleSwitchType 1605 } -- Supervisor Engine Board
unisevtModuleSw-LSXM1TGT48FX0               OBJECT IDENTIFIER ::= { unisevtModuleSwitchType 1606 } -- 48-Port 10GBASE-T Ethernet Electrical Interface Module(RJ45)(FX)
unisevtModuleSw-LSXM1TGS48FX0               OBJECT IDENTIFIER ::= { unisevtModuleSwitchType 1607 } -- 48-Port 10GBASE-T Ethernet Electrical Interface Module(RJ45)(FX)
unisevtModuleSw-LSXM1TGS48FE0               OBJECT IDENTIFIER ::= { unisevtModuleSwitchType 1608 } -- 48-Port 10GBASE Ethernet Optical Interface Module(SFP+,LC)(FE)
unisevtModuleSw-LSXM1QGS36FX0               OBJECT IDENTIFIER ::= { unisevtModuleSwitchType 1609 } -- 36-Port 40GBASE Ethernet Optical Interface Module(QSFP+)(FX)
unisevtModuleSw-LSXM1QGS24FX0               OBJECT IDENTIFIER ::= { unisevtModuleSwitchType 1610 } -- 24-Port 40GBASE Ethernet Optical Interface Module(QSFP+)(FX)
unisevtModuleSw-LSXM1QGS24FE0               OBJECT IDENTIFIER ::= { unisevtModuleSwitchType 1611 } -- 24-Port 40GBASE Ethernet Optical Interface Module(QSFP+)(FE)
unisevtModuleSw-LSXM1CGX8FX0                OBJECT IDENTIFIER ::= { unisevtModuleSwitchType 1612 } -- 8-Port 100GBASE Ethernet Optical Interface Module(CXP)(FX)
unisevtModuleSw-LSXM1CGP12FX0               OBJECT IDENTIFIER ::= { unisevtModuleSwitchType 1613 } -- 12-Port 100GBASE Ethernet Optical Interface Module(CFP2)(FX)
unisevtModuleSw-LSXM1SUPB0                  OBJECT IDENTIFIER ::= { unisevtModuleSwitchType 1614 } -- Supervisor Engine Module
unisevtModuleSw-LSXM1SFF16C0                OBJECT IDENTIFIER ::= { unisevtModuleSwitchType 1615 } -- Switching Fabric Module,Type F(Class C)
unisevtModuleSw-LSXM1SFF16A0                OBJECT IDENTIFIER ::= { unisevtModuleSwitchType 1616 } -- Switching Fabric Module,Type F(Class A)
unisevtModuleSw-LSXM1SFF08B0                OBJECT IDENTIFIER ::= { unisevtModuleSwitchType 1617 } -- Switching Fabric Module,Type F(Class B)
unisevtModuleSw-LSQM6GV48SC0                OBJECT IDENTIFIER ::= { unisevtModuleSwitchType 1618 } -- 48-Port 10/100/1000BASE-T Ethernet Interface Module(RJ45),Upgradeable to PoE
unisevtModuleSw-LSXM1SUP04B1                OBJECT IDENTIFIER ::= { unisevtModuleSwitchType 1619 } -- Supervisor Engine Module
unisevtModuleSw-LSXM1SFF04B1                OBJECT IDENTIFIER ::= { unisevtModuleSwitchType 1620 } -- Switching Fabric Module,Type F(Class B)
unisevtModuleSw-LSXM1SUP04B0                OBJECT IDENTIFIER ::= { unisevtModuleSwitchType 1621 } -- Supervisor Engine Module
unisevtModuleSw-LSXM1SFF04B0                OBJECT IDENTIFIER ::= { unisevtModuleSwitchType 1622 } -- Switching Fabric Module,Type F(Class B)
unisevtModuleSw-LSU1ADECEA0                 OBJECT IDENTIFIER ::= { unisevtModuleSwitchType 1623 } -- Application Dilevery Engine Module,Domestic&Overseas Version
unisevtModuleSw-LSU1NSCEA0                  OBJECT IDENTIFIER ::= { unisevtModuleSwitchType 1624 } -- NetStream Service Board
unisevtModuleSw-LSU3FWCEA0                  OBJECT IDENTIFIER ::= { unisevtModuleSwitchType 1625 } -- Firewall Service Board
unisevtModuleSw-LSXM1MPU06B3                OBJECT IDENTIFIER ::= { unisevtModuleSwitchType 1626 } -- Supervisor Engine Board
unisevtModuleSw-LSXM1MPU10C3                OBJECT IDENTIFIER ::= { unisevtModuleSwitchType 1627 } -- Supervisor Engine Board
unisevtModuleSw-LSXM1SUPD3                  OBJECT IDENTIFIER ::= { unisevtModuleSwitchType 1628 } -- Supervisor Engine Board
unisevtModuleSw-LSXM1FAB06C3                OBJECT IDENTIFIER ::= { unisevtModuleSwitchType 1629 } -- Switching Fabric Module
unisevtModuleSw-LSXM1FAB10C3                OBJECT IDENTIFIER ::= { unisevtModuleSwitchType 1630 } -- Switching Fabric Module
unisevtModuleSw-LSXM1FAB12D3                OBJECT IDENTIFIER ::= { unisevtModuleSwitchType 1631 } -- Switching Fabric Module
unisevtModuleSw-LSXM1FAB04D3                OBJECT IDENTIFIER ::= { unisevtModuleSwitchType 1632 } -- Switching Fabric Module
unisevtModuleSw-LSXM1FAB08D3                OBJECT IDENTIFIER ::= { unisevtModuleSwitchType 1633 } -- Switching Fabric Module
unisevtModuleSw-LSXM1GP44TSSE3              OBJECT IDENTIFIER ::= { unisevtModuleSwitchType 1634 } -- 44-Port GE Optical Interface(SFP,LC)+4-Port 10GE Optical Interface Board(SFP+,LC)(SE)
unisevtModuleSw-LSXM1GP24TSSE3              OBJECT IDENTIFIER ::= { unisevtModuleSwitchType 1635 } -- 24-Port GE Optical Interface(SFP,LC)+4-Port 10GE Optical Interface Board(SFP+,LC)(SE)
unisevtModuleSw-LSXM1GT24PTSSE3             OBJECT IDENTIFIER ::= { unisevtModuleSwitchType 1636 } -- 24-Port 1000Base-T Gigabit Ethernet Interface Board(RJ45)+20-Port GE Optical Interface(SFP,LC)+4-Port 10GE Optical Interface Board(SFP+,LC)(SE)
unisevtModuleSw-LSXM1GT48SE3                OBJECT IDENTIFIER ::= { unisevtModuleSwitchType 1637 } -- 48-Port 1000Base-T Gigabit Ethernet Interface Board(RJ45)(SE)
unisevtModuleSw-LSXM1TGS24EC3               OBJECT IDENTIFIER ::= { unisevtModuleSwitchType 1638 } -- 24-Port 10GBASE-R Ethernet SFP+ Optical Interface Board(EC)
unisevtModuleSw-LSXM1CGC2EC3                OBJECT IDENTIFIER ::= { unisevtModuleSwitchType 1639 } -- 2-Port 100GBASE-R Ethernet CFP Optical Interface Board(EC)
unisevtModuleSw-LSXM1TGT24SF3               OBJECT IDENTIFIER ::= { unisevtModuleSwitchType 1640 } -- 24-Port 10GBASE-T Ethernet Electrical Interface Board(RJ45)(SF)
unisevtModuleSw-LSXM1TGS16SF3               OBJECT IDENTIFIER ::= { unisevtModuleSwitchType 1641 } -- 16-Port 10GE Optical Interface Board(SFP+,LC)(SF)
unisevtModuleSw-LSXM1QGS12SG3               OBJECT IDENTIFIER ::= { unisevtModuleSwitchType 1642 } -- 12-Port 40GBASE-R Ethernet QSFP+ Optical Interface Board(SG)
unisevtModuleSw-LSXM1TGS48SG3               OBJECT IDENTIFIER ::= { unisevtModuleSwitchType 1643 } -- 48-Port 10GBASE-R Ethernet SFP+ Optical Interface Board(SG)
unisevtModuleSw-LSQM1FAB04B3                OBJECT IDENTIFIER ::= { unisevtModuleSwitchType 1644 } -- Switching Fabric Module
unisevtModuleSw-LSQM1FAB08B3                OBJECT IDENTIFIER ::= { unisevtModuleSwitchType 1645 } -- Switching Fabric Module
unisevtModuleSw-LSQM1FAB12B3                OBJECT IDENTIFIER ::= { unisevtModuleSwitchType 1646 } -- Switching Fabric Module
unisevtModuleSw-LSXM1SFF08A0                OBJECT IDENTIFIER ::= { unisevtModuleSwitchType 1647 } -- Switching Fabric Board
unisevtModuleSw-LSXM1SFF08A1                OBJECT IDENTIFIER ::= { unisevtModuleSwitchType 1648 } -- Switching Fabric Board
unisevtModuleSw-LSXM1FWDF1                  OBJECT IDENTIFIER ::= { unisevtModuleSwitchType 1649 } -- FW IV Next Generation Firewall Module
unisevtModuleSw-LSQM1PT8TSSC0               OBJECT IDENTIFIER ::= { unisevtModuleSwitchType 1650 } -- 8-Port 1G EPON OLT Optical Interface(SFP,SC)+2-Port 10GE Optical Interface Board(SFP+,LC)(SC)
unisevtModuleSw-LSQM1PT24TSSC0              OBJECT IDENTIFIER ::= { unisevtModuleSwitchType 1651 } -- 24-Port 1G EPON OLT Optical Interface(SFP,SC)+2-Port 10GE Optical Interface Board(SFP+,LC)(SC)
unisevtModuleSw-LSQM1TGS12EC0               OBJECT IDENTIFIER ::= { unisevtModuleSwitchType 1652 } -- 12-Port 10GBASE-R Ethernet SFP+ Optical Interface Board(EC)
unisevtModuleSw-LSX1M1CGQ32TB1              OBJECT IDENTIFIER ::= { unisevtModuleSwitchType 1653 } -- 32-Port 100GBASE Ethernet Optical Interface Board(QSFP28),Monolithic,LF
unisevtModuleSw-LSX1M1CGQ48TB1              OBJECT IDENTIFIER ::= { unisevtModuleSwitchType 1654 } -- 48-Port 100GBASE Ethernet Optical Interface Board(QSFP28),Monolithic
unisevtModuleSw-LSXM1QGS48TB1               OBJECT IDENTIFIER ::= { unisevtModuleSwitchType 1655 } -- 48-Port 40GBASE Ethernet Optical Interface Board(QSFP+),Monolithic
unisevtModuleSw-LSXM1SRT08E1                OBJECT IDENTIFIER ::= { unisevtModuleSwitchType 1656 } -- Switch Fabric Board
unisevtModuleSw-LSXM1SRT16E1                OBJECT IDENTIFIER ::= { unisevtModuleSwitchType 1657 } -- Switch Fabric Board
unisevtModuleSw-LSXM1SRT02E1                OBJECT IDENTIFIER ::= { unisevtModuleSwitchType 1658 } -- Switch Fabric Board
unisevtModuleSw-LSXM1SUP02B1                OBJECT IDENTIFIER ::= { unisevtModuleSwitchType 1659 } -- Supervisor Engine Module
unisevtModuleSw-LSUM1SUPC0                  OBJECT IDENTIFIER ::= { unisevtModuleSwitchType 1660 } -- Supervisor Engine Board
unisevtModuleSw-LSUM1SUPC3                  OBJECT IDENTIFIER ::= { unisevtModuleSwitchType 1661 } -- Supervisor Engine Board
unisevtModuleSw-LSXM1SUPC3                  OBJECT IDENTIFIER ::= { unisevtModuleSwitchType 1662 } -- Supervisor Engine Board
unisevtModuleSw-LSQM1GP44TSSE0              OBJECT IDENTIFIER ::= { unisevtModuleSwitchType 1663 } -- 44-Port GE Optical Interface(SFP,LC)+4-Port 10GE Optical Interface Board(SFP+,LC)(SC)
unisevtModuleSw-LSQM1GP24TSSE0              OBJECT IDENTIFIER ::= { unisevtModuleSwitchType 1664 } -- 24-Port GE Optical Interface(SFP,LC)+4-Port 10GE Optical Interface Board(SFP+,LC)(SC)
unisevtModuleSw-LSQM1GT48SE0                OBJECT IDENTIFIER ::= { unisevtModuleSwitchType 1665 } -- 48-Port 1000Base-T Gigabit Ethernet Interface Board(RJ45)(SC)
unisevtModuleSw-LSQM1GV48SE0                OBJECT IDENTIFIER ::= { unisevtModuleSwitchType 1666 } -- 48-Port 1000Base-T Gigabit Ethernet Interface Board(RJ45)(SC)-POE
unisevtModuleSw-LSXM1QGS12FX0               OBJECT IDENTIFIER ::= { unisevtModuleSwitchType 1667 } -- 12-Port 40GBASE Ethernet Optical Interface Module(QSFP+)(FX)
unisevtModuleSw-LSXM3QGS24FE1               OBJECT IDENTIFIER ::= { unisevtModuleSwitchType 1668 } -- 24-Port 40GBASE Ethernet Optical Interface Module(QSFP+)(FE)
unisevtModuleSw-LSXM3QGS24FX1               OBJECT IDENTIFIER ::= { unisevtModuleSwitchType 1669 } -- 24-Port 40GBASE Ethernet Optical Interface Module(QSFP+)(FX)
unisevtModuleSw-LSXM3QGS36FX1               OBJECT IDENTIFIER ::= { unisevtModuleSwitchType 1670 } -- 36-Port 40GBASE Ethernet Optical Interface Module(QSFP+)(FX)
unisevtModuleSw-LSXM3TGS48FE1               OBJECT IDENTIFIER ::= { unisevtModuleSwitchType 1671 } -- 48-Port 10GBASE Ethernet Optical Interface Module(SFP+,LC)(FX)
unisevtModuleSw-LSXM3TGS48FX1               OBJECT IDENTIFIER ::= { unisevtModuleSwitchType 1672 } -- 48-Port 10GBASE Ethernet Optical Interface Module(SFP+,LC)(FX)
unisevtModuleSw-LSXM2TGS48FX1               OBJECT IDENTIFIER ::= { unisevtModuleSwitchType 1673 } -- 48-Port 10GBASE Ethernet Optical Interface Module(SFP+,LC)(FX)
unisevtModuleSw-LSQM1MPU06B0                OBJECT IDENTIFIER ::= { unisevtModuleSwitchType 1674 } -- Supervisor Engine Board
unisevtModuleSw-LSQM1MPU10C0                OBJECT IDENTIFIER ::= { unisevtModuleSwitchType 1675 } -- Supervisor Engine Board
unisevtModuleSw-LSQM1FAB06C0                OBJECT IDENTIFIER ::= { unisevtModuleSwitchType 1676 } -- Switching Fabric Module
unisevtModuleSw-LSQM1FAB10C0                OBJECT IDENTIFIER ::= { unisevtModuleSwitchType 1677 } -- Switching Fabric Module
unisevtModuleSw-LSQM1QGS12SG0               OBJECT IDENTIFIER ::= { unisevtModuleSwitchType 1678 } -- 12-Port 40GBASE-R Ethernet QSFP+ Optical Interface Board(SG)
unisevtModuleSw-LSQM1TGS48SG0               OBJECT IDENTIFIER ::= { unisevtModuleSwitchType 1679 } -- 48-Port 10GBASE-R Ethernet SFP+ Optical Interface Board(SG)
unisevtModuleSw-LSQM1TGT24SF0               OBJECT IDENTIFIER ::= { unisevtModuleSwitchType 1680 } -- 24-Port 10GBASE-T Ethernet Electrical Interface Board(RJ45)(SF)
unisevtModuleSw-LSQM1QGS8A0                 OBJECT IDENTIFIER ::= { unisevtModuleSwitchType 1681 } -- 8-Port QSFP+ Module
unisevtModuleSw-LSQM1TGS24QSM0              OBJECT IDENTIFIER ::= { unisevtModuleSwitchType 1682 } -- 24-Port SFP+ and 2-Port QSFP+ Module
unisevtModuleSw-LSQM1TGT24QSM0              OBJECT IDENTIFIER ::= { unisevtModuleSwitchType 1683 } -- 24-Port 10G BASE-T and 2-Port QSFP+ Module
unisevtModuleSw-LSQM1TGS24QSA0              OBJECT IDENTIFIER ::= { unisevtModuleSwitchType 1684 } -- 24-Port SFP+ and 2-Port QSFP+ Module
unisevtModuleSw-LSUM1FWCEAB0                OBJECT IDENTIFIER ::= { unisevtModuleSwitchType 1685 } -- Firewall Board
unisevtModuleSw-LSQM2GP24TSSA0              OBJECT IDENTIFIER ::= { unisevtModuleSwitchType 1686 } -- 24-Port GE Optical Interface(SFP,LC)+4-Port 10GE Optical Interface Board(SFP+,LC)(SA)
unisevtModuleSw-LSQM2GT48SA0                OBJECT IDENTIFIER ::= { unisevtModuleSwitchType 1687 } -- 48-Port 1000Base-T Gigabit Ethernet Interface Board(RJ45)(SA)
unisevtModuleSw-LSQM2GP48SA0                OBJECT IDENTIFIER ::= { unisevtModuleSwitchType 1688 } -- 48-Port 1000BASE-X Ethernet Optical Interface Board(SFP,LC)(SA)
unisevtModuleSw-LSQM2GP24TSSA3              OBJECT IDENTIFIER ::= { unisevtModuleSwitchType 1689 } -- 24-Port GE Optical Interface(SFP,LC)+4-Port 10GE Optical Interface Board(SFP+,LC)(SA)
unisevtModuleSw-LSQM2GT48SA3                OBJECT IDENTIFIER ::= { unisevtModuleSwitchType 1690 } -- 48-Port 1000Base-T Gigabit Ethernet Interface Board(RJ45)(SA)
unisevtModuleSw-LSQM2GP48SA3                OBJECT IDENTIFIER ::= { unisevtModuleSwitchType 1691 } -- 48-Port 1000BASE-X Ethernet Optical Interface Board(SFP,LC)(SA)
unisevtModuleSw-LSUM2GP24TSSA0              OBJECT IDENTIFIER ::= { unisevtModuleSwitchType 1692 } -- 24-Port GE Optical Interface(SFP,LC)+4-Port 10GE Optical Interface Board(SFP+,LC)(SA)
unisevtModuleSw-LSUM2GT48SA0                OBJECT IDENTIFIER ::= { unisevtModuleSwitchType 1693 } -- 48-Port 1000Base-T Gigabit Ethernet Interface Board(RJ45)(SA)
unisevtModuleSw-LSUM2GP48SA0                OBJECT IDENTIFIER ::= { unisevtModuleSwitchType 1694 } -- 48-Port 1000BASE-X Ethernet Optical Interface Board(SFP,LC)(SA)
unisevtModuleSw-LSXM1SUPT1                  OBJECT IDENTIFIER ::= { unisevtModuleSwitchType 1695 } -- Supervisor Engine Module
unisevtModuleSw-LSXM1SUP02T1                OBJECT IDENTIFIER ::= { unisevtModuleSwitchType 1696 } -- Supervisor Engine Module
unisevtModuleSw-LSXM1SFF16B0                OBJECT IDENTIFIER ::= { unisevtModuleSwitchType 1697 } -- Switch Fabric Board
unisevtModuleSw-LSXM4TGS48FX1               OBJECT IDENTIFIER ::= { unisevtModuleSwitchType 1698 } -- 48-Port 10GBASE Ethernet Optical Interface Module(SFP+,LC)(FX)
unisevtModuleSw-LSXM4QGS24FX1               OBJECT IDENTIFIER ::= { unisevtModuleSwitchType 1699 } -- 24-Port 40GBASE Ethernet Optical Interface Module(QSFP+)(FX)
unisevtModuleSw-LSXM1TGS48FD1               OBJECT IDENTIFIER ::= { unisevtModuleSwitchType 1700 } -- 48-Port 10GBASE Ethernet Optical Interface Module(SFP+,LC)(FD)
unisevtModuleSw-LSXM1QGS24FD1               OBJECT IDENTIFIER ::= { unisevtModuleSwitchType 1701 } -- 24-Port 40GBASE Ethernet Optical Interface Module(QSFP+)(FD)
unisevtModuleSw-LSXM2QGS24FX1               OBJECT IDENTIFIER ::= { unisevtModuleSwitchType 1702 } -- 24-Port 40GBASE Ethernet Optical Interface Module(QSFP+)(FX)
unisevtModuleSw-LSXM1TGS48FD0               OBJECT IDENTIFIER ::= { unisevtModuleSwitchType 1703 } -- 48-Port 10GBASE Ethernet Optical Interface Module(SFP+,LC)
unisevtModuleSw-LSXM1QGS24FD0               OBJECT IDENTIFIER ::= { unisevtModuleSwitchType 1704 } -- 24-Port 40GBASE Ethernet Optical Interface Module(QSFP+)(FD)
unisevtModuleSw-LSXM2TGS48FX0               OBJECT IDENTIFIER ::= { unisevtModuleSwitchType 1705 } -- 48-Port 10GBASE Ethernet Optical Interface Module(SFP+,LC)(FX)
unisevtModuleSw-LSXM2QGS24FX0               OBJECT IDENTIFIER ::= { unisevtModuleSwitchType 1706 } -- 24-Port 40GBASE Ethernet Optical Interface Module(QSFP+)(FX)
unisevtModuleSw-LSXM4TGS48FX0               OBJECT IDENTIFIER ::= { unisevtModuleSwitchType 1707 } -- 48-Port 10GBASE Ethernet Optical Interface Module(SFP+,LC)(FX)
unisevtModuleSw-LSXM4QGS24FX0               OBJECT IDENTIFIER ::= { unisevtModuleSwitchType 1708 } -- 24-Port 40GBASE Ethernet Optical Interface Module(QSFP+)(FX)
unisevtModuleSw-LSXM1TGW48FX1               OBJECT IDENTIFIER ::= { unisevtModuleSwitchType 1709 } -- 48-Port 10GBASE Ethernet WAN Optical Interface Module(SFP+,LC)(FX)
unisevtModuleSw-LSUM1MPU10A0                OBJECT IDENTIFIER ::= { unisevtModuleSwitchType 1710 } -- Supervisor Engine Board
unisevtModuleSw-LSUM1FAB10A0                OBJECT IDENTIFIER ::= { unisevtModuleSwitchType 1711 } -- Switching Fabric Module
unisevtModuleSw-LSUM2TGS32QSSG0             OBJECT IDENTIFIER ::= { unisevtModuleSwitchType 1712 } -- 32-Port 10GBASE-R Ethernet Optical Interface(SFP+,LC)+4-Port 40GBASE-R Ethernet Optical Interface Board(QSFP+,LC)(SG)
unisevtModuleSw-LSUM2QGS12SG0               OBJECT IDENTIFIER ::= { unisevtModuleSwitchType 1713 } -- 12-Port 40GBASE-R Ethernet QSFP+ Optical Interface Board(SG)
unisevtModuleSw-LSUM2TGS48SG0               OBJECT IDENTIFIER ::= { unisevtModuleSwitchType 1714 } -- 48-Port 10GBASE-R Ethernet SFP+ Optical Interface Board(SG)
unisevtModuleSw-LSXM2QGS12SG3               OBJECT IDENTIFIER ::= { unisevtModuleSwitchType 1715 } -- 12-Port 40GBASE-R Ethernet QSFP+ Optical Interface Board(SG)
unisevtModuleSw-LSXM2TGS48SG3               OBJECT IDENTIFIER ::= { unisevtModuleSwitchType 1716 } -- 48-Port 10GBASE-R Ethernet SFP+ Optical Interface Board(SG)
unisevtModuleSw-LSUM1FWDEC0                 OBJECT IDENTIFIER ::= { unisevtModuleSwitchType 1717 } -- Firewall Service Board
unisevtModuleSw-LSQM1FWDSC0                 OBJECT IDENTIFIER ::= { unisevtModuleSwitchType 1718 } -- Firewall Service Board
unisevtModuleSw-LSQM1TGS48RSG0              OBJECT IDENTIFIER ::= { unisevtModuleSwitchType 1719 } -- 48-Port 10GBASE-R Ethernet SFP+ Optical Interface Board(SG)
unisevtModuleSw-LSQM2TGS48XSG0              OBJECT IDENTIFIER ::= { unisevtModuleSwitchType 1720 } -- 48-Port 10GBASE-R Ethernet SFP+ Optical Interface Board(SG)
unisevtModuleSw-LSQM2QGS12XSG0              OBJECT IDENTIFIER ::= { unisevtModuleSwitchType 1721 } -- 12-Port 40GBASE-R Ethernet QSFP+ Optical Interface Board(SG)
unisevtModuleSw-LSQM3GP44TSSC0              OBJECT IDENTIFIER ::= { unisevtModuleSwitchType 1722 } -- 44-Port GE Optical Interface(SFP,LC)+4-Port 10GE Optical Interface Board(SFP+,LC)(SC)
unisevtModuleSw-LSXM1CGQ36HB1               OBJECT IDENTIFIER ::= { unisevtModuleSwitchType 1723 } -- 36-Port 100GBASE Ethernet Optical Interface Module(QSFP28)(HB)
unisevtModuleSw-LSXM1CGQ36HC1               OBJECT IDENTIFIER ::= { unisevtModuleSwitchType 1724 } -- 36-Port 100GBASE Ethernet Optical Interface Module(QSFP28)(HC)
unisevtModuleSw-LSXM1CGQ18QGHB1             OBJECT IDENTIFIER ::= { unisevtModuleSwitchType 1725 } -- 18-Port 100GBASE (QSFP28) + 18-Port 40GBASE Ethernet Optical Interface Module (QSFP+)(HB)
unisevtModuleSw-LSXM1CGQ18QGHC1             OBJECT IDENTIFIER ::= { unisevtModuleSwitchType 1726 } -- 18-Port 100GBASE (QSFP28) + 18-Port 40GBASE Ethernet Optical Interface Module (QSFP+)(HC)
unisevtModuleSw-LSXM1QGS48HB1               OBJECT IDENTIFIER ::= { unisevtModuleSwitchType 1727 } -- 48-Port 40GBASE Ethernet Optical Interface Module(QSFP+)(HB)
unisevtModuleSw-LSXM1QGS48HC1               OBJECT IDENTIFIER ::= { unisevtModuleSwitchType 1728 } -- 48-Port 40GBASE Ethernet Optical Interface Module(QSFP+)(HC)
unisevtModuleSw-LSXM1TGS48C2HB1             OBJECT IDENTIFIER ::= { unisevtModuleSwitchType 1729 } -- 48-Port 10G BASE Ethernet Optical Interface(SFP+,LC)+2-Port 100GBASE Ethernet Optical Interface Module(QSFP28)(HB)
unisevtModuleSw-LSXM1SFH04D1                OBJECT IDENTIFIER ::= { unisevtModuleSwitchType 1730 } -- Switch Fabric Board,Type H(Class D)
unisevtModuleSw-LSXM1SFH08D1                OBJECT IDENTIFIER ::= { unisevtModuleSwitchType 1731 } -- Switch Fabric Board For S12508X-AF,Type D(F2)
unisevtModuleSw-LSXM1SFH12D1                OBJECT IDENTIFIER ::= { unisevtModuleSwitchType 1732 } -- Fabric Module,Type H(Class D)
unisevtModuleSw-LSXM1SFH16C1                OBJECT IDENTIFIER ::= { unisevtModuleSwitchType 1733 } -- Switch Fabric Board,Type H(Class C)
unisevtModuleSw-LSXM1GP48FD0                OBJECT IDENTIFIER ::= { unisevtModuleSwitchType 1737 } -- 48-Port 1000BASE-X Gigabit Ethernet Optical Interface Module(SFP,LC)(FD)
unisevtModuleSw-LSXM1GP48FD1                OBJECT IDENTIFIER ::= { unisevtModuleSwitchType 1738 } -- 48-Port 1000BASE-X Gigabit Ethernet Optical Interface Module(SFP,LC)(FD)
unisevtModuleSw-LSXM1GT48FD0                OBJECT IDENTIFIER ::= { unisevtModuleSwitchType 1739 } -- 48-Port 1000Base-T Gigabit Ethernet Interface Module(RJ45)(FD)
unisevtModuleSw-LSXM1GT48FD1                OBJECT IDENTIFIER ::= { unisevtModuleSwitchType 1740 } -- 48-Port 1000Base-T Gigabit Ethernet Interface Module(RJ45)(FD)
unisevtModuleSw-LSXM1FAB10B0                OBJECT IDENTIFIER ::= { unisevtModuleSwitchType 1741 } -- Switching Fabric Module
unisevtModuleSw-LSUM1MPU10A3                OBJECT IDENTIFIER ::= { unisevtModuleSwitchType 1742 } -- Supervisor Engine Board
unisevtModuleSw-LSUM1FAB10A3                OBJECT IDENTIFIER ::= { unisevtModuleSwitchType 1743 } -- Switching Fabric Module
unisevtModuleSw-LSQM1MPU10A0                OBJECT IDENTIFIER ::= { unisevtModuleSwitchType 1744 } -- Supervisor Engine Board
unisevtModuleSw-LSQM1FAB10A0                OBJECT IDENTIFIER ::= { unisevtModuleSwitchType 1745 } -- Switching Fabric Module
unisevtModuleSw-LSQM2TGS32QSXSG0            OBJECT IDENTIFIER ::= { unisevtModuleSwitchType 1746 } -- 32-Port 10GBASE-R Ethernet Optical Interface(SFP+,LC)+4-Port 40GBASE-R Ethernet Optical Interface Board(QSFP+,LC)(SG)
unisevtModuleSw-LSQM1TGS48RSG3              OBJECT IDENTIFIER ::= { unisevtModuleSwitchType 1747 } -- 48-Port 10GBASE-R Ethernet SFP+ Optical Interface Board(SG)
unisevtModuleSw-LSXM2TGS32QSSG3             OBJECT IDENTIFIER ::= { unisevtModuleSwitchType 1748 } -- 32-Port 10GBASE-R Ethernet Optical Interface(SFP+,LC)+4-Port 40GBASE-R Ethernet Optical Interface Board(QSFP+,LC)(SG)
unisevtModuleSw-LSUM1NSDEC0                 OBJECT IDENTIFIER ::= { unisevtModuleSwitchType 1749 } -- NetStream Service Board
unisevtModuleSw-LSQM1NSDSC0                 OBJECT IDENTIFIER ::= { unisevtModuleSwitchType 1750 } -- NetStream Service Board
unisevtModuleSw-LSQM1QGS4SC0                OBJECT IDENTIFIER ::= { unisevtModuleSwitchType 1751 } -- 4-Port 40G BASE Ethernet Optical Interface Board(QSFP+,MPO)(SC)
unisevtModuleSw-LLSQM2MPUD3                 OBJECT IDENTIFIER ::= { unisevtModuleSwitchType 1752 } -- Supervisor Engine Board
unisevtModuleSw-LLSQM3MPUB3                 OBJECT IDENTIFIER ::= { unisevtModuleSwitchType 1753 } -- Supervisor Engine Board
unisevtModuleSw-LSQM3MPUB4                  OBJECT IDENTIFIER ::= { unisevtModuleSwitchType 1754 } -- Supervisor Engine Board
unisevtModuleSw-LSQM2MPUDS0                 OBJECT IDENTIFIER ::= { unisevtModuleSwitchType 1755 } -- Supervisor Engine Board
unisevtModuleSw-LSQM4GV48SA0                OBJECT IDENTIFIER ::= { unisevtModuleSwitchType 1756 } -- 48-Port 1000Base-T Gigabit Ethernet Interface Board(RJ45)(SA)-POE
unisevtModuleSw-LSQM1WCMX20                 OBJECT IDENTIFIER ::= { unisevtModuleSwitchType 1757 } -- Access Controller Service Board
unisevtModuleSw-LSQM1WCMX40                 OBJECT IDENTIFIER ::= { unisevtModuleSwitchType 1758 } -- Access Controller Service Board
unisevtModuleSw-LSUM1WCMX20RT               OBJECT IDENTIFIER ::= { unisevtModuleSwitchType 1759 } -- Access Controller Service Board
unisevtModuleSw-LSUM1WCMX40RT               OBJECT IDENTIFIER ::= { unisevtModuleSwitchType 1760 } -- Access Controller Service Board
unisevtModuleSw-LSXM1CGQ18QGHB0             OBJECT IDENTIFIER ::= { unisevtModuleSwitchType 1761 } -- 18-PORT 100GBASE Ethernet Optical Interface (QSFP28)/36-PORT 40GBASE Ethernet Optical Interface Module(QSFP+)(HB)
unisevtModuleSw-LSXM1SFH08C0                OBJECT IDENTIFIER ::= { unisevtModuleSwitchType 1762 } -- Fabric Module,Type H(Class C)
unisevtModuleSw-LSXM1SFH08C1                OBJECT IDENTIFIER ::= { unisevtModuleSwitchType 1763 } -- Fabric Module,Type H(Class C)
unisevtModuleSw-LSXM2SFH16C0                OBJECT IDENTIFIER ::= { unisevtModuleSwitchType 1764 } -- Fabric Module,Type H(Class C)
unisevtModuleSw-LSXM2SFH16C1                OBJECT IDENTIFIER ::= { unisevtModuleSwitchType 1765 } -- Fabric Module,Type H(Class C)
unisevtModuleSw-LSXM1NSDF1                  OBJECT IDENTIFIER ::= { unisevtModuleSwitchType 1766 } -- SecBlade IV NetStream Module
unisevtModuleSw-LSUM2TGS48SG3               OBJECT IDENTIFIER ::= { unisevtModuleSwitchType 1767 } -- 48-Port 10GBASE-R Ethernet SFP+ Optical Interface Board(SG)
unisevtModuleSw-DS-3E7602-MPU               OBJECT IDENTIFIER ::= { unisevtModuleSwitchType 1768 } -- Supervisor Engine Board
unisevtModuleSw-DS-3E7606-MPU               OBJECT IDENTIFIER ::= { unisevtModuleSwitchType 1769 } -- Supervisor Engine Board
unisevtModuleSw-DS-3E7600-24T4X-SC          OBJECT IDENTIFIER ::= { unisevtModuleSwitchType 1770 } -- 24-Port 1000Base-T Gigabit Ethernet Interface Board(RJ45)+4-Port 10GE Optical Interface Board(SFP+,LC)(SC)
unisevtModuleSw-DS-3E7600-24F4X-SA          OBJECT IDENTIFIER ::= { unisevtModuleSwitchType 1771 } -- 24-Port GE Optical Interface(SFP,LC)+4-Port 10GE Optical Interface Board(SFP+,LC)(SA)
unisevtModuleSw-DS-3E7600-48T-SA            OBJECT IDENTIFIER ::= { unisevtModuleSwitchType 1772 } -- 48-Port 1000Base-T Gigabit Ethernet Interface Board(RJ45)(SA)
unisevtModuleSw-DS-3E7600-48F-SA            OBJECT IDENTIFIER ::= { unisevtModuleSwitchType 1773 } -- 48-Port 1000BASE-X Ethernet Optical Interface Board(SFP,LC)(SA)
unisevtModuleSw-DS-3E7600-24F4X-SC          OBJECT IDENTIFIER ::= { unisevtModuleSwitchType 1774 } -- 24-Port GE Optical Interface(SFP,LC)+4-Port 10GE Optical Interface Board(SFP+,LC)(SC)
unisevtModuleSw-DS-3E7600-44F4X-SC          OBJECT IDENTIFIER ::= { unisevtModuleSwitchType 1775 } -- 44-Port GE Optical Interface(SFP,LC)+4-Port 10GE Optical Interface Board(SFP+,LC)(SC)
unisevtModuleSw-DS-3E7600-48T-SC            OBJECT IDENTIFIER ::= { unisevtModuleSwitchType 1776 } -- 48-Port 1000Base-T Gigabit Ethernet Interface Board(RJ45)(SC)
unisevtModuleSw-DS-3E7600-16X-SC            OBJECT IDENTIFIER ::= { unisevtModuleSwitchType 1777 } -- 16-Port 10GE Optical Interface Board(SFP+,LC)(SF)
unisevtModuleSw-S7602-MPU                   OBJECT IDENTIFIER ::= { unisevtModuleSwitchType 1778 } -- Supervisor Engine Board
unisevtModuleSw-S7606-MPU                   OBJECT IDENTIFIER ::= { unisevtModuleSwitchType 1779 } -- Supervisor Engine Board
unisevtModuleSw-S76-24GT4XFSC               OBJECT IDENTIFIER ::= { unisevtModuleSwitchType 1780 } -- 24-Port 1000Base-T Gigabit Ethernet Interface Board(RJ45)+4-Port 10GE Optical Interface Board(SFP+,LC)(SC)
unisevtModuleSw-S76-24GF4XFSA               OBJECT IDENTIFIER ::= { unisevtModuleSwitchType 1781 } -- 24-Port GE Optical Interface(SFP,LC)+4-Port 10GE Optical Interface Board(SFP+,LC)(SA)
unisevtModuleSw-S76-48GTSA                  OBJECT IDENTIFIER ::= { unisevtModuleSwitchType 1782 } -- 48-Port 1000Base-T Gigabit Ethernet Interface Board(RJ45)(SA)
unisevtModuleSw-S76-48GFSA                  OBJECT IDENTIFIER ::= { unisevtModuleSwitchType 1783 } -- 48-Port 1000BASE-X Ethernet Optical Interface Board(SFP,LC)(SA)
unisevtModuleSw-S76-24GT20GF4XFSC           OBJECT IDENTIFIER ::= { unisevtModuleSwitchType 1784 } -- 24-Port 1000Base-T Gigabit Ethernet Interface Board(RJ45)+20-Port GE Optical Interface(SFP,LC)+4-Port 10GE Optical Interface Board(SFP+,LC)(SC)
unisevtModuleSw-LSXM1TGS48C2HB0             OBJECT IDENTIFIER ::= { unisevtModuleSwitchType 1785 } -- 48-PORT 10GBASE Ethernet Optical Interface (SFP+,LC)+2-PORT 100GBASE Ethernet Optical Interface Module(QSFP28)(HB)
unisevtModuleSw-LSXM1CGQ18QGHC0             OBJECT IDENTIFIER ::= { unisevtModuleSwitchType 1786 } -- 18-PORT 100GBASE Ethernet Optical Interface (QSFP28)/36-PORT 40GBASE Ethernet Optical Interface Module(QSFP+)(HC)
unisevtModuleSw-LSXM1TGS48HB1               OBJECT IDENTIFIER ::= { unisevtModuleSwitchType 1787 } -- 48-Port 10G BASE Ethernet Optical Interface Module(SFP+,LC)(HB)
unisevtModuleSw-LSXM1TGS48HB0               OBJECT IDENTIFIER ::= { unisevtModuleSwitchType 1788 } -- 48-Port 10G BASE Ethernet Optical Interface Module(SFP+,LC)(HB)
unisevtModuleSw-LSQM1CGP24TSSC0             OBJECT IDENTIFIER ::= { unisevtModuleSwitchType 1789 } -- Supervisor Engine Board With 24-Port 1000BASE-X Ethernet SFP Optical Interface+4-Port 10GBASE-R Ethernet SFP+ Optical Interfaces
unisevtModuleSw-LSQM1CGP24TSSA0             OBJECT IDENTIFIER ::= { unisevtModuleSwitchType 1790 } -- Supervisor Engine Board With 24-Port 1000BASE-X Ethernet SFP Optical Interface+4-Port 10GBASE-R Ethernet SFP+ Optical Interfaces
unisevtModuleSw-LSQM1CGT24TSSC0             OBJECT IDENTIFIER ::= { unisevtModuleSwitchType 1791 } -- Supervisor Engine Board With 24-Port 10/100/1000BASE-T Ethernet Interface+4-Port 10GBASE-R Ethernet SFP+ Optical Interfaces
unisevtModuleSw-LSQM1CGT24TSSA0             OBJECT IDENTIFIER ::= { unisevtModuleSwitchType 1792 } -- Supervisor Engine Board With 24-Port 10/100/1000BASE-T Ethernet Interface+4-Port 10GBASE-R Ethernet SFP+ Optical Interfaces
unisevtModuleSw-LSQM2GP24SA0                OBJECT IDENTIFIER ::= { unisevtModuleSwitchType 1793 } -- 24-Port GE Optical Interface(SFP,LC)(SA)
unisevtModuleSw-LSX1SUPH1                   OBJECT IDENTIFIER ::= { unisevtModuleSwitchType 1794 } -- Supervisor Engine Board
unisevtModuleSw-LSX1SUPH0                   OBJECT IDENTIFIER ::= { unisevtModuleSwitchType 1795 } -- Supervisor Engine Board
unisevtModuleSw-LSX1SUP04H1                 OBJECT IDENTIFIER ::= { unisevtModuleSwitchType 1796 } -- Supervisor Engine Board
unisevtModuleSw-LSX1SUP04H0                 OBJECT IDENTIFIER ::= { unisevtModuleSwitchType 1797 } -- Supervisor Engine Board
unisevtModuleSw-LSXM1SFH08D0                OBJECT IDENTIFIER ::= { unisevtModuleSwitchType 1798 } -- Fabric Module,Type H(Class D)
unisevtModuleSw-LSXM1SFH04D0                OBJECT IDENTIFIER ::= { unisevtModuleSwitchType 1799 } -- Fabric Module,Type H(Class D)
--
-- 1800 for united assignment
--
unisevtModuleSw-LSXM1SFH16C0                OBJECT IDENTIFIER ::= { unisevtModuleSwitchType 1800 } -- Fabric Module,Type H(Class C+)
unisevtModuleSw-LSXM1SFH12D0                OBJECT IDENTIFIER ::= { unisevtModuleSwitchType 1801 } -- Fabric Module,Type H(Class D)
unisevtModuleSw-LSXM1QGS48HB0               OBJECT IDENTIFIER ::= { unisevtModuleSwitchType 1802 } -- 48-Port 40GBASE Ethernet Optical Interface Module(QSFP+)(HB)
unisevtModuleSw-LSXM1QGS48HC0               OBJECT IDENTIFIER ::= { unisevtModuleSwitchType 1803 } -- 48-Port 40GBASE Ethernet Optical Interface Module(QSFP+)(HC)
unisevtModuleSw-LSXM1CGQ36HB0               OBJECT IDENTIFIER ::= { unisevtModuleSwitchType 1804 } -- 36-Port 100GBASE Ethernet Optical Interface Module(QSFP28)(HB)
unisevtModuleSw-LSXM1TGS48C2HC0             OBJECT IDENTIFIER ::= { unisevtModuleSwitchType 1805 } -- 48-PORT 10GBASE Ethernet Optical Interface (SFP+,LC)+2-PORT 100GBASE Ethernet Optical Interface Module(QSFP28)(HC)
unisevtModuleSw-LSQM2GP44TSSE0              OBJECT IDENTIFIER ::= { unisevtModuleSwitchType 1806 } -- 44-Port GE Optical Interface(SFP,LC)+4-Port 10GE Optical Interface Board(SFP+,LC)(SE)
unisevtModuleSw-LSQM2GP24TSSA8              OBJECT IDENTIFIER ::= { unisevtModuleSwitchType 1807 } -- 24-Port GE Optical Interface(SFP,LC)+4-Port 10GE Optical Interface Board(SFP+,LC)(SA)
unisevtModuleSw-LSQM2GT48SA8                OBJECT IDENTIFIER ::= { unisevtModuleSwitchType 1808 } -- 48-Port 1000Base-T Gigabit Ethernet Interface Board(RJ45)(SA)
unisevtModuleSw-LSQM2GP48SA8                OBJECT IDENTIFIER ::= { unisevtModuleSwitchType 1809 } -- 48-Port 1000BASE-X Ethernet Optical Interface Board(SFP,LC)(SA)
unisevtModuleSw-EWPXM1CGP24TSSC0            OBJECT IDENTIFIER ::= { unisevtModuleSwitchType 1810 } -- Supervisor Engine Board With 24-Port 1000BASE-X Ethernet SFP Optical Interface+4-Port 10GBASE-R Ethernet SFP+ Optical Interfaces
unisevtModuleSw-EWPXM3MPUB0                 OBJECT IDENTIFIER ::= { unisevtModuleSwitchType 1811 } -- Supervisor Engine Board
unisevtModuleSw-EWPXM2MPUDS0                OBJECT IDENTIFIER ::= { unisevtModuleSwitchType 1812 } -- Supervisor Engine Board
unisevtModuleSw-EWPXM2TGS16SF0              OBJECT IDENTIFIER ::= { unisevtModuleSwitchType 1813 } -- 16-Port 10GE Optical Interface Board(SFP+,LC)(SF)
unisevtModuleSw-EWPXM2GP44TSSC0             OBJECT IDENTIFIER ::= { unisevtModuleSwitchType 1814 } -- 44-Port GE Optical Interface(SFP,LC)+4-Port 10GE Optical Interface Board(SFP+,LC)(SC)
unisevtModuleSw-EWPXM2GP24TSSC0             OBJECT IDENTIFIER ::= { unisevtModuleSwitchType 1815 } -- 24-Port GE Optical Interface(SFP,LC)+4-Port 10GE Optical Interface Board(SFP+,LC)(SC)
unisevtModuleSw-EWPXM1MAC0F                 OBJECT IDENTIFIER ::= { unisevtModuleSwitchType 1816 } -- Access Controller Service Board
unisevtModuleSw-LSQM1CGP24TSSA8             OBJECT IDENTIFIER ::= { unisevtModuleSwitchType 1817 } -- Supervisor Engine Board With 24-Port 1000BASE-X Ethernet SFP Optical Interface+4-Port 10GBASE-R Ethernet SFP+ Optical Interfaces
unisevtModuleSw-LSQM1CGT24TSSA8             OBJECT IDENTIFIER ::= { unisevtModuleSwitchType 1818 } -- Supervisor Engine Board With 24-Port 10/100/1000BASE-T Ethernet Interface+4-Port 10GBASE-R Ethernet SFP+ Optical Interfaces
unisevtModuleSw-LSWM1FWD0                   OBJECT IDENTIFIER ::= { unisevtModuleSwitchType 1819 } -- Firewall Service Board
unisevtModuleSw-LSUM2MPU10C0                OBJECT IDENTIFIER ::= { unisevtModuleSwitchType 1820 } -- Supervisor Engine Board
unisevtModuleSw-LSQM2MPU10C0                OBJECT IDENTIFIER ::= { unisevtModuleSwitchType 1821 } -- Supervisor Engine Board
unisevtModuleSw-LSUM2MPU10C3                OBJECT IDENTIFIER ::= { unisevtModuleSwitchType 1822 } -- Supervisor Engine Board
unisevtModuleSw-LSUM2FAB10C0                OBJECT IDENTIFIER ::= { unisevtModuleSwitchType 1823 } -- Switching Fabric Module
unisevtModuleSw-LSQM2FAB10C0                OBJECT IDENTIFIER ::= { unisevtModuleSwitchType 1824 } -- Switching Fabric Module
unisevtModuleSw-LSUM2FAB10C3                OBJECT IDENTIFIER ::= { unisevtModuleSwitchType 1825 } -- Switching Fabric Module
unisevtModuleSw-LSUM2CQGS12SG0              OBJECT IDENTIFIER ::= { unisevtModuleSwitchType 1826 } -- 12-Port 40GBASE-R QSFP+ or 4-Port 100GBASE-R QSFP28 Optical Interface Board(SG)
unisevtModuleSw-LSXM2CQGS12SG3              OBJECT IDENTIFIER ::= { unisevtModuleSwitchType 1827 } -- 12-Port 40GBASE-R QSFP+ or 4-Port 100GBASE-R QSFP28 Optical Interface Board(SG)
unisevtModuleSw-LSQM2CQGS12XSG0             OBJECT IDENTIFIER ::= { unisevtModuleSwitchType 1828 } -- 12-Port 40GBASE-R QSFP+ or 4-Port 100GBASE-R QSFP28 Optical Interface Board(SG)
unisevtModuleSw-LSQM1CQGS12SG0              OBJECT IDENTIFIER ::= { unisevtModuleSwitchType 1829 } -- 12-Port 40GBASE-R QSFP+ or 4-Port 100GBASE-R QSFP28 Optical Interface Board(SG)
unisevtModuleSw-LSXM1CGQ6QGHB0              OBJECT IDENTIFIER ::= { unisevtModuleSwitchType 1830 } -- 6-Port 100GBASE Ethernet Optical Interface(QSFP28)/12-Port 40GBASE Ethernet Optical Interface Module(QSFP+)(HB)
unisevtModuleSw-LSXM1CGQ6QGHB1              OBJECT IDENTIFIER ::= { unisevtModuleSwitchType 1831 } -- 6-Port 100GBASE Ethernet Optical Interface(QSFP28)/12-Port 40GBASE Ethernet Optical Interface Module(QSFP+)(HB)
unisevtModuleSw-LSXM1CGQ6QGHC0              OBJECT IDENTIFIER ::= { unisevtModuleSwitchType 1832 } -- 6-Port 100GBASE Ethernet Optical Interface(QSFP28)/12-Port 40GBASE Ethernet Optical Interface Module(QSFP+)(HC)
unisevtModuleSw-LSXM1QGS36HB0               OBJECT IDENTIFIER ::= { unisevtModuleSwitchType 1833 } -- 36-Port 40GBASE Ethernet Optical Interface Module(QSFP+)(HB)
unisevtModuleSw-LSXM1QGS36HB1               OBJECT IDENTIFIER ::= { unisevtModuleSwitchType 1834 } -- 36-Port 40GBASE Ethernet Optical Interface Module(QSFP+)(HB)
unisevtModuleSw-LSXM1QGS36HC0               OBJECT IDENTIFIER ::= { unisevtModuleSwitchType 1835 } -- 36-Port 40GBASE Ethernet Optical Interface Module(QSFP+)(HC)
unisevtModuleSw-LSXM1SUPC0                  OBJECT IDENTIFIER ::= { unisevtModuleSwitchType 1836 } -- Supervisor Engine Unit
unisevtModuleSw-LSXM1SUPC1                  OBJECT IDENTIFIER ::= { unisevtModuleSwitchType 1837 } -- Supervisor Engine Unit
unisevtModuleSw-LSXM1SUP04H0                OBJECT IDENTIFIER ::= { unisevtModuleSwitchType 1838 } -- Supervisor Engine Unit
unisevtModuleSw-LSXM1SUP04H1                OBJECT IDENTIFIER ::= { unisevtModuleSwitchType 1839 } -- Supervisor Engine Unit
unisevtModuleSw-LSXM1SUPH0                  OBJECT IDENTIFIER ::= { unisevtModuleSwitchType 1840 } -- Supervisor Engine Unit
unisevtModuleSw-LSXM1SUPH1                  OBJECT IDENTIFIER ::= { unisevtModuleSwitchType 1841 } -- Supervisor Engine Unit
unisevtModuleSw-EWPXM2WCMD0F                OBJECT IDENTIFIER ::= { unisevtModuleSwitchType 1842 } -- 20G Access Controller Module
unisevtModuleSw-LSUM2QGS24RSG0              OBJECT IDENTIFIER ::= { unisevtModuleSwitchType 1843 } -- 24-Port 40GBASE-R Ethernet QSFP+ Optical Interface Board(SG)
unisevtModuleSw-LSQM1QGS24RSG0              OBJECT IDENTIFIER ::= { unisevtModuleSwitchType 1844 } -- 24-Port 40GBASE-R Ethernet QSFP+ Optical Interface Board(SG)
unisevtModuleSw-LSXM2QGS24RSG3              OBJECT IDENTIFIER ::= { unisevtModuleSwitchType 1845 } -- 24-Port 40GBASE-R Ethernet QSFP+ Optical Interface Board(SG)
unisevtModuleSw-LSQM2QGS24RXSG0             OBJECT IDENTIFIER ::= { unisevtModuleSwitchType 1846 } -- 24-Port 40GBASE-R Ethernet QSFP+ Optical Interface Board(SG)
unisevtModuleSw-LSQM2TGS48RSG0              OBJECT IDENTIFIER ::= { unisevtModuleSwitchType 1847 } -- 48-Port 10GBASE-R Ethernet SFP+ Optical Interface Board(SG)
unisevtModuleSw-LSXM1X86SUPE0               OBJECT IDENTIFIER ::= { unisevtModuleSwitchType 1848 } -- Cloud Supervisor Engine Unit
unisevtModuleSw-LSXM1X86SUPE1               OBJECT IDENTIFIER ::= { unisevtModuleSwitchType 1849 } -- Cloud Supervisor Engine Unit
unisevtModuleSw-LSQM1CGS2QSA0               OBJECT IDENTIFIER ::= { unisevtModuleSwitchType 1850 } -- 2-Port 100G Ethernet Optical Interface(QSFP28)+2-Port 40G Ethernet Optical Interface Module(QSFP+)
unisevtModuleSw-LSUM1ACGDEC0                OBJECT IDENTIFIER ::= { unisevtModuleSwitchType 1851 } -- SecBlade IV Application Control Module
unisevtModuleSw-LSQM1ACGDSC0                OBJECT IDENTIFIER ::= { unisevtModuleSwitchType 1852 } -- SecBlade IV Application Control Module
unisevtModuleSw-LSXM1CGQ36HF1               OBJECT IDENTIFIER ::= { unisevtModuleSwitchType 1853 } -- 36-Port 100GBASE Ethernet Optical Interface Module(QSFP28)(HF)
unisevtModuleSw-LSXM1QGS48HF1               OBJECT IDENTIFIER ::= { unisevtModuleSwitchType 1854 } -- 48-Port 40GBASE Ethernet Optical Interface Module(QSFP+)(HF)
unisevtModuleSw-LSXM1CGQ18QGHF1             OBJECT IDENTIFIER ::= { unisevtModuleSwitchType 1855 } -- 18-PORT 100GBASE Ethernet Optical Interface(QSFP28)/36-Port 40GBASE Ethernet Optical Interface Module(QSFP+)(HF)
unisevtModuleSw-LSXM1QGS36HF1               OBJECT IDENTIFIER ::= { unisevtModuleSwitchType 1856 } -- 36-Port 40GBASE Ethernet Optical Interface Module(QSFP+)(HF)
unisevtModuleSw-LSXM1CGQ6QGHF1              OBJECT IDENTIFIER ::= { unisevtModuleSwitchType 1857 } -- 6-Port 100GBASE Ethernet Optical Interface(QSFP28)/12-Port 40GBASE Ethernet Optical Interface Module(QSFP+)(HF)
unisevtModuleSw-LSXM1QGS48HF0               OBJECT IDENTIFIER ::= { unisevtModuleSwitchType 1858 } -- 48-Port 40GBASE Ethernet Optical Interface Module(QSFP+)(HF)
unisevtModuleSw-LSXM1CGQ18QGHF0             OBJECT IDENTIFIER ::= { unisevtModuleSwitchType 1859 } -- 18-PORT 100GBASE Ethernet Optical Interface(QSFP28)/36-Port 40GBASE Ethernet Optical Interface Module(QSFP+)(HF)
unisevtModuleSw-LSXM1CGQ6QGHF0              OBJECT IDENTIFIER ::= { unisevtModuleSwitchType 1860 } -- 6-Port 100GBASE Ethernet Optical Interface(QSFP28)/12-Port 40GBASE Ethernet Optical Interface Module(QSFP+)(HF)
unisevtModuleSw-LSXM1TGS48HF0               OBJECT IDENTIFIER ::= { unisevtModuleSwitchType 1861 } -- 48-Port 10GBASE Ethernet Optical Interface Module(SFP+,LC)(HF)
unisevtModuleSw-LSXM1TGS48HF1               OBJECT IDENTIFIER ::= { unisevtModuleSwitchType 1862 } -- 48-Port 10GBASE Ethernet Optical Interface Module(SFP+,LC)(HF)
unisevtModuleSw-LSQM1GP24FC3                OBJECT IDENTIFIER ::= { unisevtModuleSwitchType 1863 } -- 24-Port 1000BASE-X Optical Interface Board(SFP,LC)
unisevtModuleSw-LSQM1GP24FD3                OBJECT IDENTIFIER ::= { unisevtModuleSwitchType 1864 } -- 24-Port 1000BASE-X Optical Interface Board(SFP,LC)
unisevtModuleSw-LSQM1GP24TSFC3              OBJECT IDENTIFIER ::= { unisevtModuleSwitchType 1865 } -- 24-Port 1000BASE-X Optical Interface(SFP,LC)+4-Port 10GBASE-R Ethernet Optical Interface Board(SFP+,LC)
unisevtModuleSw-LSQM1GP24TSFD3              OBJECT IDENTIFIER ::= { unisevtModuleSwitchType 1866 } -- 24-Port 1000BASE-X Optical Interface(SFP,LC)+4-Port 10GBASE-R Ethernet Optical Interface Board(SFP+,LC)
unisevtModuleSw-LSQM1GP40TS8FD0             OBJECT IDENTIFIER ::= { unisevtModuleSwitchType 1867 } -- 40-Port 1000BASE-X Optical Interface(SFP,LC)+8-Port 10GBASE-R Ethernet Optical Interface Board(SFP+,LC)
unisevtModuleSw-LSQM1GP48FC3                OBJECT IDENTIFIER ::= { unisevtModuleSwitchType 1868 } -- 48-Port 1000BASE-X Optical Interface Board(SFP,LC)
unisevtModuleSw-LSQM1GP48FD0                OBJECT IDENTIFIER ::= { unisevtModuleSwitchType 1869 } -- 48-Port 1000BASE-X Optical Interface Board(SFP,LC)
unisevtModuleSw-LSQM1GP48FD3                OBJECT IDENTIFIER ::= { unisevtModuleSwitchType 1870 } -- 48-Port 1000BASE-X Optical Interface Board(SFP,LC)
unisevtModuleSw-LSQM1GT48FC3                OBJECT IDENTIFIER ::= { unisevtModuleSwitchType 1871 } -- 48-Port 10/100/1000BASE-T Electrical Interface Board(RJ45)
unisevtModuleSw-LSQM1GT48FD0                OBJECT IDENTIFIER ::= { unisevtModuleSwitchType 1872 } -- 48-Port 10/100/1000BASE-T Electrical Interface Board(RJ45)
unisevtModuleSw-LSQM1GT48FD3                OBJECT IDENTIFIER ::= { unisevtModuleSwitchType 1873 } -- 48-Port 10/100/1000BASE-T Electrical Interface Board(RJ45)
unisevtModuleSw-LSQM1TGS24FC3               OBJECT IDENTIFIER ::= { unisevtModuleSwitchType 1874 } -- 24-Port 10GBASE-R Ethernet Optical Interface Board(SFP+,LC)
unisevtModuleSw-LSQM1TGS24FD0               OBJECT IDENTIFIER ::= { unisevtModuleSwitchType 1875 } -- 24-Port 10GBASE-R Ethernet Optical Interface Board(SFP+,LC)
unisevtModuleSw-LSQM1TGS24FD3               OBJECT IDENTIFIER ::= { unisevtModuleSwitchType 1876 } -- 24-Port 10GBASE-R Ethernet Optical Interface Board(SFP+,LC)
unisevtModuleSw-LSQM1TGS24XFD0              OBJECT IDENTIFIER ::= { unisevtModuleSwitchType 1877 } -- 24-Port 10GBASE-R Ethernet Optical Interface Board(SFP+,LC)
unisevtModuleSw-LSQM1TGS48RFE0              OBJECT IDENTIFIER ::= { unisevtModuleSwitchType 1878 } -- 48-Port 10GBASE-R Ethernet Optical Interface Board(SFP+,LC)
unisevtModuleSw-LSQM1TGS8FC3                OBJECT IDENTIFIER ::= { unisevtModuleSwitchType 1879 } -- 8-Port 10GBASE-R Ethernet Optical Interface Board(SFP+,LC)
unisevtModuleSw-LSQM1TGS8FD3                OBJECT IDENTIFIER ::= { unisevtModuleSwitchType 1880 } -- 8-Port 10GBASE-R Ethernet Optical Interface Board(SFP+,LC)
unisevtModuleSw-LSUM1GP40TS8FD0             OBJECT IDENTIFIER ::= { unisevtModuleSwitchType 1881 } -- 40-Port 1000BASE-X Optical Interface(SFP,LC)+8-Port 10GBASE-R Ethernet Optical Interface Board(SFP+,LC)
unisevtModuleSw-LSUM1GP48FD0                OBJECT IDENTIFIER ::= { unisevtModuleSwitchType 1882 } -- 48-Port 1000BASE-X Optical Interface Board(SFP,LC)
unisevtModuleSw-LSUM1GP48FD3                OBJECT IDENTIFIER ::= { unisevtModuleSwitchType 1883 } -- 48-Port 1000BASE-X Optical Interface Board(SFP,LC)
unisevtModuleSw-LSUM1GT48FD0                OBJECT IDENTIFIER ::= { unisevtModuleSwitchType 1884 } -- 48-Port 10/100/1000BASE-T Electrical Interface Board(RJ45)
unisevtModuleSw-LSUM1GT48FD3                OBJECT IDENTIFIER ::= { unisevtModuleSwitchType 1885 } -- 48-Port 10/100/1000BASE-T Electrical Interface Board(RJ45)
unisevtModuleSw-LSUM1TGS24FD0               OBJECT IDENTIFIER ::= { unisevtModuleSwitchType 1886 } -- 24-Port 10GBASE-R Ethernet Optical Interface Board(SFP+,LC)
unisevtModuleSw-LSUM1TGS24FD3               OBJECT IDENTIFIER ::= { unisevtModuleSwitchType 1887 } -- 24-Port 10GBASE-R Ethernet Optical Interface Board(SFP+,LC)
unisevtModuleSw-LSXM1GP40TS8FD0             OBJECT IDENTIFIER ::= { unisevtModuleSwitchType 1888 } -- 40-Port 1000BASE-X Optical Interface(SFP,LC)+8-Port 10GBASE-R Ethernet Optical Interface Board(SFP+,LC)
unisevtModuleSw-LSXM1GT48FD3                OBJECT IDENTIFIER ::= { unisevtModuleSwitchType 1889 } -- 48-Port 10/100/1000BASE-T Electrical Interface Board(RJ45)
unisevtModuleSw-LSXM1TGS24FD3               OBJECT IDENTIFIER ::= { unisevtModuleSwitchType 1890 } -- 24-Port 10GBASE-R Ethernet Optical Interface Board(SFP+,LC)
unisevtModuleSw-LSQM1MPUS10C3               OBJECT IDENTIFIER ::= { unisevtModuleSwitchType 1891 } -- Supervisor Engine Board
unisevtModuleSw-LSQM1MPUSA3                 OBJECT IDENTIFIER ::= { unisevtModuleSwitchType 1892 } -- Supervisor Engine Board
unisevtModuleSw-LSQM2SUPA3                  OBJECT IDENTIFIER ::= { unisevtModuleSwitchType 1893 } -- Supervisor Engine Board
unisevtModuleSw-LSXM1SFH16E1                OBJECT IDENTIFIER ::= { unisevtModuleSwitchType 1894 } -- S12516X-AF Fabric Module,Type H(Class E)
unisevtModuleSw-LSXM1SFH16E0                OBJECT IDENTIFIER ::= { unisevtModuleSwitchType 1895 } -- S12516X-AF Fabric Module,Type H(Class E)
unisevtModuleSw-LSXM1GP40TS8FD3             OBJECT IDENTIFIER ::= { unisevtModuleSwitchType 1896 } -- 40-Port 1000BASE-X Optical Interface(SFP,LC)+8-Port 10GBASE-R Ethernet Optical Interface Board(SFP+,LC)
unisevtModuleSw-LSQM1MPUS10C0               OBJECT IDENTIFIER ::= { unisevtModuleSwitchType 1897 } -- Supervisor Engine Board
unisevtModuleSw-LSQM1MPUSA0                 OBJECT IDENTIFIER ::= { unisevtModuleSwitchType 1898 } -- Supervisor Engine Board
unisevtModuleSw-LSQM2SUPA0                  OBJECT IDENTIFIER ::= { unisevtModuleSwitchType 1899 } -- Supervisor Engine Board
unisevtModuleSw-LSQM1TGS16FC3               OBJECT IDENTIFIER ::= { unisevtModuleSwitchType 1900 } -- 16-Port 10GBASE-R Ethernet SFP+ Optical Interface Board(FC)
unisevtModuleSw-LSQM1TGS16FD0               OBJECT IDENTIFIER ::= { unisevtModuleSwitchType 1901 } -- 16-Port 10GBASE-R Ethernet SFP+ Optical Interface Board(FD)
unisevtModuleSw-LSQM1TGS16FD3               OBJECT IDENTIFIER ::= { unisevtModuleSwitchType 1902 } -- 16-Port 10GBASE-R Ethernet SFP+ Optical Interface Board(FD)
unisevtModuleSw-LSQM2TGS48SG0               OBJECT IDENTIFIER ::= { unisevtModuleSwitchType 1903 } -- 48-Port 10GBASE-R Ethernet SFP+ Optical Interface Board(SG)
unisevtModuleSw-LSQM2TGS48SG3               OBJECT IDENTIFIER ::= { unisevtModuleSwitchType 1904 } -- 48-Port 10GBASE-R Ethernet SFP+ Optical Interface Board(SG)
unisevtModuleSw-LSXM1CGQ48HB1               OBJECT IDENTIFIER ::= { unisevtModuleSwitchType 1905 } -- 48-Port 100GBASE Ethernet Optical Interface Module(QSFP+)(HB)
unisevtModuleSw-LSQM1MPUS06A8               OBJECT IDENTIFIER ::= { unisevtModuleSwitchType 1906 } -- Supervisor Engine Board
unisevtModuleSw-LSQM1TGS16FD8               OBJECT IDENTIFIER ::= { unisevtModuleSwitchType 1907 } -- 16-Port 10GBASE-R Ethernet SFP+ Optical Interface Board(FD)
unisevtModuleSw-LSXM1SFH08E1                OBJECT IDENTIFIER ::= { unisevtModuleSwitchType 1908 } -- Fabric Module,Type H(Class E)

unisevtModuleSw-LSXM1SFH08CC0               OBJECT IDENTIFIER ::= { unisevtModuleSwitchType 1909 } -- S12508M-AF Fabric Module,Type H(Class C)
unisevtModuleSw-LSXM1SUP08C0                OBJECT IDENTIFIER ::= { unisevtModuleSwitchType 1910 } -- S12508M-AF Supervisor Engine Unit
unisevtModuleSw-LSUM2FAB04D0                OBJECT IDENTIFIER ::= { unisevtModuleSwitchType 1911 } -- Switching Fabric Module
unisevtModuleSw-LSUM2FAB04D3                OBJECT IDENTIFIER ::= { unisevtModuleSwitchType 1912 } -- Switching Fabric Module
unisevtModuleSw-LSXM2FAB04D3                OBJECT IDENTIFIER ::= { unisevtModuleSwitchType 1913 } -- Switching Fabric Module
unisevtModuleSw-LSUM2FAB04B0                OBJECT IDENTIFIER ::= { unisevtModuleSwitchType 1914 } -- Switching Fabric Module
unisevtModuleSw-LSUM2FAB04B3                OBJECT IDENTIFIER ::= { unisevtModuleSwitchType 1915 } -- Switching Fabric Module
unisevtModuleSw-LSUM2FAB08D0                OBJECT IDENTIFIER ::= { unisevtModuleSwitchType 1916 } -- Switching Fabric Module
unisevtModuleSw-LSUM2FAB08D3                OBJECT IDENTIFIER ::= { unisevtModuleSwitchType 1917 } -- Switching Fabric Module
unisevtModuleSw-LSXM2FAB08D3                OBJECT IDENTIFIER ::= { unisevtModuleSwitchType 1918 } -- Switching Fabric Module
unisevtModuleSw-LSUM2FAB08B0                OBJECT IDENTIFIER ::= { unisevtModuleSwitchType 1919 } -- Switching Fabric Module
unisevtModuleSw-LSUM2FAB08B3                OBJECT IDENTIFIER ::= { unisevtModuleSwitchType 1920 } -- Switching Fabric Module
unisevtModuleSw-LSUM2FAB12D0                OBJECT IDENTIFIER ::= { unisevtModuleSwitchType 1921 } -- Switching Fabric Module
unisevtModuleSw-LSUM2FAB12D3                OBJECT IDENTIFIER ::= { unisevtModuleSwitchType 1922 } -- Switching Fabric Module
unisevtModuleSw-LSXM2FAB12D3                OBJECT IDENTIFIER ::= { unisevtModuleSwitchType 1923 } -- Switching Fabric Module
unisevtModuleSw-LSUM2FAB12B0                OBJECT IDENTIFIER ::= { unisevtModuleSwitchType 1924 } -- Switching Fabric Module
unisevtModuleSw-LSUM2FAB12B3                OBJECT IDENTIFIER ::= { unisevtModuleSwitchType 1925 } -- Switching Fabric Module
unisevtModuleSw-LSQM1CGS2FE0                OBJECT IDENTIFIER ::= { unisevtModuleSwitchType 1926 } -- 2-Port 100GBASE-R Ethernet QSFP28 Optical Interface Board(FE)
unisevtModuleSw-LSQM1CGS2FE3                OBJECT IDENTIFIER ::= { unisevtModuleSwitchType 1927 } -- 2-Port 100GBASE-R Ethernet QSFP28 Optical Interface Board(FE)
unisevtModuleSw-LSQM1CGS2XFE0               OBJECT IDENTIFIER ::= { unisevtModuleSwitchType 1928 } -- 2-Port 100GBASE-R Ethernet QSFP28 Optical Interface Board(FE)
unisevtModuleSw-LSUM1CGS2FE0                OBJECT IDENTIFIER ::= { unisevtModuleSwitchType 1929 } -- 2-Port 100GBASE-R Ethernet QSFP28 Optical Interface Board(FE)
unisevtModuleSw-LSUM1CGS2FE3                OBJECT IDENTIFIER ::= { unisevtModuleSwitchType 1930 } -- 2-Port 100GBASE-R Ethernet QSFP28 Optical Interface Board(FE)
unisevtModuleSw-LSXM1CGS2FE3                OBJECT IDENTIFIER ::= { unisevtModuleSwitchType 1931 } -- 2-Port 100GBASE-R Ethernet QSFP28 Optical Interface Board(FE)
unisevtModuleSw-LSUM1TGS16FD0               OBJECT IDENTIFIER ::= { unisevtModuleSwitchType 1932 } -- 16-Port 10GBASE-R Ethernet SFP+ Optical Interface Board(FD)
unisevtModuleSw-LSUM1TGS16FD3               OBJECT IDENTIFIER ::= { unisevtModuleSwitchType 1933 } -- 16-Port 10GBASE-R Ethernet SFP+ Optical Interface Board(FD)
unisevtModuleSw-LSQM1TGS16XFD0              OBJECT IDENTIFIER ::= { unisevtModuleSwitchType 1934 } -- 16-Port 10GBASE-R Ethernet SFP+ Optical Interface Board(FD)
unisevtModuleSw-LSQM1GP40TS8FC3             OBJECT IDENTIFIER ::= { unisevtModuleSwitchType 1935 } -- 40-Port 1000BASE-X Optical Interface(SFP,LC)+8-Port 10GBASE-R Ethernet Optical Interface Board(SFP+,LC)
unisevtModuleSw-S76-16XFSF                  OBJECT IDENTIFIER ::= { unisevtModuleSwitchType 1936 } -- 16-Port 10GE Optical Interface Board(SFP+,LC)(SF)
unisevtModuleSw-S76-24EP2XFSC-OLT           OBJECT IDENTIFIER ::= { unisevtModuleSwitchType 1937 } -- 24-Port 1G EPON OLT Optical Interface(SFP,SC)+2-Port 10GE Optical Interface Board(SFP+,LC)(SC)
unisevtModuleSw-DS-3E7600-24T20F4X-SC       OBJECT IDENTIFIER ::= { unisevtModuleSwitchType 1938 } -- 24-Port 1000Base-T Gigabit Ethernet Interface Board(RJ45)+20-Port GE Optical Interface(SFP,LC)+4-Port 10GE Optical Interface Board(SFP+,LC)(SC)
unisevtModuleSw-LSUM1FAB04E0                OBJECT IDENTIFIER ::= { unisevtModuleSwitchType 1939 } -- Switching Fabric Module
unisevtModuleSw-LSUM1FAB08E0                OBJECT IDENTIFIER ::= { unisevtModuleSwitchType 1940 } -- Switching Fabric Module
unisevtModuleSw-LSUM1FAB12E0                OBJECT IDENTIFIER ::= { unisevtModuleSwitchType 1941 } -- Switching Fabric Module
unisevtModuleSw-LSXM1CGQ8FX1                OBJECT IDENTIFIER ::= { unisevtModuleSwitchType 1942 } -- 8-Port 100GBASE Ethernet Optical Interface Module(QSFP28)(FX)
unisevtModuleSw-LSQM1IPSDSC0                OBJECT IDENTIFIER ::= { unisevtModuleSwitchType 1943 } -- SecBlade IV Intrusion Prevention System Module
unisevtModuleSw-LSQM2ACGDSC0                OBJECT IDENTIFIER ::= { unisevtModuleSwitchType 1944 } -- SecBlade IV Application Control Module
unisevtModuleSw-LSQM1ADEDSC0                OBJECT IDENTIFIER ::= { unisevtModuleSwitchType 1945 } -- SecBlade IV Load Balancing Module
unisevtModuleSw-LSWM1ADED0                  OBJECT IDENTIFIER ::= { unisevtModuleSwitchType 1946 } -- SecBlade IV Load Balancing Card
unisevtModuleSw-LSWM1IPSD0                  OBJECT IDENTIFIER ::= { unisevtModuleSwitchType 1947 } -- SecBlade IV Intrusion Prevention System Card
unisevtModuleSw-LSQM1GP40TS8FD3             OBJECT IDENTIFIER ::= { unisevtModuleSwitchType 1948 } -- 40-Port 1000BASE-X Optical Interface(SFP,LC)+8-Port 10GBASE-R Ethernet Optical Interface Board(SFP+,LC)
unisevtModuleSw-LSUM1SUPXD0                 OBJECT IDENTIFIER ::= { unisevtModuleSwitchType 1949 } -- Supervisor Engine Board
unisevtModuleSw-LSUM1CQGS32SF0              OBJECT IDENTIFIER ::= { unisevtModuleSwitchType 1950 } -- 32-Port 40GBASE-R QSFP+ or 16-Port 100GBASE-R QSFP28 Optical Interface Board(SF)
unisevtModuleSw-LSUM1TGS48XSG0              OBJECT IDENTIFIER ::= { unisevtModuleSwitchType 1951 } -- 48-Port 10GBASE-R Ethernet SFP+ Optical Interface Board(SG)
unisevtModuleSw-LSUM1FAB08XE0               OBJECT IDENTIFIER ::= { unisevtModuleSwitchType 1952 } -- Switching Fabric Module
unisevtModuleSw-LSUM1FAB16XD0               OBJECT IDENTIFIER ::= { unisevtModuleSwitchType 1953 } -- Switching Fabric Module
unisevtModuleSw-LSXM1SFH02E0                OBJECT IDENTIFIER ::= { unisevtModuleSwitchType 1954 } -- Switching Fabric Module
unisevtModuleSw-LSXM1SFH02E1                OBJECT IDENTIFIER ::= { unisevtModuleSwitchType 1955 } -- Switching Fabric Module
unisevtModuleSw-LSXM1SFH12C0                OBJECT IDENTIFIER ::= { unisevtModuleSwitchType 1956 } -- Fabric Module,Type H(Class C)
unisevtModuleSw-LSXM1SFH12C1                OBJECT IDENTIFIER ::= { unisevtModuleSwitchType 1957 } -- Fabric Module,Type H(Class C)
unisevtModuleSw-LSUM1CQGS12XSG0             OBJECT IDENTIFIER ::= { unisevtModuleSwitchType 1958 } -- 12-Port 40GBASE-R QSFP+ or 4-Port 100GBASE-R QSFP28 Optical Interface Board(SG)
unisevtModuleSw-LSQM1CTGS24QSFD0            OBJECT IDENTIFIER ::= { unisevtModuleSwitchType 1959 } -- Supervisor Engine Board With 24-Port 10GBASE-R SFP+ Optical Interface+2-Port 40GBASE-R QSFP+ Optical Interfaces or 1-Port 100GBASE-R QSFP28 Optical Interfaces
unisevtModuleSw-LSQM1TGS24QSFD0             OBJECT IDENTIFIER ::= { unisevtModuleSwitchType 1960 } -- 24-Port 10GBASE-R Optical Interface(SFP+,LC)+2-Port 40GBASE-R Optical Interface Board(QSFP+) or 1-Port 100GBASE-R Optical Interface Board(QSFP28)
unisevtModuleSw-LSUM1WBCZ720RT              OBJECT IDENTIFIER ::= { unisevtModuleSwitchType 1961 } -- Access Controller Service Board
unisevtModuleSw-LSQM1WBCZ720                OBJECT IDENTIFIER ::= { unisevtModuleSwitchType 1962 } -- Access Controller Service Board
unisevtModuleSw-DS-3E7610X-MPU              OBJECT IDENTIFIER ::= { unisevtModuleSwitchType 1963 } -- Supervisor Engine Board
unisevtModuleSw-DS-3E7610X-CLOS             OBJECT IDENTIFIER ::= { unisevtModuleSwitchType 1964 } -- Switching Fabric Module
unisevtModuleSw-DS-3E7610X-32X4QX-SF        OBJECT IDENTIFIER ::= { unisevtModuleSwitchType 1965 } -- 32-Port 10GBASE-R Ethernet Optical Interface(SFP+,LC)+4-Port 40GBASE-R Ethernet Optical Interface Board(QSFP+,LC)(SF)
unisevtModuleSw-DS-3E7610X-16X-SF           OBJECT IDENTIFIER ::= { unisevtModuleSwitchType 1966 } -- 16-Port 10GBASE-R Ethernet SFP+ Optical
unisevtModuleSw-DS-3E7610X-44F4X-SE         OBJECT IDENTIFIER ::= { unisevtModuleSwitchType 1967 } -- 44-Port GE Optical Interface(SFP,LC)+4-Port 10GE Optical Interface Board(SFP+,LC)(SE)
unisevtModuleSw-DS-3E7610X-48T-SE           OBJECT IDENTIFIER ::= { unisevtModuleSwitchType 1968 } -- 48-Port 1000Base-T Gigabit Ethernet Interface Board(RJ45)(SE)
unisevtModuleSw-LSQM2GT24PTSSC8             OBJECT IDENTIFIER ::= { unisevtModuleSwitchType 1969 } -- 24-Port 1000Base-T Gigabit Ethernet Interface Board(RJ45)+20-Port GE Optical Interface(SFP,LC)+4-Port 10GE Optical Interface Board(SFP+,LC)(SC)
unisevtModuleSw-LSQM1CGP24TSSC8             OBJECT IDENTIFIER ::= { unisevtModuleSwitchType 1970 } -- Supervisor Engine Board With 24-Port 1000BASE-X Ethernet SFP Optical Interface+4-Port 10GBASE-R Ethernet SFP+ Optical Interfaces
unisevtModuleSw-LSQM1CGT24TSSC8             OBJECT IDENTIFIER ::= { unisevtModuleSwitchType 1971 } -- Supervisor Engine Board With 24-Port 10/100/1000BASE-T Ethernet Interface+4-Port 10GBASE-R Ethernet SFP+ Optical Interfaces
unisevtModuleSw-LSQM1MPUS06B8               OBJECT IDENTIFIER ::= { unisevtModuleSwitchType 1972 } -- Supervisor Engine Board
unisevtModuleSw-LSVM1MPUB1                  OBJECT IDENTIFIER ::= { unisevtModuleSwitchType 1973 } -- Supervisor Engine Unit
unisevtModuleSw-LSXM1TGS24QGMODHB0          OBJECT IDENTIFIER ::= { unisevtModuleSwitchType 1974 } -- 24-Port 10GBASE Ethernet Optical Interface(SFP+,LC)+4-Port 40GBASE Ethernet Optical Interface Module(QSFP+)(HB),With 1 Expansion Slot
unisevtModuleSw-LSXM1TGS24QGMODHB1          OBJECT IDENTIFIER ::= { unisevtModuleSwitchType 1975 } -- 24-Port 10GBASE Ethernet Optical Interface(SFP+,LC)+4-Port 40GBASE Ethernet Optical Interface Module(QSFP+)(HB),With 1 Expansion Slot
unisevtModuleSw-LSXM1TGS48QGHA0             OBJECT IDENTIFIER ::= { unisevtModuleSwitchType 1976 } -- 48-Port 10GBASE Ethernet Optical Interface(SFP+,LC)+4-Port 40GBASE Ethernet Optical Interface Module(QSFP+)(HA)
unisevtModuleSw-LSXM1TGS48QGHA1             OBJECT IDENTIFIER ::= { unisevtModuleSwitchType 1977 } -- 48-Port 10GBASE Ethernet Optical Interface(SFP+,LC)+4-Port 40GBASE Ethernet Optical Interface Module(QSFP+)(HA)
unisevtModuleSw-LSXM1CGC2A0                 OBJECT IDENTIFIER ::= { unisevtModuleSwitchType 1978 } -- 2-Ports 100G CFP Ethernet Optical Interface Module(CFP)
unisevtModuleSw-LSXM1CGC2A1                 OBJECT IDENTIFIER ::= { unisevtModuleSwitchType 1979 } -- 2-Ports 100G CFP Ethernet Optical Interface Module(CFP)
unisevtModuleSw-LSQM2FWDSC0                 OBJECT IDENTIFIER ::= { unisevtModuleSwitchType 1980 } -- Firewall Service Board
unisevtModuleSw-LSQM1XPT12TSFD0             OBJECT IDENTIFIER ::= { unisevtModuleSwitchType 1981 } -- 12-Port 10/1GBASE EPON OLT Optical Interface(XFP,LC)+8-Port 10GBASE-R Ethernet Optical Interface Board(SFP+,LC)
unisevtModuleSw-LSXM1QGS24HB0               OBJECT IDENTIFIER ::= { unisevtModuleSwitchType 1982 } -- 24-Port 40GBASE Ethernet Optical Interface Module(QSFP+)(HB)
unisevtModuleSw-LSXM1QGS24HB1               OBJECT IDENTIFIER ::= { unisevtModuleSwitchType 1983 } -- 24-Port 40GBASE Ethernet Optical Interface Module(QSFP+)(HB)
unisevtModuleSw-LSXM1QGS24HC0               OBJECT IDENTIFIER ::= { unisevtModuleSwitchType 1984 } -- 24-Port 40GBASE Ethernet Optical Interface Module(QSFP+)(HC)
unisevtModuleSw-LSXM1SUP01B1                OBJECT IDENTIFIER ::= { unisevtModuleSwitchType 1985 } -- Supervisor Engine Board
unisevtModuleSw-LSCM1SUP03A0                OBJECT IDENTIFIER ::= { unisevtModuleSwitchType 1986 } -- Supervisor Engine Board
unisevtModuleSw-LSCM1SUP03A0-Z              OBJECT IDENTIFIER ::= { unisevtModuleSwitchType 1987 } -- Supervisor Engine Board
unisevtModuleSw-LSCM1MPUS06A0               OBJECT IDENTIFIER ::= { unisevtModuleSwitchType 1988 } -- Supervisor Engine Board
unisevtModuleSw-LSCM1MPUS06A0-Z             OBJECT IDENTIFIER ::= { unisevtModuleSwitchType 1989 } -- Supervisor Engine Board
unisevtModuleSw-LSCM1GT48SC0                OBJECT IDENTIFIER ::= { unisevtModuleSwitchType 1990 } -- 48-Port 10/100/1000BASE-T Electrical Interface Board(RJ45)(SC)
unisevtModuleSw-LSCM1GT48SC0-Z              OBJECT IDENTIFIER ::= { unisevtModuleSwitchType 1991 } -- 48-Port 10/100/1000BASE-T Electrical Interface Board(RJ45)(SC)
unisevtModuleSw-LSCM1TGS48SE0               OBJECT IDENTIFIER ::= { unisevtModuleSwitchType 1992 } -- 48-Port 10GBASE-R Ethernet SFP+ Optical Interface Board(SE)
unisevtModuleSw-LSCM1TGS48SE0-Z             OBJECT IDENTIFIER ::= { unisevtModuleSwitchType 1993 } -- 48-Port 10GBASE-R Ethernet SFP+ Optical Interface Board(SE)
unisevtModuleSw-LSCM1QGS8CSSE0              OBJECT IDENTIFIER ::= { unisevtModuleSwitchType 1994 } -- 8-Port 40GBASE-R QSFP+ + 4-Port 100GBASE-R QSFP28 Optical Interface Board(SE)
unisevtModuleSw-LSCM1QGS8CSSE0-Z            OBJECT IDENTIFIER ::= { unisevtModuleSwitchType 1995 } -- 8-Port 40GBASE-R QSFP+ + 4-Port 100GBASE-R QSFP28 Optical Interface Board(SE)
unisevtModuleSw-LSWM2SP4P                   OBJECT IDENTIFIER ::= { unisevtModuleSwitchType 1996 } -- 4-Port 10GBASE-R Ethernet SFP+ Optical Interface Module
unisevtModuleSw-LSWM2SP4P-Z                 OBJECT IDENTIFIER ::= { unisevtModuleSwitchType 1997 } -- 4-Port 10GBASE-R Ethernet SFP+ Optical Interface Module
unisevtModuleSw-LSQM1MPUS10B0               OBJECT IDENTIFIER ::= { unisevtModuleSwitchType 1998 } -- Supervisor Engine Board
unisevtModuleSw-LSQM1MPUS10B3               OBJECT IDENTIFIER ::= { unisevtModuleSwitchType 1999 } -- Supervisor Engine Board
unisevtModuleSw-LSQM1MPUSC0                 OBJECT IDENTIFIER ::= { unisevtModuleSwitchType 2000 } -- Supervisor Engine Board
unisevtModuleSw-LSQM1MPUSC3                 OBJECT IDENTIFIER ::= { unisevtModuleSwitchType 2001 } -- Supervisor Engine Board
unisevtModuleSw-LSQM2GP24TSSC8              OBJECT IDENTIFIER ::= { unisevtModuleSwitchType 2002 } -- 24-Port 1000BASE-X Optical Interface(SFP,LC)+4-Port 10GBASE-R Ethernet Optical Interface Board(SFP+,LC)(SC)
unisevtModuleSw-LSQM2GT24TSSC8              OBJECT IDENTIFIER ::= { unisevtModuleSwitchType 2003 } -- 24-Port 10/100/1000BASE-T Electrical Interface(RJ45)+4-Port 10GBASE-R Ethernet Optical Interface Board(SFP+,LC)(SC)
unisevtModuleSw-LSXM1TGS24CGMODHD0          OBJECT IDENTIFIER ::= { unisevtModuleSwitchType 2004 } -- 24-Port 10GBASE Ethernet Optical Interface(SFP+,LC)+4-Port 100GBASE Ethernet Optical Interface Module(QSFP28)(HD),With 1 Expansion Slot
unisevtModuleSw-LSXM1TGS24CGMODHD1          OBJECT IDENTIFIER ::= { unisevtModuleSwitchType 2005 } -- 24-Port 10GBASE Ethernet Optical Interface(SFP+,LC)+4-Port 100GBASE Ethernet Optical Interface Module(QSFP28)(HD),With 1 Expansion Slot
unisevtModuleSw-LSQM1TGS16GPSA0             OBJECT IDENTIFIER ::= { unisevtModuleSwitchType 2006 } -- 24-Port 1000BASE-R Ethernet Optical Interface(SFP,LC)+16-Port 10GBASE-R Ethernet Optical Interface Board(SFP+,LC)
unisevtModuleSw-EWPXM2TGS48SG0              OBJECT IDENTIFIER ::= { unisevtModuleSwitchType 2007 } -- 48-Port 10GBASE-R Ethernet SFP+ Optical Interface Board(SG)
unisevtModuleSw-EWPXM1TGS16FD0              OBJECT IDENTIFIER ::= { unisevtModuleSwitchType 2008 } -- 16-Port 10GBASE-R Ethernet SFP+ Optical Interface Board(FD)
unisevtModuleSw-LSXM1CGQ36HF0               OBJECT IDENTIFIER ::= { unisevtModuleSwitchType 2009 } -- 36-Port 100GBASE Ethernet Optical Interface Module(QSFP28)(HF)
unisevtModuleSw-LSXM2SUPT0                  OBJECT IDENTIFIER ::= { unisevtModuleSwitchType 2010 } -- Supervisor Engine Board
unisevtModuleSw-LSXM2SUPT1                  OBJECT IDENTIFIER ::= { unisevtModuleSwitchType 2011 } -- Supervisor Engine Board
unisevtModuleSw-LSXM1SFT16E0                OBJECT IDENTIFIER ::= { unisevtModuleSwitchType 2012 } -- Switch Fabric Board
unisevtModuleSw-LSXM1SFT16E1                OBJECT IDENTIFIER ::= { unisevtModuleSwitchType 2013 } -- Switch Fabric Board
unisevtModuleSw-lsxM1CGQ36TD0               OBJECT IDENTIFIER ::= { unisevtModuleSwitchType 2014 } -- 36-Port 100GBASE Ethernet Optical Interface Board(QSFP28)
unisevtModuleSw-lsxM1CGQ36TD1               OBJECT IDENTIFIER ::= { unisevtModuleSwitchType 2015 } -- 36-Port 100GBASE Ethernet Optical Interface Board(QSFP28)
unisevtModuleSw-LSQM1TGT24FD0               OBJECT IDENTIFIER ::= { unisevtModuleSwitchType 2016 } -- 24-Port 10GBASE-T Ethernet Copper Interface Module(RJ45)(FD)
unisevtModuleSw-LSUM1TGT24FD0               OBJECT IDENTIFIER ::= { unisevtModuleSwitchType 2017 } -- 24-Port 10GBASE-T Ethernet Copper Interface Module(RJ45)(FD)
unisevtModuleSw-LSXM2SFT08E0                OBJECT IDENTIFIER ::= { unisevtModuleSwitchType 2018 } -- S12508F-AF Fabric Module,Type T(Class E)
unisevtModuleSw-LSXM2SFT08E1                OBJECT IDENTIFIER ::= { unisevtModuleSwitchType 2019 } -- S12508F-AF Fabric Module,Type T(Class E)
unisevtModuleSw-LSXM1CCP8HF0                OBJECT IDENTIFIER ::= { unisevtModuleSwitchType 2020 } -- 8-Port 200GBASE Ethernet Optical Interface Module(CFP2)(HF)
unisevtModuleSw-LSXM1CCP8HF1                OBJECT IDENTIFIER ::= { unisevtModuleSwitchType 2021 } -- 8-Port 200GBASE Ethernet Optical Interface Module(CFP2)(HF)



unisevtModuleSw-S8610-MPU                   OBJECT IDENTIFIER ::= { unisevtModuleSwitchType 2028 } -- Supervisor Engine Board
unisevtModuleSw-S8610-NET                   OBJECT IDENTIFIER ::= { unisevtModuleSwitchType 2029 } -- Switching Fabric Module
unisevtModuleSw-S86-44GF4XFSE               OBJECT IDENTIFIER ::= { unisevtModuleSwitchType 2030 } -- 44-Port GE Optical Interface(SFP,LC)+4-Port 10GE Optical Interface Board(SFP+,LC)(SE)
unisevtModuleSw-S86-48GTSE                  OBJECT IDENTIFIER ::= { unisevtModuleSwitchType 2031 } -- 48-Port 1000Base-T Gigabit Ethernet Interface Board(RJ45)(SE)
unisevtModuleSw-S86-12QFSG                  OBJECT IDENTIFIER ::= { unisevtModuleSwitchType 2032 } -- 12-Port 40GBASE-R Ethernet QSFP+ Optical Interface Board(SG)
unisevtModuleSw-S86-48XFSG                  OBJECT IDENTIFIER ::= { unisevtModuleSwitchType 2033 } -- 48-Port 10GBASE-R Ethernet SFP+ Optical Interface Board(SG)
unisevtModuleSw-LSUM1MPUS06XEC0             OBJECT IDENTIFIER ::= { unisevtModuleSwitchType 2034 } -- Supervisor Engine Board
unisevtModuleSw-LSUM1MPUS10XE0              OBJECT IDENTIFIER ::= { unisevtModuleSwitchType 2035 } -- Supervisor Engine Board
unisevtModuleSw-LSUM1MPUS10XEB0             OBJECT IDENTIFIER ::= { unisevtModuleSwitchType 2036 } -- Supervisor Engine Board
unisevtModuleSw-LSUM1FAB06XEC0              OBJECT IDENTIFIER ::= { unisevtModuleSwitchType 2037 } -- Switch Fabric Board
unisevtModuleSw-LSUM1FAB10XE0               OBJECT IDENTIFIER ::= { unisevtModuleSwitchType 2038 } -- Switch Fabric Board
unisevtModuleSw-LSUM1FAB10XEB0              OBJECT IDENTIFIER ::= { unisevtModuleSwitchType 2039 } -- Switch Fabric Board
unisevtModuleSw-LSUM1FAB08XEB0              OBJECT IDENTIFIER ::= { unisevtModuleSwitchType 2040 } -- Switch Fabric Board
unisevtModuleSw-LSUM1TGS48SH0               OBJECT IDENTIFIER ::= { unisevtModuleSwitchType 2041 } -- 48-Port 10G Ethernet Optical Interface Module(SFP+,LC)(SH)
unisevtModuleSw-LSUM1CGS8SH0                OBJECT IDENTIFIER ::= { unisevtModuleSwitchType 2042 } -- 8-Port 100G Ethernet Optical Interface Module(QSFP28)(SH)
unisevtModuleSw-LSUM1YGS24CSSH0             OBJECT IDENTIFIER ::= { unisevtModuleSwitchType 2043 } -- 24-Port 25G Ethernet Optical Interface(SFP28,LC)+4-Port 100G Ethernet Optical Interface Module(QSFP28)(SH)
unisevtModuleSw-LSUM1CGS20XSH0              OBJECT IDENTIFIER ::= { unisevtModuleSwitchType 2044 } -- 20-Port 100G Ethernet Optical Interface Module(QSFP28)(SH)
unisevtModuleSw-LSUM1CGS32XSH0              OBJECT IDENTIFIER ::= { unisevtModuleSwitchType 2045 } -- 32-Port 100G Ethernet Optical Interface Module(QSFP28)(SH)
unisevtModuleSw-LSUM1CGS8QSSH0              OBJECT IDENTIFIER ::= { unisevtModuleSwitchType 2046 } -- 8-Port 100G Ethernet Optical Interface Module(QSFP28) +8-port 40G/4-Port 100G Ethernet Optical Interface Module(QSFP28)(SH)
unisevtModuleSw-LSUM1YGS48XSH0              OBJECT IDENTIFIER ::= { unisevtModuleSwitchType 2047 } -- 48-Port 25G Ethernet Optical Interface(SFP28,LC)(SH)
unisevtModuleSw-LSXM3SUPT1                  OBJECT IDENTIFIER ::= { unisevtModuleSwitchType 2048 } -- Comware 9 Type-H Supervisor Engine Unit
unisevtModuleSw-LSXM4SUPT1                  OBJECT IDENTIFIER ::= { unisevtModuleSwitchType 2049 } -- Comware 9 Type-T Supervisor Engine Unit
unisevtModuleSw-LSQM2GP24TSSA0-Z            OBJECT IDENTIFIER ::= { unisevtModuleSwitchType 2050 } -- 24-Port GE Optical Interface(SFP,LC)+4-Port 10GE Optical Interface Board(SFP+,LC)(SA)
unisevtModuleSw-LSQM2GT48SA0-Z              OBJECT IDENTIFIER ::= { unisevtModuleSwitchType 2051 } -- 48-Port 1000Base-T Gigabit Ethernet Interface Board(RJ45)(SA)
unisevtModuleSw-LSQM2GP48SA0-Z              OBJECT IDENTIFIER ::= { unisevtModuleSwitchType 2052 } -- 48-Port 1000BASE-X Ethernet Optical Interface Board(SFP,LC)(SA)
unisevtModuleSw-LSUM2TGS48SG0-Z             OBJECT IDENTIFIER ::= { unisevtModuleSwitchType 2053 } -- 48-Port 10GBASE-R Ethernet SFP+ Optical Interface Board(SG)
unisevtModuleSw-LSUM2QGS12SG0-Z             OBJECT IDENTIFIER ::= { unisevtModuleSwitchType 2054 } -- 12-Port 40GBASE-R Ethernet QSFP+ Optical Interface Board(SG)
unisevtModuleSw-LSUM2TGS32QSSG0-Z           OBJECT IDENTIFIER ::= { unisevtModuleSwitchType 2055 } -- 32-Port 10GBASE-R Ethernet Optical Interface(SFP+,LC)+4-Port 40GBASE-R Ethernet Optical Interface Board(QSFP+,LC)(SG)
unisevtModuleSw-LSUM1TGS48RSH0              OBJECT IDENTIFIER ::= { unisevtModuleSwitchType 2056 } -- 48-Port 10GBASE-R Ethernet Optical Interface Module(SFP+,LC)(SH)
unisevtModuleSw-LSUM1MPUS06XEB0             OBJECT IDENTIFIER ::= { unisevtModuleSwitchType 2057 } -- Supervisor Engine Board
unisevtModuleSw-LSUM1MPUS10XEA0             OBJECT IDENTIFIER ::= { unisevtModuleSwitchType 2058 } -- Supervisor Engine Board
unisevtModuleSw-LSUM1FAB06XEB0              OBJECT IDENTIFIER ::= { unisevtModuleSwitchType 2059 } -- Switch Fabric Board
unisevtModuleSw-LSUM1FAB10XEA0              OBJECT IDENTIFIER ::= { unisevtModuleSwitchType 2060 } -- Switch Fabric Board
unisevtModuleSw-EWPXM1WCMX100               OBJECT IDENTIFIER ::= { unisevtModuleSwitchType 2061 } -- Access Controller Service Board
unisevtModuleSw-LSQM1WBCZ720X               OBJECT IDENTIFIER ::= { unisevtModuleSwitchType 2062 } -- Access Controller Service Board
unisevtModuleSw-LSUM1WBCZ720XRT             OBJECT IDENTIFIER ::= { unisevtModuleSwitchType 2063 } -- Access Controller Service Board
unisevtModuleSw-LSXM1CGQ8TD1                OBJECT IDENTIFIER ::= { unisevtModuleSwitchType 2064 } -- 8-Port 100GBASE  Ethernet Optical Interface Board(QSFP28)
unisevtModuleSw-LSXM1CGQ12TD1               OBJECT IDENTIFIER ::= { unisevtModuleSwitchType 2065 } -- 12-Port 100GBASE  Ethernet Optical Interface Board(QSFP28)
unisevtModuleSw-LSXM1CGQ18TD1               OBJECT IDENTIFIER ::= { unisevtModuleSwitchType 2066 } -- 18-Port 100GBASE  Ethernet Optical Interface Board(QSFP28)
unisevtModuleSw-LSXM1QGS24C6TD1             OBJECT IDENTIFIER ::= { unisevtModuleSwitchType 2067 } -- 24-Port 40GBASE Ethernet Optical Interface Module (QSFP+) + 6-Port 100GBASE (QSFP28)
unisevtModuleSw-LSXM1QGS36TD1               OBJECT IDENTIFIER ::= { unisevtModuleSwitchType 2068 } -- 36-Port 40GBASE Ethernet Optical Interface Module(QSFP+)
unisevtModuleSw-LSXM1QGS48TD1               OBJECT IDENTIFIER ::= { unisevtModuleSwitchType 2069 } -- 48-Port 40GBASE Ethernet Optical Interface Module(QSFP+)
unisevtModuleSw-LSXM1TGS48C4TD1             OBJECT IDENTIFIER ::= { unisevtModuleSwitchType 2070 } -- 48-Port 10GBASE Ethernet Optical Interface(SFP+,LC)+4-Port 100GBASE Ethernet Optical Interface Module(QSFP28)
unisevtModuleSw-LSXM1GP48TD1                OBJECT IDENTIFIER ::= { unisevtModuleSwitchType 2071 } -- 48-Port GE BASE Ethernet Optical Interface Module(SFP,LC))
unisevtModuleSw-LSXM1TGS48TD1               OBJECT IDENTIFIER ::= { unisevtModuleSwitchType 2072 } -- 48-Port 10G BASE Ethernet Optical Interface Module(SFP+,LC))




unisevtModuleSw-LSWM124TG2H1               OBJECT IDENTIFIER ::= { unisevtModuleSwitchType 2076 }
unisevtModuleSw-LSQM2FWDSC8                OBJECT IDENTIFIER ::= { unisevtModuleSwitchType 2077 }

unisevtModuleSw-IM-MSEX-B                  OBJECT IDENTIFIER ::= { unisevtModuleSwitchType 2080 } -- Service Processing Unit(IM-MSEX-B)
unisevtModuleSw-IM-MSEX-B-IM-SP-B          OBJECT IDENTIFIER ::= { unisevtModuleSwitchType 2081 } -- Service Processing Unit + Universal Line Processing Interface Card(IM-MSEX-B-IM-SP-B)
unisevtModuleSw-LSUM1MPUS06XEC0-Z          OBJECT IDENTIFIER ::= { unisevtModuleSwitchType 2082 }
unisevtModuleSw-LSUM1CGS8SH0-Z             OBJECT IDENTIFIER ::= { unisevtModuleSwitchType 2083 }
unisevtModuleSw-LSUM1SUPXD0-Z              OBJECT IDENTIFIER ::= { unisevtModuleSwitchType 2084 }
unisevtModuleSw-LSUM1FAB08XE0-Z            OBJECT IDENTIFIER ::= { unisevtModuleSwitchType 2085 }
unisevtModuleSw-LSUM1CGS20XSH0-Z           OBJECT IDENTIFIER ::= { unisevtModuleSwitchType 2086 }
unisevtModuleSw-LSUM1FAB06XEC0-Z           OBJECT IDENTIFIER ::= { unisevtModuleSwitchType 2087 }
unisevtModuleSw-LSUM1CQGS32SF0-Z           OBJECT IDENTIFIER ::= { unisevtModuleSwitchType 2088 }
unisevtModuleSw-LSXM1FAB10XE3              OBJECT IDENTIFIER ::= { unisevtModuleSwitchType 2089 }
unisevtModuleSw-LSXM1FAB08XE3              OBJECT IDENTIFIER ::= { unisevtModuleSwitchType 2090 }
unisevtModuleSw-LSXM1YGS48XSH3             OBJECT IDENTIFIER ::= { unisevtModuleSwitchType 2091 }
unisevtModuleSw-LSXM1YGS24CSSH3            OBJECT IDENTIFIER ::= { unisevtModuleSwitchType 2092 }
unisevtModuleSw-LSXM1CGS8QSSH3             OBJECT IDENTIFIER ::= { unisevtModuleSwitchType 2093 }
unisevtModuleSw-LSXM1TGS48SH3              OBJECT IDENTIFIER ::= { unisevtModuleSwitchType 2094 }
unisevtModuleSw-LSXM1MPUS10XE3             OBJECT IDENTIFIER ::= { unisevtModuleSwitchType 2095 }
unisevtModuleSw-LSXM1FAB06XEC3             OBJECT IDENTIFIER ::= { unisevtModuleSwitchType 2096 }
unisevtModuleSw-LSXM1MPUS06XEC3            OBJECT IDENTIFIER ::= { unisevtModuleSwitchType 2097 }
unisevtModuleSw-LSXM1CGS8SH3               OBJECT IDENTIFIER ::= { unisevtModuleSwitchType 2098 }
unisevtModuleSw-LSXM1SUPXD3                OBJECT IDENTIFIER ::= { unisevtModuleSwitchType 2099 }
unisevtModuleSw-LSXM1CGS20XSH3             OBJECT IDENTIFIER ::= { unisevtModuleSwitchType 2100 }
unisevtModuleSw-LSUM1GP48FD0-Z             OBJECT IDENTIFIER ::= { unisevtModuleSwitchType 2101 }
unisevtModuleSw-LSQM1TGS48RFE0-Z           OBJECT IDENTIFIER ::= { unisevtModuleSwitchType 2102 }
unisevtModuleSw-LSXM1CGS32XSH3             OBJECT IDENTIFIER ::= { unisevtModuleSwitchType 2103 }
unisevtModuleSw-LSQM2GP40TS8FD0            OBJECT IDENTIFIER ::= { unisevtModuleSwitchType 2104 }
unisevtModuleSw-LSUM1SUPXES0               OBJECT IDENTIFIER ::= { unisevtModuleSwitchType 2105 }
unisevtModuleSw-LSQM2SUPB0                 OBJECT IDENTIFIER ::= { unisevtModuleSwitchType 2106 }
unisevtModuleSw-LSUM2GP40TS8FD0            OBJECT IDENTIFIER ::= { unisevtModuleSwitchType 2107 }
unisevtModuleSw-LSXM1YGS48XXSH3            OBJECT IDENTIFIER ::= { unisevtModuleSwitchType 2108 }
unisevtModuleSw-LSXM2SFT08E2               OBJECT IDENTIFIER ::= { unisevtModuleSwitchType 2109 }
unisevtModuleSw-LSXM1TGS48TD2              OBJECT IDENTIFIER ::= { unisevtModuleSwitchType 2110 }
unisevtModuleSw-LSXM1CGQ36TD2              OBJECT IDENTIFIER ::= { unisevtModuleSwitchType 2111 }
unisevtModuleSw-RX-NIC-LGQ4L               OBJECT IDENTIFIER ::= { unisevtModuleSwitchType 2112 } -- 4-port 50G Ethernet Optical Interface Card(QSFP28,LC)(RX-NIC)
unisevtModuleSw-LSXM1CDQ24KB1              OBJECT IDENTIFIER ::= { unisevtModuleSwitchType 2113 }
unisevtModuleSw-LSXM1SUP02L1               OBJECT IDENTIFIER ::= { unisevtModuleSwitchType 2114 }
unisevtModuleSw-LSXM1CGQ48KB1              OBJECT IDENTIFIER ::= { unisevtModuleSwitchType 2115 }
unisevtModuleSw-LSXM1SFK08F1               OBJECT IDENTIFIER ::= { unisevtModuleSwitchType 2116 }
unisevtModuleSw-CSPEX-1214X                OBJECT IDENTIFIER ::= { unisevtModuleSwitchType 2117 }
unisevtModuleSw-MIC-CQ1L1                  OBJECT IDENTIFIER ::= { unisevtModuleSwitchType 2118 } -- 1-port 100G Ethernet Optical Interface Card(QSFP28)
unisevtModuleSw-DS-3E7600-16X-SCB          OBJECT IDENTIFIER ::= { unisevtModuleSwitchType 2119 }
unisevtModuleSw-DS-3E12508-MPU             OBJECT IDENTIFIER ::= { unisevtModuleSwitchType 2120 }
unisevtModuleSw-DS-3E12500-7610-48T-SE     OBJECT IDENTIFIER ::= { unisevtModuleSwitchType 2121 }
unisevtModuleSw-DS-3E7603-MPU              OBJECT IDENTIFIER ::= { unisevtModuleSwitchType 2122 }
unisevtModuleSw-DS-3E12500-7610-16X-SF     OBJECT IDENTIFIER ::= { unisevtModuleSwitchType 2123 }
unisevtModuleSw-DS-3E12500-24T20F4X-SE     OBJECT IDENTIFIER ::= { unisevtModuleSwitchType 2124 }
unisevtModuleSw-DS-3E12500-12Q-SG          OBJECT IDENTIFIER ::= { unisevtModuleSwitchType 2125 }
unisevtModuleSw-DS-3E12500-48X-SG          OBJECT IDENTIFIER ::= { unisevtModuleSwitchType 2126 }
unisevtModuleSw-DS-3E12500-7610-32X4QX-SF  OBJECT IDENTIFIER ::= { unisevtModuleSwitchType 2127 }
unisevtModuleSw-DS-3E12500-7610-44F4X-SE   OBJECT IDENTIFIER ::= { unisevtModuleSwitchType 2128 }
unisevtModuleSw-DS-3E12508-CLOS            OBJECT IDENTIFIER ::= { unisevtModuleSwitchType 2129 }
unisevtModuleSw-LSXM2SUPT2                 OBJECT IDENTIFIER ::= { unisevtModuleSwitchType 2130 }
unisevtModuleSw-CSR05SRP1P3A               OBJECT IDENTIFIER ::= { unisevtModuleSwitchType 2131 } -- CR16000-FA Main Processing Unit(1P3A)
unisevtModuleSw-CSFC-08E1A                 OBJECT IDENTIFIER ::= { unisevtModuleSwitchType 2132 } -- CR16010H-FA Fabric Module(E Type)
unisevtModuleSw-CSFC-16EA                  OBJECT IDENTIFIER ::= { unisevtModuleSwitchType 2133 } -- CR16018-FA Fabric Module(E Type)
unisevtModuleSw-CSPEX-1602XA               OBJECT IDENTIFIER ::= { unisevtModuleSwitchType 2134 } -- Service Processing Unit(1602XA)
unisevtModuleSw-CEPC-CP4RXA                OBJECT IDENTIFIER ::= { unisevtModuleSwitchType 2135 } -- 4-port 100GBASE Ethernet Optical Interface Line Processing Unit A(CFP2)
unisevtModuleSw-CSPEX-1504XA               OBJECT IDENTIFIER ::= { unisevtModuleSwitchType 2136 } -- Service Processing Unit(1504XA)
unisevtModuleSw-CSPEX-1804XA               OBJECT IDENTIFIER ::= { unisevtModuleSwitchType 2137 } -- Service Processing Unit(1804XA)
unisevtModuleSw-MIC-GP10LA                 OBJECT IDENTIFIER ::= { unisevtModuleSwitchType 2138 } -- 10-port 1000BASE-X Ethernet Optical Interface Card A(SFP,LC)
unisevtModuleSw-MIC-GT20LA                 OBJECT IDENTIFIER ::= { unisevtModuleSwitchType 2139 } -- 20-port 1000BASE-X Ethernet Copper Interface Card A(RJ45)
unisevtModuleSw-MIC-XP20LA                 OBJECT IDENTIFIER ::= { unisevtModuleSwitchType 2140 } -- 20-port 10GBASE-R/W Ethernet Optical Interface Card A(SFP+,LC)

unisevtModuleSw-LSDM1QGS12SE0-Z            OBJECT IDENTIFIER ::= { unisevtModuleSwitchType 2142 }
unisevtModuleSw-LSDM1TGS48SE0-Z            OBJECT IDENTIFIER ::= { unisevtModuleSwitchType 2143 }
unisevtModuleSw-LSDM1SUPA0-Z               OBJECT IDENTIFIER ::= { unisevtModuleSwitchType 2144 }
unisevtModuleSw-LSDM1FAB08D0-Z             OBJECT IDENTIFIER ::= { unisevtModuleSwitchType 2145 }
unisevtModuleSw-LSDM1GT24GPSE0-Z           OBJECT IDENTIFIER ::= { unisevtModuleSwitchType 2146 }
unisevtModuleSw-LSXM1CGQ18TD2              OBJECT IDENTIFIER ::= { unisevtModuleSwitchType 2147 }
unisevtModuleSw-LSXM1QGS36TD2              OBJECT IDENTIFIER ::= { unisevtModuleSwitchType 2148 }
unisevtModuleSw-RP-S-G                     OBJECT IDENTIFIER ::= { unisevtModuleSwitchType 2149 }
unisevtModuleSw-MOD20-G                    OBJECT IDENTIFIER ::= { unisevtModuleSwitchType 2150 }
unisevtModuleSw-MPA-PSP4L-G                OBJECT IDENTIFIER ::= { unisevtModuleSwitchType 2151 }
unisevtModuleSw-MPA-TCP8L-G                OBJECT IDENTIFIER ::= { unisevtModuleSwitchType 2152 }
unisevtModuleSw-MPA-ET16L-G                OBJECT IDENTIFIER ::= { unisevtModuleSwitchType 2153 }
unisevtModuleSw-MPA-GP10L-G                OBJECT IDENTIFIER ::= { unisevtModuleSwitchType 2154 }
unisevtModuleSw-MPA-XP4L-G                 OBJECT IDENTIFIER ::= { unisevtModuleSwitchType 2155 }
unisevtModuleSw-LSXM1SFH04DR1              OBJECT IDENTIFIER ::= { unisevtModuleSwitchType 2156 }
unisevtModuleSw-LSXM1SFH08CR1              OBJECT IDENTIFIER ::= { unisevtModuleSwitchType 2157 }
unisevtModuleSw-LSXM1SFH08DR1              OBJECT IDENTIFIER ::= { unisevtModuleSwitchType 2158 }
unisevtModuleSw-LSXM1SFH16CR1              OBJECT IDENTIFIER ::= { unisevtModuleSwitchType 2159 }
unisevtModuleSw-LSXM1SFH16ER1              OBJECT IDENTIFIER ::= { unisevtModuleSwitchType 2160 }
unisevtModuleSw-LSXM1TGS48HFR1             OBJECT IDENTIFIER ::= { unisevtModuleSwitchType 2161 }
unisevtModuleSw-LSXM1CGQ18QGHFR1           OBJECT IDENTIFIER ::= { unisevtModuleSwitchType 2162 }
unisevtModuleSw-LSXM1SUP04TR1              OBJECT IDENTIFIER ::= { unisevtModuleSwitchType 2163 }
unisevtModuleSw-LSXM1CGQ36HBR1             OBJECT IDENTIFIER ::= { unisevtModuleSwitchType 2164 }
unisevtModuleSw-LSXM1CGQ36HFR1             OBJECT IDENTIFIER ::= { unisevtModuleSwitchType 2165 }
unisevtModuleSw-LSXM1CGQ6QGHFR1            OBJECT IDENTIFIER ::= { unisevtModuleSwitchType 2166 }
unisevtModuleSw-LSXM1TGS48HBR1             OBJECT IDENTIFIER ::= { unisevtModuleSwitchType 2167 }
unisevtModuleSw-LSXM1CGQ18QGHBR1           OBJECT IDENTIFIER ::= { unisevtModuleSwitchType 2168 }
unisevtModuleSw-LSXM1SUPER1                OBJECT IDENTIFIER ::= { unisevtModuleSwitchType 2169 }
unisevtModuleSw-LSQM1SDNB0                 OBJECT IDENTIFIER ::= { unisevtModuleSwitchType 2170 } -- SDN-engine Blade
unisevtModuleSw-LSUM1SDNB0                 OBJECT IDENTIFIER ::= { unisevtModuleSwitchType 2171 } -- SDN-engine Blade
unisevtModuleSw-LSQM1EPSB0                 OBJECT IDENTIFIER ::= { unisevtModuleSwitchType 2172 } -- EPS-engine Blade
unisevtModuleSw-LSUM1EPSB0                 OBJECT IDENTIFIER ::= { unisevtModuleSwitchType 2173 } -- EPS-engine Blade
unisevtModuleSw-LSXM2TGS48HB2              OBJECT IDENTIFIER ::= { unisevtModuleSwitchType 2174 }
unisevtModuleSw-LSXM2CGQ18QGHB2            OBJECT IDENTIFIER ::= { unisevtModuleSwitchType 2175 }
unisevtModuleSw-LSUM1CGS8SH3               OBJECT IDENTIFIER ::= { unisevtModuleSwitchType 2176 }
unisevtModuleSw-LSUM1GT48FC3               OBJECT IDENTIFIER ::= { unisevtModuleSwitchType 2177 }
unisevtModuleSw-LSUM1FAB10XEA3             OBJECT IDENTIFIER ::= { unisevtModuleSwitchType 2178 }
unisevtModuleSw-LSUM1TGS48SH3              OBJECT IDENTIFIER ::= { unisevtModuleSwitchType 2179 }
unisevtModuleSw-LSUM1MPUS10XE3             OBJECT IDENTIFIER ::= { unisevtModuleSwitchType 2180 }
unisevtModuleSw-LSUM1GP48FC3               OBJECT IDENTIFIER ::= { unisevtModuleSwitchType 2181 }
unisevtModuleSw-LSQM1TGS16FD0-Z            OBJECT IDENTIFIER ::= { unisevtModuleSwitchType 2182 }
unisevtModuleSw-LSQM2SUPA0-Z               OBJECT IDENTIFIER ::= { unisevtModuleSwitchType 2183 }
unisevtModuleSw-LSUM1TGS16FD0-Z            OBJECT IDENTIFIER ::= { unisevtModuleSwitchType 2184 }
unisevtModuleSw-LSWM2FPGAB                 OBJECT IDENTIFIER ::= { unisevtModuleSwitchType 2185 }
unisevtModuleSw-LSWM2EC                    OBJECT IDENTIFIER ::= { unisevtModuleSwitchType 2186 } -- EScaner
unisevtModuleSw-LSWM2FPGA                  OBJECT IDENTIFIER ::= { unisevtModuleSwitchType 2187 }
unisevtModuleSw-LSWM2ZSP4P                 OBJECT IDENTIFIER ::= { unisevtModuleSwitchType 2188 }
unisevtModuleSw-LSXM1CGQ8TD2               OBJECT IDENTIFIER ::= { unisevtModuleSwitchType 2189 }
unisevtModuleSw-LSXM1TGS48C4TD2            OBJECT IDENTIFIER ::= { unisevtModuleSwitchType 2190 }
unisevtModuleSw-LSXM1QGS24C6TD2            OBJECT IDENTIFIER ::= { unisevtModuleSwitchType 2191 }
unisevtModuleSw-LSCM1MPUS06A8              OBJECT IDENTIFIER ::= { unisevtModuleSwitchType 2192 }
unisevtModuleSw-LSCM1TGS48SC8              OBJECT IDENTIFIER ::= { unisevtModuleSwitchType 2193 }
unisevtModuleSw-LSQM1MPUS06S0              OBJECT IDENTIFIER ::= { unisevtModuleSwitchType 2194 }
unisevtModuleSw-LSQM1SRP4Y06A0             OBJECT IDENTIFIER ::= { unisevtModuleSwitchType 2195 }
unisevtModuleSw-S76-16XFSF-E               OBJECT IDENTIFIER ::= { unisevtModuleSwitchType 2196 }
unisevtModuleSw-S7603-MPU                  OBJECT IDENTIFIER ::= { unisevtModuleSwitchType 2197 }
unisevtModuleSw-LSCM2MPUS06AS8             OBJECT IDENTIFIER ::= { unisevtModuleSwitchType 2198 }  -- Supervisor Engine Board
unisevtModuleSw-LSCM2CGT24TSSC8            OBJECT IDENTIFIER ::= { unisevtModuleSwitchType 2199 }  -- Supervisor Engine Board With 24-Port 10/100/1000BASE-T Ethernet Interface+4-Port 10GBASE-R Ethernet SFP+ Optical Interfaces
unisevtModuleSw-LSCM2CGP24TSSC8            OBJECT IDENTIFIER ::= { unisevtModuleSwitchType 2200 }  -- Supervisor Engine Board With 24-Port 1000BASE-X Ethernet SFP Optical Interface+4-Port 10GBASE-R Ethernet SFP+ Optical Interfaces
unisevtModuleSw-LSCM2CTGS12GTSC8           OBJECT IDENTIFIER ::= { unisevtModuleSwitchType 2201 }  -- Supervisor Engine Board With 16-Port 10/100/1000BASE-T Ethernet Interface+12-Port 10GBASE-R Ethernet SFP+ Optical Interfaces
unisevtModuleSw-LSCM2CTGS12GPSC8           OBJECT IDENTIFIER ::= { unisevtModuleSwitchType 2202 }  -- Supervisor Engine Board With 16-Port 1000BASE-X Ethernet SFP Optical Interface+12-Port 10GBASE-R Ethernet SFP+ Optical Interfaces
unisevtModuleSw-LSCM2GT24GPTSSC8           OBJECT IDENTIFIER ::= { unisevtModuleSwitchType 2203 }  -- 24-Port 10/100/1000BASE-T Ethernet Interface Board(RJ45)+20-Port 1000BASE-X Ethernet SFP Optical Interface(SFP,LC)+4-Port 10GBASE-R Optical Interface Board(SFP+,LC)(SC)
unisevtModuleSw-LSCM2GT24GPSC8             OBJECT IDENTIFIER ::= { unisevtModuleSwitchType 2204 }  -- 24-Port 10/100/1000BASE-T Ethernet Interface Board(RJ45)+8-Port 1000BASE-X Ethernet SFP Optical Interface(SFP,LC)(SC)
unisevtModuleSw-LSCM2GP24GTSC8             OBJECT IDENTIFIER ::= { unisevtModuleSwitchType 2205 }  -- 8-Port 10/100/1000BASE-T Ethernet Interface Board(RJ45)+24-Port 1000BASE-X Ethernet SFP Optical Interface(SFP,LC)(SC)
unisevtModuleSw-LSCM2GT48SC8               OBJECT IDENTIFIER ::= { unisevtModuleSwitchType 2206 }  -- 48-Port 10/100/1000BASE-T Ethernet Interface Board(RJ45)(SC)
unisevtModuleSw-LSCM2GP48SC8               OBJECT IDENTIFIER ::= { unisevtModuleSwitchType 2207 }  -- 48-Port 1000BASE-X Ethernet Optical Interface Board(SFP,LC)
unisevtModuleSw-LSCM2TGS16GPSC8            OBJECT IDENTIFIER ::= { unisevtModuleSwitchType 2208 }  -- 24-Port 1000BASE-R Ethernet Optical Interface(SFP,LC)+16-Port 10GBASE-R Ethernet Optical Interface Board(SFP+,LC)

unisevtModuleSw-LSXM2SFH16CR1              OBJECT IDENTIFIER ::= { unisevtModuleSwitchType 2209 }  -- Fabric Module,Type H(Class C)
unisevtModuleSw-LSXM1SEERBXC2              OBJECT IDENTIFIER ::= { unisevtModuleSwitchType 2210 }
unisevtModuleSw-LSXM1SEERBG2               OBJECT IDENTIFIER ::= { unisevtModuleSwitchType 2211 }
unisevtModuleSw-LSXM1SEERBXD2              OBJECT IDENTIFIER ::= { unisevtModuleSwitchType 2212 }
unisevtModuleSwLSXM1SFK08FR1               OBJECT IDENTIFIER ::= { unisevtModuleSwitchType 2213 }
unisevtModuleSwLSXM1CDQ24KBR1              OBJECT IDENTIFIER ::= { unisevtModuleSwitchType 2214 }
unisevtModuleSwLSXM1SUP02LR1               OBJECT IDENTIFIER ::= { unisevtModuleSwitchType 2215 }
unisevtModuleSwLSXM1CGQ48KBR1              OBJECT IDENTIFIER ::= { unisevtModuleSwitchType 2216 }
unisevtModuleSwLSXM1CGQ36HC0               OBJECT IDENTIFIER ::= { unisevtModuleSwitchType 2217 }
unisevtModuleSw-LSXM1TGS48TE2              OBJECT IDENTIFIER ::= { unisevtModuleSwitchType 2218 }
unisevtModuleSw-LSXM1CGQ36TE2              OBJECT IDENTIFIER ::= { unisevtModuleSwitchType 2219 }
unisevtModuleSw-LSXM1SFT16F1               OBJECT IDENTIFIER ::= { unisevtModuleSwitchType 2220 }
unisevtModuleSw-LSXM1CGQ18TE2              OBJECT IDENTIFIER ::= { unisevtModuleSwitchType 2221 }
unisevtModuleSw-LSXM1CGQ8TE2               OBJECT IDENTIFIER ::= { unisevtModuleSwitchType 2222 }
unisevtModuleSwLSWM116H                    OBJECT IDENTIFIER ::= { unisevtModuleSwitchType 2223 }
unisevtModuleSwLSWM1M4CD                   OBJECT IDENTIFIER ::= { unisevtModuleSwitchType 2224 }
unisevtModuleSw-LSXM1QGS36TE2              OBJECT IDENTIFIER ::= { unisevtModuleSwitchType 2225 }
unisevtModuleSw-LSXM1SFT16F2               OBJECT IDENTIFIER ::= { unisevtModuleSwitchType 2226 }
unisevtModuleSw-CSPEX-1812X-E              OBJECT IDENTIFIER ::= { unisevtModuleSwitchType 2227 } -- Service Processing Unit(1812X-E)
unisevtModuleSw-MOD20-A3                   OBJECT IDENTIFIER ::= { unisevtModuleSwitchType 2228 } -- R9900-S-G,SR0MZLF1DQM1,Service Processing Unit(MOD20-G),Domestic&Overseas Version
unisevtModuleSw-RP-S-G-A3                  OBJECT IDENTIFIER ::= { unisevtModuleSwitchType 2229 } -- R9900-S-G,SR0MZSRP1A4,Main Processing Unit,Domestic Version
unisevtModuleSw-LSXM1SFT16EA1              OBJECT IDENTIFIER ::= { unisevtModuleSwitchType 2230 } -- Switch Fabric Board
unisevtModuleSw-RP1-S-G                    OBJECT IDENTIFIER ::= { unisevtModuleSwitchType 2231 } -- R9900-S-G,SR0MZSRP1A3A,Main Processing Unit(S Type),Domestic&Overseas Version
unisevtModuleSw-MOD21-G                    OBJECT IDENTIFIER ::= { unisevtModuleSwitchType 2232 } -- R9900-S1-G,SR0MZLF1DQM1,Service Processing Unit(MOD21-G),Domestic&Overseas Version
unisevtModuleSw-LSXM1SUPKR1                OBJECT IDENTIFIER ::= { unisevtModuleSwitchType 2233 } -- Supervisor Engine Module
unisevtModuleSw-LSXM1CDQ36KBR1             OBJECT IDENTIFIER ::= { unisevtModuleSwitchType 2234 } -- 36-Port 400GBASE Ethernet Optical Interface Module(QSFP-DD)(KB)
unisevtModuleSw-LSXM1CMUR1                 OBJECT IDENTIFIER ::= { unisevtModuleSwitchType 2235 } -- Board Monitor Unit
unisevtModuleSw-LSXM1SFK16GR1              OBJECT IDENTIFIER ::= { unisevtModuleSwitchType 2236 } -- Switch Fabric Board,Type K(Class G)
unisevtModuleSw-CSR05SRP1R3                OBJECT IDENTIFIER ::= { unisevtModuleSwitchType 2237 } -- CR16000-F,CSR05SRP1R3,Main Processing Unit(1R3)
unisevtModuleSw-MIC-TCP8L                  OBJECT IDENTIFIER ::= { unisevtModuleSwitchType 2238 } -- SR8800-X, SR0MDTCP8LA1,8-port OC-3c/OC-12c POS Optical Interface Card(SFP,LC),Domestic&Overseas Version
unisevtModuleSw-MIC-PSP4L                  OBJECT IDENTIFIER ::= { unisevtModuleSwitchType 2239 } -- SR8800-X , SR0MDPSP4LA1,4-port OC-48c/STM-16c POS Optical Interface Card(SFP,LC),Domestic&Overseas Version



unisevtModuleSw-LSUM1MPU06B8               OBJECT IDENTIFIER ::= { unisevtModuleSwitchType 2240 } -- Supervisor Engine Board
unisevtModuleSw-LSUM1MPU10C8               OBJECT IDENTIFIER ::= { unisevtModuleSwitchType 2241 } -- Supervisor Engine Board
unisevtModuleSw-LSUM1FAB06C8               OBJECT IDENTIFIER ::= { unisevtModuleSwitchType 2242 } -- Switching Fabric Module
unisevtModuleSw-LSUM1FAB10C8               OBJECT IDENTIFIER ::= { unisevtModuleSwitchType 2243 } -- Switching Fabric Module
unisevtModuleSw-LSUM1MPU10A8               OBJECT IDENTIFIER ::= { unisevtModuleSwitchType 2244 } -- Supervisor Engine Board
unisevtModuleSw-LSUM1FAB10A8               OBJECT IDENTIFIER ::= { unisevtModuleSwitchType 2245 } -- Switching Fabric Module
unisevtModuleSw-LSUM1TGS16FD8              OBJECT IDENTIFIER ::= { unisevtModuleSwitchType 2246 } -- 16-Port 10GBASE-R Ethernet SFP+ Optical Interface Board(FD)
unisevtModuleSw-LSUM1GP48FD8               OBJECT IDENTIFIER ::= { unisevtModuleSwitchType 2247 } -- 48-Port 1000BASE-X Optical Interface Board(SFP,LC)
unisevtModuleSw-LSUM1GT48FD8               OBJECT IDENTIFIER ::= { unisevtModuleSwitchType 2248 } -- 48-Port 10/100/1000BASE-T Electrical Interface Board(RJ45)
unisevtModuleSw-LSUM1GP40TS8FD8            OBJECT IDENTIFIER ::= { unisevtModuleSwitchType 2249 } -- 40-Port 1000BASE-X Optical Interface(SFP,LC)+8-Port 10GBASE-R Ethernet Optical Interface Board(SFP+,LC)
unisevtModuleSw-LSUM1TGS48RSH8             OBJECT IDENTIFIER ::= { unisevtModuleSwitchType 2250 } -- 48-Port 10GBASE-R Ethernet Optical Interface Module(SFP+,LC)(SH)
unisevtModuleSw-LSDM1GP48SE0-Z             OBJECT IDENTIFIER ::= { unisevtModuleSwitchType 2251 } -- 48-Port 1000BASE-X Ethernet Optical Interface Board(SFP,LC)
unisevtModuleSw-LSDM1GT48SE0-Z             OBJECT IDENTIFIER ::= { unisevtModuleSwitchType 2252 } -- 48-Port 10/100/1000BASE-T Ethernet Interface Board(RJ45)(SE)
unisevtModuleSw-LSDM1CGS8SE0-Z             OBJECT IDENTIFIER ::= { unisevtModuleSwitchType 2253 } -- 8-Port 100GBASE-R Ethernet Optical Interface Board(QSFP28,LC)
unisevtModuleSw-LSXM1SUP04T2               OBJECT IDENTIFIER ::= { unisevtModuleSwitchType 2254 } -- Supervisor Engine Board
unisevtModuleSw-LSXM1SFT04F2               OBJECT IDENTIFIER ::= { unisevtModuleSwitchType 2255 } -- Switch Fabric Board
unisevtModuleSw-LSXM1SFT08F2               OBJECT IDENTIFIER ::= { unisevtModuleSwitchType 2256 } -- Switch Fabric Board
unisevtModuleSw-RX-NIC-CQ2LF-E             OBJECT IDENTIFIER ::= { unisevtModuleSwitchType 2257 } -- 2-port 100G Flexible Ethernet Optical Interface Card(QSFP28,LC)(RX-NIC)
unisevtModuleSw-LSUM1TGS24FD8              OBJECT IDENTIFIER ::= { unisevtModuleSwitchType 2258 } -- 24-Port 10GBASE-R Ethernet Optical Interface Board(SFP+,LC)
unisevtModuleSw-RX-SPE400-E                OBJECT IDENTIFIER ::= { unisevtModuleSwitchType 2259 } -- Service Processing Unit(SPE400-E)
unisevtModuleSw-LSXM1SFK08GR1              OBJECT IDENTIFIER ::= { unisevtModuleSwitchType 2260 } -- Switch Fabric Board,Type K(Class G)
unisevtModuleSw-RX-SFC-16T1                OBJECT IDENTIFIER ::= { unisevtModuleSwitchType 2261 } -- 1Tbps Fabric Module(16)
unisevtModuleSw-LSCM3SUP03A0-Z             OBJECT IDENTIFIER ::= { unisevtModuleSwitchType 2262 } -- Supervisor Engine Board
unisevtModuleSw-LSCM3MPUS06A0-Z            OBJECT IDENTIFIER ::= { unisevtModuleSwitchType 2263 } -- Supervisor Engine Board
unisevtModuleSw-LSCM3GT48SC0-Z             OBJECT IDENTIFIER ::= { unisevtModuleSwitchType 2264 } -- 48-Port 10/100/1000BASE-T Electrical Interface Board(RJ45)(SC)
unisevtModuleSw-LSCM3TGS48SE0-Z            OBJECT IDENTIFIER ::= { unisevtModuleSwitchType 2265 } -- 48-Port 10GBASE-R Ethernet SFP+ Optical Interface Board(SE)
unisevtModuleSw-LSCM3QGS8CSSE0-Z           OBJECT IDENTIFIER ::= { unisevtModuleSwitchType 2266 } -- 8-Port 40GBASE-R QSFP+ + 4-Port 100GBASE-R QSFP28 Optical Interface Board(SE)
unisevtModuleSw-LSDM3QGS12SE0-Z            OBJECT IDENTIFIER ::= { unisevtModuleSwitchType 2267 } -- 12-Port 40GBASE-R Ethernet QSFP+ Optical Interface Board(SE)
unisevtModuleSw-LSDM3TGS48SE0-Z            OBJECT IDENTIFIER ::= { unisevtModuleSwitchType 2268 } -- 48-Port 10GBASE-R Ethernet SFP+ Optical Interface Board(SE)
unisevtModuleSw-LSDM3SUPA0-Z               OBJECT IDENTIFIER ::= { unisevtModuleSwitchType 2269 } -- Supervisor Engine Board
unisevtModuleSw-LSDM3FAB08D0-Z             OBJECT IDENTIFIER ::= { unisevtModuleSwitchType 2270 } -- Switch Fabric Board
unisevtModuleSw-LSDM3GT24GPSE0-Z           OBJECT IDENTIFIER ::= { unisevtModuleSwitchType 2271 } -- 24-Port 10/100/1000BASE-T Electrical Interface(RJ45)+24-Port 1000BASE-X Ethernet Optical Interface Board(SFP,LC)(SE)
unisevtModuleSw-LSDM3GP48SE0-Z             OBJECT IDENTIFIER ::= { unisevtModuleSwitchType 2272 } -- 48-Port 1000BASE-X Ethernet Optical Interface Board(SFP,LC)
unisevtModuleSw-LSDM3GT48SE0-Z             OBJECT IDENTIFIER ::= { unisevtModuleSwitchType 2273 } -- 48-Port 10/100/1000BASE-T Ethernet Interface Board(RJ45)(SE)
unisevtModuleSw-LSDM3CGS8SE0-Z             OBJECT IDENTIFIER ::= { unisevtModuleSwitchType 2274 } -- 8-Port 100GBASE-R Ethernet Optical Interface Board(QSFP28,LC)
unisevtModuleSw-RX-CEPC-CQ8LF              OBJECT IDENTIFIER ::= { unisevtModuleSwitchType 2275 } -- 8-port 100G Flexible Ethernet Optical Interface Line Processing Unit(QSFP28,LC)
unisevtModuleSw-RX-SPE200-E                OBJECT IDENTIFIER ::= { unisevtModuleSwitchType 2276 } -- Service Processing Unit(SPE200-E)

unisevtModuleSw-DSH7503-MP                 OBJECT IDENTIFIER ::= { unisevtModuleSwitchType 2277 } -- Supervisor Engine Board
unisevtModuleSw-DSH7506-MP                 OBJECT IDENTIFIER ::= { unisevtModuleSwitchType 2278 } -- Supervisor Engine Board
unisevtModuleSw-DSH7510-MP                 OBJECT IDENTIFIER ::= { unisevtModuleSwitchType 2279 } -- Supervisor Engine Board
unisevtModuleSw-DSH7500-48T-P              OBJECT IDENTIFIER ::= { unisevtModuleSwitchType 2280 } -- 48-Port 1000Base-T Gigabit Ethernet Interface Board(RJ45)-POE
unisevtModuleSw-DSH7500-16X                OBJECT IDENTIFIER ::= { unisevtModuleSwitchType 2281 } -- 16-Port 10GBASE-R Ethernet SFP+ Optical Interface Board
unisevtModuleSw-DSH7500-48F                OBJECT IDENTIFIER ::= { unisevtModuleSwitchType 2282 } -- 48-Port 1000BASE-X Optical Interface Board(SFP,LC)
unisevtModuleSw-DSH7500-12QX4Q28           OBJECT IDENTIFIER ::= { unisevtModuleSwitchType 2283 } -- 12-Port 40GBASE-R QSFP+ or 4-Port 100GBASE-R QSFP28 Optical Interface Board
unisevtModuleSw-DSH7500-24F4X              OBJECT IDENTIFIER ::= { unisevtModuleSwitchType 2284 } -- 24-Port GE Optical Interface(SFP,LC)+4-Port 10GE Optical Interface Board(SFP+,LC)
unisevtModuleSw-DSH7500-24QX               OBJECT IDENTIFIER ::= { unisevtModuleSwitchType 2285 } -- 24-Port 40GBASE-R Ethernet QSFP+ Optical Interface Board
unisevtModuleSw-DSH7500-24T4X              OBJECT IDENTIFIER ::= { unisevtModuleSwitchType 2286 } -- 24-Port 1000Base-T Gigabit Ethernet Interface Board(RJ45)+4-Port 10GE Optical Interface Board(SFP+,LC)
unisevtModuleSw-DSH7500-24X2QX1Q28         OBJECT IDENTIFIER ::= { unisevtModuleSwitchType 2287 } -- 24-Port 10GBASE-R Optical Interface(SFP+,LC)+2-Port 40GBASE-R Optical Interface Board(QSFP+) or 1-Port 100GBASE-R Optical Interface Board(QSFP28)
unisevtModuleSw-DSH7500-2Q28               OBJECT IDENTIFIER ::= { unisevtModuleSwitchType 2288 } -- 2-Port 100GBASE-R Ethernet QSFP28 Optical Interface Board
unisevtModuleSw-DSH7500-44F4X              OBJECT IDENTIFIER ::= { unisevtModuleSwitchType 2289 } -- 44-Port GE Optical Interface(SFP,LC)+4-Port 10GE Optical Interface Board(SFP+,LC)
unisevtModuleSw-DSH7500-48T                OBJECT IDENTIFIER ::= { unisevtModuleSwitchType 2290 } -- 48-Port 10/100/1000BASE-T Electrical Interface Board(RJ45)
unisevtModuleSw-DSH7500-48X                OBJECT IDENTIFIER ::= { unisevtModuleSwitchType 2291 } -- 48-Port 10GBASE-R Ethernet SFP+ Optical Interface Board
unisevtModuleSw-LSWM2-iMC                  OBJECT IDENTIFIER ::= { unisevtModuleSwitchType 2292 } -- Intelligent Network Management Module
unisevtModuleSw-LSWM2ZQP2P-Z               OBJECT IDENTIFIER ::= { unisevtModuleSwitchType 2293 } -- 2-Port QSFP28 Interface Module
unisevtModuleSw-LSWM2ZSP4P-Z               OBJECT IDENTIFIER ::= { unisevtModuleSwitchType 2294 } -- 4-Port SFP28 Interface Module
unisevtModuleSw-LSWM2ZSP8P-Z               OBJECT IDENTIFIER ::= { unisevtModuleSwitchType 2295 } -- 8-Port SFP28 Interface Module
unisevtModuleSw-LSDM3SUP04A0-Z             OBJECT IDENTIFIER ::= { unisevtModuleSwitchType 2296 } -- Supervisor Engine Board
unisevtModuleSw-LSDM3FAB04E0-Z             OBJECT IDENTIFIER ::= { unisevtModuleSwitchType 2297 } -- Switching Fabric Module
unisevtModuleSw-LSDM3FAB08E0-Z             OBJECT IDENTIFIER ::= { unisevtModuleSwitchType 2298 } -- Switching Fabric Module
unisevtModuleSw-LSDM3QGS36SE0-Z            OBJECT IDENTIFIER ::= { unisevtModuleSwitchType 2299 } -- 36-Port 40GBASE-R Ethernet QSFP+ Optical Interface Board
unisevtModuleSw-LSDM3CGS12SE0-Z            OBJECT IDENTIFIER ::= { unisevtModuleSwitchType 2300 } -- 12-Port 100GBASE-R Ethernet QSFP28 Optical Interface Board
unisevtModuleSw-LSQM2XPT12TSFD0            OBJECT IDENTIFIER ::= { unisevtModuleSwitchType 2301 } -- 12-Port 10/1GBASE-PR/PRX Ethernet Optical(SFP+,LC) and 8-Port 10GBASE-R SFP+ Optical Interface Board
unisevtModuleSw-CSPEX-1702X                OBJECT IDENTIFIER ::= { unisevtModuleSwitchType 2302 } -- Service Processing Unit(1702X)
unisevtModuleSw-CSR05SRP1P1                OBJECT IDENTIFIER ::= { unisevtModuleSwitchType 2303 } -- H3C CR16000-F CSR05SRP1P1 Main Processing Unit(1P1)
unisevtModuleSw-NIC-GP24L1                 OBJECT IDENTIFIER ::= { unisevtModuleSwitchType 2304 } -- 24-port 1000BASE-X Ethernet Optical Interface Card(SFP,LC)(NIC)
unisevtModuleSw-NIC-GP24LA                 OBJECT IDENTIFIER ::= { unisevtModuleSwitchType 2305 } -- 24-port 1000BASE-X Ethernet Optical Interface Card A(SFP,LC)(NIC)
unisevtModuleSw-NIC-XP20L1                 OBJECT IDENTIFIER ::= { unisevtModuleSwitchType 2306 } -- 20-port 10GBASE-R/W Ethernet Optical Interface Card(SFP+,LC)(NIC)
unisevtModuleSw-NIC-XP20LA                 OBJECT IDENTIFIER ::= { unisevtModuleSwitchType 2307 } -- 20-port 10GBASE-R/W Ethernet Optical Interface Card A(SFP+,LC)(NIC)
unisevtModuleSw-RX-NIC-LGQ4LF              OBJECT IDENTIFIER ::= { unisevtModuleSwitchType 2308 } -- 4-port 50G Flexible Ethernet Optical Interface Card(QSFP28,LC)(RX-NIC)
unisevtModuleSw-CSR05SRP1R3A               OBJECT IDENTIFIER ::= { unisevtModuleSwitchType 2309 } -- H3C CR16000-FA Main Processing Unit(1R3A)
unisevtModuleSw-CEPC-CQ8L                  OBJECT IDENTIFIER ::= { unisevtModuleSwitchType 2310 } -- 8-port 100G Ethernet Optical Interface Line Processing Unit(QSFP28,LC)
unisevtModuleSw-CEPC-CQ8LA                 OBJECT IDENTIFIER ::= { unisevtModuleSwitchType 2311 } -- 8-port 100G Ethernet Optical Interface Line Processing Unit A(QSFP28,LC)
unisevtModuleSw-CSPEX-1802XA               OBJECT IDENTIFIER ::= { unisevtModuleSwitchType 2312 } -- Service Processing Unit(1802XA)
unisevtModuleSw-CSPEX-1802XB               OBJECT IDENTIFIER ::= { unisevtModuleSwitchType 2313 } -- Service Processing Unit(1802XB)
unisevtModuleSw-CSPEX-1502XA               OBJECT IDENTIFIER ::= { unisevtModuleSwitchType 2314 } -- Service Processing Unit(1502XA)
unisevtModuleSw-CSPEX-1512XB               OBJECT IDENTIFIER ::= { unisevtModuleSwitchType 2315 } -- Service Processing Unit(1512XB)

unisevtModuleSw-NIC-XP20L1A                OBJECT IDENTIFIER ::= { unisevtModuleSwitchType 2317 } -- 20-port 10GBASE-R/W Ethernet Optical Interface Card A(SFP+,LC)(NIC)
unisevtModuleSw-NIC-XP20L1B                OBJECT IDENTIFIER ::= { unisevtModuleSwitchType 2318 } -- 20-port 10GBASE-R/W Ethernet Optical Interface Card B(SFP+,LC)(NIC)

unisevtModuleSw-NIC-GP24L1A                OBJECT IDENTIFIER ::= { unisevtModuleSwitchType 2320 } -- 24-port 1000BASE-X Ethernet Optical Interface Card A(SFP,LC)(NIC)
unisevtModuleSw-NIC-GP24L1B                OBJECT IDENTIFIER ::= { unisevtModuleSwitchType 2321 } -- 24-port 1000BASE-X Ethernet Optical Interface Card B(SFP,LC)(NIC)
unisevtModuleSw-NIC-CQ2LA                  OBJECT IDENTIFIER ::= { unisevtModuleSwitchType 2322 } -- 2-port 100G Ethernet Optical Interface Card A(QSFP28)(NIC)
unisevtModuleSw-NIC-CQ2LB                  OBJECT IDENTIFIER ::= { unisevtModuleSwitchType 2323 } -- 2-port 100G Ethernet Optical Interface Card B(QSFP28)(NIC)
unisevtModuleSw-NIC-XP5LA                  OBJECT IDENTIFIER ::= { unisevtModuleSwitchType 2324 } -- 5-port 10GBASE-R/W Ethernet Optical Interface Card A(SFP+,LC)(NIC)
unisevtModuleSw-NIC-XP5LB                  OBJECT IDENTIFIER ::= { unisevtModuleSwitchType 2325 } -- 5-port 10GBASE-R/W Ethernet Optical Interface Card B(SFP+,LC)(NIC)
unisevtModuleSw-CSFC-16T1                  OBJECT IDENTIFIER ::= { unisevtModuleSwitchType 2326 } -- CR16018-F Fabric Module(T Type)
unisevtModuleSw-LSUM1MPUS10XEC0            OBJECT IDENTIFIER ::= { unisevtModuleSwitchType 2327 } -- Supervisor Engine Board
unisevtModuleSw-LSUM1MPUS10XEC3            OBJECT IDENTIFIER ::= { unisevtModuleSwitchType 2328 } -- Supervisor Engine Board
unisevtModuleSw-LSUM1MPUS06XEC3            OBJECT IDENTIFIER ::= { unisevtModuleSwitchType 2329 } -- Supervisor Engine Board
unisevtModuleSw-LSUM1FAB10XEC0             OBJECT IDENTIFIER ::= { unisevtModuleSwitchType 2330 } -- Switching Fabric Module
unisevtModuleSw-LSCM2MPUS06AS0-Z           OBJECT IDENTIFIER ::= { unisevtModuleSwitchType 2331 } -- Supervisor Engine Board
unisevtModuleSw-LSCM2CGT24TSSC0-Z          OBJECT IDENTIFIER ::= { unisevtModuleSwitchType 2332 } -- Supervisor Engine Board With 24-Port 10/100/1000BASE-T Ethernet Interface+4-Port 10GBASE-R Ethernet SFP+ Optical Interfaces
unisevtModuleSw-LSCM2CGP24TSSC0-Z          OBJECT IDENTIFIER ::= { unisevtModuleSwitchType 2333 } -- Supervisor Engine Board With 24-Port 1000BASE-X Ethernet SFP Optical Interface+4-Port 10GBASE-R Ethernet SFP+ Optical Interfaces
unisevtModuleSw-LSCM2CTGS12GTSC0-Z         OBJECT IDENTIFIER ::= { unisevtModuleSwitchType 2334 } -- Supervisor Engine Board With 16-Port 10/100/1000BASE-T Ethernet Interface+12-Port 10GBASE-R Ethernet SFP+ Optical Interfaces
unisevtModuleSw-LSCM2CTGS12GPSC0-Z         OBJECT IDENTIFIER ::= { unisevtModuleSwitchType 2335 } -- Supervisor Engine Board With 16-Port 1000BASE-X Ethernet SFP Optical Interface+12-Port 10GBASE-R Ethernet SFP+ Optical Interfaces
unisevtModuleSw-LSCM2GT24GPTSSC0-Z         OBJECT IDENTIFIER ::= { unisevtModuleSwitchType 2336 } -- 24-Port 10/100/1000BASE-T Ethernet Interface Board(RJ45)+20-Port 1000BASE-X Ethernet SFP Optical Interface(SFP,LC)+4-Port 10GBASE-R Optical Interface Board(SFP+,LC)(SC)
unisevtModuleSw-LSCM2GT24GPSC0-Z           OBJECT IDENTIFIER ::= { unisevtModuleSwitchType 2337 } -- 24-Port 10/100/1000BASE-T Ethernet Interface Board(RJ45)+8-Port 1000BASE-X Ethernet SFP Optical Interface(SFP,LC)(SC)
unisevtModuleSw-LSCM2GP24GTSC0-Z           OBJECT IDENTIFIER ::= { unisevtModuleSwitchType 2338 } -- 8-Port 10/100/1000BASE-T Ethernet Interface Board(RJ45)+24-Port 1000BASE-X Ethernet SFP Optical Interface(SFP,LC)(SC)
unisevtModuleSw-LSCM2GT48SC0-Z             OBJECT IDENTIFIER ::= { unisevtModuleSwitchType 2339 } -- 48-Port 10/100/1000BASE-T Ethernet Interface Board(RJ45)(SC)
unisevtModuleSw-LSCM2GP48SC0-Z             OBJECT IDENTIFIER ::= { unisevtModuleSwitchType 2340 } -- 48-Port 1000BASE-X Ethernet Optical Interface Board(SFP,LC)
unisevtModuleSw-LSCM2TGS16GPSC0-Z          OBJECT IDENTIFIER ::= { unisevtModuleSwitchType 2341 } -- 24-Port 1000BASE-R Ethernet Optical Interface(SFP,LC)+16-Port 10GBASE-R Ethernet Optical Interface Board(SFP+,LC)
unisevtModuleSw-LSWM2SP2PM-Z               OBJECT IDENTIFIER ::= { unisevtModuleSwitchType 2342 } -- 2-Port SFP+ Interface Module with MACsec
unisevtModuleSw-LSWM2QP2P-Z                OBJECT IDENTIFIER ::= { unisevtModuleSwitchType 2343 } -- 2-Port QSFP+ Interface Module
unisevtModuleSw-LSWM2SP8P-Z                OBJECT IDENTIFIER ::= { unisevtModuleSwitchType 2344 } -- 8-Port SFP+ Interface Module
unisevtModuleSw-LSCM2MPUS06AS0             OBJECT IDENTIFIER ::= { unisevtModuleSwitchType 2345 }  -- Supervisor Engine Board
unisevtModuleSw-LSCM2CGT24TSSC0            OBJECT IDENTIFIER ::= { unisevtModuleSwitchType 2346 }  -- Supervisor Engine Board With 24-Port 10/100/1000BASE-T Ethernet Interface+4-Port 10GBASE-R Ethernet SFP+ Optical Interfaces
unisevtModuleSw-LSCM2CGP24TSSC0            OBJECT IDENTIFIER ::= { unisevtModuleSwitchType 2347 }  -- Supervisor Engine Board With 24-Port 1000BASE-X Ethernet SFP Optical Interface+4-Port 10GBASE-R Ethernet SFP+ Optical Interfaces
unisevtModuleSw-LSCM2CTGS12GTSC0           OBJECT IDENTIFIER ::= { unisevtModuleSwitchType 2348 }  -- Supervisor Engine Board With 16-Port 10/100/1000BASE-T Ethernet Interface+12-Port 10GBASE-R Ethernet SFP+ Optical Interfaces
unisevtModuleSw-LSCM2CTGS12GPSC0           OBJECT IDENTIFIER ::= { unisevtModuleSwitchType 2349 }  -- Supervisor Engine Board With 16-Port 1000BASE-X Ethernet SFP Optical Interface+12-Port 10GBASE-R Ethernet SFP+ Optical Interfaces
unisevtModuleSw-LSCM2GT24GPTSSC0           OBJECT IDENTIFIER ::= { unisevtModuleSwitchType 2350 }  -- 24-Port 10/100/1000BASE-T Ethernet Interface Board(RJ45)+20-Port 1000BASE-X Ethernet SFP Optical Interface(SFP,LC)+4-Port 10GBASE-R Optical Interface Board(SFP+,LC)(SC)
unisevtModuleSw-LSCM2GT24GPSC0             OBJECT IDENTIFIER ::= { unisevtModuleSwitchType 2351 }  -- 24-Port 10/100/1000BASE-T Ethernet Interface Board(RJ45)+8-Port 1000BASE-X Ethernet SFP Optical Interface(SFP,LC)(SC)
unisevtModuleSw-LSCM2GP24GTSC0             OBJECT IDENTIFIER ::= { unisevtModuleSwitchType 2352 }  -- 8-Port 10/100/1000BASE-T Ethernet Interface Board(RJ45)+24-Port 1000BASE-X Ethernet SFP Optical Interface(SFP,LC)(SC)
unisevtModuleSw-LSCM2GT48SC0               OBJECT IDENTIFIER ::= { unisevtModuleSwitchType 2353 }  -- 48-Port 10/100/1000BASE-T Ethernet Interface Board(RJ45)(SC)
unisevtModuleSw-LSCM2GP48SC0               OBJECT IDENTIFIER ::= { unisevtModuleSwitchType 2354 }  -- 48-Port 1000BASE-X Ethernet Optical Interface Board(SFP,LC)
unisevtModuleSw-LSCM2TGS16GPSC0            OBJECT IDENTIFIER ::= { unisevtModuleSwitchType 2355 }  -- 24-Port 1000BASE-R Ethernet Optical Interface(SFP,LC)+16-Port 10GBASE-R Ethernet Optical Interface Board(SFP+,LC)
-- Here define submodule for routers
unisevtSubModuleRouter       OBJECT IDENTIFIER ::= { unisevtModule 5 }


-- Here define submodule for switches
unisevtSubModuleSwitch       OBJECT IDENTIFIER ::= { unisevtModule 6 }
-- Here define Compact Flash
unisevtModuleCFCard          OBJECT IDENTIFIER ::= { unisevtModule 7 }

-- Here define Secure Digital Memory Card
unisevtModuleSDCard          OBJECT IDENTIFIER ::= { unisevtModule 8 }

--
-- unisevtPort section:
--
unisevtPort          OBJECT IDENTIFIER ::= { unisEntityVendortypeObjects 10 }

unisevtPortUnknownPorts      OBJECT IDENTIFIER ::= { unisevtPort 1 }
unisevtPortCommonPorts       OBJECT IDENTIFIER ::= { unisevtPort 2 }
unisevtPortRouterType        OBJECT IDENTIFIER ::= { unisevtPort 3 }
unisevtPortSwitchType        OBJECT IDENTIFIER ::= { unisevtPort 4 }


-- Below are ports used to router
unisevtPortRt-Async          OBJECT IDENTIFIER ::= { unisevtPortRouterType 1 }    -- Async interface
unisevtPortRt-Analogmodem    OBJECT IDENTIFIER ::= { unisevtPortRouterType 2 }    -- Analog modem interface
unisevtPortRt-Atm            OBJECT IDENTIFIER ::= { unisevtPortRouterType 3 }
unisevtPortRt-AtmAdsl        OBJECT IDENTIFIER ::= { unisevtPortRouterType 4 }
unisevtPortRt-AtmShdsl       OBJECT IDENTIFIER ::= { unisevtPortRouterType 5 }
unisevtPortRt-AtmE1          OBJECT IDENTIFIER ::= { unisevtPortRouterType 6 }
unisevtPortRt-AtmT1          OBJECT IDENTIFIER ::= { unisevtPortRouterType 7 }
unisevtPortRt-AtmE3          OBJECT IDENTIFIER ::= { unisevtPortRouterType 8 }
unisevtPortRt-AtmT3          OBJECT IDENTIFIER ::= { unisevtPortRouterType 9 }
unisevtPortRt-Atm622M        OBJECT IDENTIFIER ::= { unisevtPortRouterType 10 }
unisevtPortRt-AtmImaE1       OBJECT IDENTIFIER ::= { unisevtPortRouterType 11 }
unisevtPortRt-AtmImaT1       OBJECT IDENTIFIER ::= { unisevtPortRouterType 12 }
unisevtPortRt-Atm25M         OBJECT IDENTIFIER ::= { unisevtPortRouterType 13 }
unisevtPortRt-Bri            OBJECT IDENTIFIER ::= { unisevtPortRouterType 14 }
unisevtPortRt-Console        OBJECT IDENTIFIER ::= { unisevtPortRouterType 15 }
unisevtPortRt-E1             OBJECT IDENTIFIER ::= { unisevtPortRouterType 16 }
unisevtPortRt-E3             OBJECT IDENTIFIER ::= { unisevtPortRouterType 17 }
unisevtPortRt-T1             OBJECT IDENTIFIER ::= { unisevtPortRouterType 18 }
unisevtPortRt-T3             OBJECT IDENTIFIER ::= { unisevtPortRouterType 19 }
unisevtPortRt-Cpos           OBJECT IDENTIFIER ::= { unisevtPortRouterType 20 }
unisevtPortRt-Ethernet       OBJECT IDENTIFIER ::= { unisevtPortRouterType 21 }
unisevtPortRt-Serial         OBJECT IDENTIFIER ::= { unisevtPortRouterType 22 }
unisevtPortRt-E1f            OBJECT IDENTIFIER ::= { unisevtPortRouterType 23 }
unisevtPortRt-T1f            OBJECT IDENTIFIER ::= { unisevtPortRouterType 24 }
unisevtPortRt-Pos            OBJECT IDENTIFIER ::= { unisevtPortRouterType 25 }
unisevtPortRt-Ge             OBJECT IDENTIFIER ::= { unisevtPortRouterType 26 }
unisevtPortRt-Aux            OBJECT IDENTIFIER ::= { unisevtPortRouterType 27 }
-- unisevtPortRt-Null         OBJECT IDENTIFIER ::= { unisevtPortRouterType 28 }   reserved
-- unisevtPortRt-Max          OBJECT IDENTIFIER ::= { unisevtPortRouterType 29 }   reserved
unisevtPortRt-VG-Fxs         OBJECT IDENTIFIER ::= { unisevtPortRouterType 30 }
unisevtPortRt-VG-Fxo         OBJECT IDENTIFIER ::= { unisevtPortRouterType 31 }
unisevtPortRt-VG-E1vi        OBJECT IDENTIFIER ::= { unisevtPortRouterType 32 }
unisevtPortRt-VG-T1vi        OBJECT IDENTIFIER ::= { unisevtPortRouterType 33 }
unisevtPortRt-Usb            OBJECT IDENTIFIER ::= { unisevtPortRouterType 34 }
unisevtPortRt-Ndec           OBJECT IDENTIFIER ::= { unisevtPortRouterType 35 }   -- NDEC port, Encrypt card version 1.0
unisevtPortRt-Cavium         OBJECT IDENTIFIER ::= { unisevtPortRouterType 36 }   -- NDEC port, Encrypt card version 2.0
unisevtPortRt-Fcm            OBJECT IDENTIFIER ::= { unisevtPortRouterType 37 }   -- POS/Fast connect module port
unisevtPortRt-E1vi           OBJECT IDENTIFIER ::= { unisevtPortRouterType 38 }   -- E1VI port
unisevtPortRt-T1vi           OBJECT IDENTIFIER ::= { unisevtPortRouterType 39 }   -- T1VI port
unisevtPortRt-Vi             OBJECT IDENTIFIER ::= { unisevtPortRouterType 40 }   -- Voice port
unisevtPortRt-Adls2Plus      OBJECT IDENTIFIER ::= { unisevtPortRouterType 41 }   -- ADSL2Plus port
unisevtPortRt-RADIO-AG       OBJECT IDENTIFIER ::= { unisevtPortRouterType 42 }   -- 802.11ag Radio port
unisevtPortRt-1exp           OBJECT IDENTIFIER ::= { unisevtPortRouterType 43 }   -- 10GBASE-R/W Ethernet port
unisevtPortRt-G-SHDSL-BIS    OBJECT IDENTIFIER ::= { unisevtPortRouterType 44 }   -- 4 wire G.SHDSL.BIS interface
unisevtPortRt-ONU-1000BASE-BX-SFF-SC    OBJECT IDENTIFIER ::= { unisevtPortRouterType 45 }   -- 1000 BASE-BX SFF SC ONU Interface
unisevtPortRt-CELLULAR       OBJECT IDENTIFIER ::= { unisevtPortRouterType 46 }   -- 3G Wireless WAN Interface
unisevtPortRt-CELLULAR-ETHERNET         OBJECT IDENTIFIER ::= { unisevtPortRouterType 47 }   -- 3G Wireless WAN Interface for Ethernet mode
unisevtPortRt-VGe            OBJECT IDENTIFIER ::= { unisevtPortRouterType 48 } -- virtual Ge port
unisevtPortRt-VXGe           OBJECT IDENTIFIER ::= { unisevtPortRouterType 49 } -- virtual XGe port
unisevtPortRt-Xpos           OBJECT IDENTIFIER ::= { unisevtPortRouterType 50 } -- 10G POS port
unisevtPortRt-Fge            OBJECT IDENTIFIER ::= { unisevtPortRouterType 51 } -- 40G Ethernet port
unisevtPortRt-XGe            OBJECT IDENTIFIER ::= { unisevtPortRouterType 52 } -- 10G Ethernet port
unisevtPortRt-HgeQsfp28Lc    OBJECT IDENTIFIER ::= { unisevtPortRouterType 53 } -- 100G Ethernet Port with QSFP28 Form Factor and LC Connector
unisevtPortRt-HgeCfp2Lc      OBJECT IDENTIFIER ::= { unisevtPortRouterType 54 } -- 100G Ethernet Port with CFP2 Form Factor and LC Connector
unisevtPortRt-HgeCfpLc       OBJECT IDENTIFIER ::= { unisevtPortRouterType 55 } -- 100G Ethernet Port with CFP Form Factor and LC Connector
unisevtPortRt-GeM12          OBJECT IDENTIFIER ::= { unisevtPortRouterType 56 } -- Gigabit Ethernet Port with M12 Form Connector
unisevtPortRt-VMEth          OBJECT IDENTIFIER ::= { unisevtPortRouterType 57 } -- Virtual Machine Ethernet Port
unisevtPortRt-FiberGe        OBJECT IDENTIFIER ::= { unisevtPortRouterType 58 } -- 1G Fiber Ethernet port
unisevtPortRt-GeOptic        OBJECT IDENTIFIER ::= { unisevtPortRouterType 59 }
unisevtPortRt-25Ge           OBJECT IDENTIFIER ::= { unisevtPortRouterType 60 } -- 25G Ethernet port with SFP28
unisevtPortRt-50Ge           OBJECT IDENTIFIER ::= { unisevtPortRouterType 61 } -- 50G Ethernet port with QSFP28
unisevtPortRt-FlexE-50-100G  OBJECT IDENTIFIER ::= { unisevtPortRouterType 62 } -- 50-100G FlexE port with QSFP28
unisevtPortRt-50-100Ge       OBJECT IDENTIFIER ::= { unisevtPortRouterType 63 } -- 50-100G Ethernet port with QSFP28
unisevtPortRt-FlexE          OBJECT IDENTIFIER ::= { unisevtPortRouterType 64 } -- FlexE port with QSFP28
unisevtPortRt-100GBase-F     OBJECT IDENTIFIER ::= { unisevtPortRouterType 65 } -- 100G Ethernet port with QSFP28
unisevtPortRt-FlexE-50G      OBJECT IDENTIFIER ::= { unisevtPortRouterType 66 } -- 50G FlexE port with QSFP28
unisevtPortRt-Async-Phoniex  OBJECT IDENTIFIER ::= { unisevtPortRouterType 67 } -- Async interface

-- Below are ports used to switches
--unisevtPortSw-Unknown              OBJECT IDENTIFIER ::= { unisevtPortSwitchType 0 }
unisevtPortSw-10or100M               OBJECT IDENTIFIER ::= { unisevtPortSwitchType 1 }
unisevtPortSw-1000BaseLxSm           OBJECT IDENTIFIER ::= { unisevtPortSwitchType 2 }
unisevtPortSw-1000BaseSxMm           OBJECT IDENTIFIER ::= { unisevtPortSwitchType 3 }
unisevtPortSw-1000BaseTx             OBJECT IDENTIFIER ::= { unisevtPortSwitchType 4 }
unisevtPortSw-100MSinglemodeFx       OBJECT IDENTIFIER ::= { unisevtPortSwitchType 5 }
unisevtPortSw-100MMultimodeFx        OBJECT IDENTIFIER ::= { unisevtPortSwitchType 6 }
unisevtPortSw-100M100BaseTx          OBJECT IDENTIFIER ::= { unisevtPortSwitchType 7 }
unisevtPortSw-100MHub                OBJECT IDENTIFIER ::= { unisevtPortSwitchType 8 }
unisevtPortSw-Vdsl                   OBJECT IDENTIFIER ::= { unisevtPortSwitchType 9 }
unisevtPortSw-Stack                  OBJECT IDENTIFIER ::= { unisevtPortSwitchType 10 }
unisevtPortSw-1000BaseZenithFx       OBJECT IDENTIFIER ::= { unisevtPortSwitchType 11 }
unisevtPortSw-1000BaseLongFx         OBJECT IDENTIFIER ::= { unisevtPortSwitchType 12 }
unisevtPortSw-Adsl                   OBJECT IDENTIFIER ::= { unisevtPortSwitchType 13 }
unisevtPortSw-10or100MDb             OBJECT IDENTIFIER ::= { unisevtPortSwitchType 14 }
unisevtPortSw-10GBaseLrSm            OBJECT IDENTIFIER ::= { unisevtPortSwitchType 15 }
unisevtPortSw-10GBaseLx4Mm           OBJECT IDENTIFIER ::= { unisevtPortSwitchType 16 }
unisevtPortSw-10GBaseLx4Sm           OBJECT IDENTIFIER ::= { unisevtPortSwitchType 17 }
unisevtPortSw-100MLongFx             OBJECT IDENTIFIER ::= { unisevtPortSwitchType 18 }
unisevtPortSw-1000BaseCx             OBJECT IDENTIFIER ::= { unisevtPortSwitchType 19 }
unisevtPortSw-1000BaseZenithFxLc     OBJECT IDENTIFIER ::= { unisevtPortSwitchType 20 }
unisevtPortSw-1000BaseLongFxLc       OBJECT IDENTIFIER ::= { unisevtPortSwitchType 21 }
unisevtPortSw-100MSmFxSc             OBJECT IDENTIFIER ::= { unisevtPortSwitchType 22 }
unisevtPortSw-100MMmFxSc             OBJECT IDENTIFIER ::= { unisevtPortSwitchType 23 }
unisevtPortSw-100MSmFxLc             OBJECT IDENTIFIER ::= { unisevtPortSwitchType 24 }
unisevtPortSw-100MMmFxLc             OBJECT IDENTIFIER ::= { unisevtPortSwitchType 25 }
unisevtPortSw-GbicNoConnector        OBJECT IDENTIFIER ::= { unisevtPortSwitchType 26 }
unisevtPortSw-Gbic1000BaseT          OBJECT IDENTIFIER ::= { unisevtPortSwitchType 27 }
unisevtPortSw-Gbic1000BaseLx         OBJECT IDENTIFIER ::= { unisevtPortSwitchType 28 }
unisevtPortSw-Gbic1000BaseSx         OBJECT IDENTIFIER ::= { unisevtPortSwitchType 29 }
unisevtPortSw-Gbic1000BaseZx         OBJECT IDENTIFIER ::= { unisevtPortSwitchType 30 }
unisevtPortSw-ComboNoConnector       OBJECT IDENTIFIER ::= { unisevtPortSwitchType 31 }
unisevtPortSw-Combo1000BaseLx        OBJECT IDENTIFIER ::= { unisevtPortSwitchType 32 }
unisevtPortSw-Combo1000BaseLxFiber   OBJECT IDENTIFIER ::= { unisevtPortSwitchType 33 }
unisevtPortSw-Combo1000BaseLxCopper  OBJECT IDENTIFIER ::= { unisevtPortSwitchType 34 }
unisevtPortSw-Combo1000BaseSx        OBJECT IDENTIFIER ::= { unisevtPortSwitchType 35 }
unisevtPortSw-Combo1000BaseSxFiber   OBJECT IDENTIFIER ::= { unisevtPortSwitchType 36 }
unisevtPortSw-Combo1000BaseSxCopper  OBJECT IDENTIFIER ::= { unisevtPortSwitchType 37 }
unisevtPortSw-Combo1000BaseZx        OBJECT IDENTIFIER ::= { unisevtPortSwitchType 38 }
unisevtPortSw-Combo1000BaseZxFiber   OBJECT IDENTIFIER ::= { unisevtPortSwitchType 39 }
unisevtPortSw-Combo1000BaseZxCopper  OBJECT IDENTIFIER ::= { unisevtPortSwitchType 40 }
unisevtPortSw-155PosSxMmf            OBJECT IDENTIFIER ::= { unisevtPortSwitchType 41 }
unisevtPortSw-155PosLxSmf            OBJECT IDENTIFIER ::= { unisevtPortSwitchType 42 }

-- added by Garibaldi
unisevtPortSw-1000BASE-T             OBJECT IDENTIFIER ::= { unisevtPortSwitchType 43 }  -- 1000 Base-T Port
unisevtPortSw-1000BASE-SX-SFP        OBJECT IDENTIFIER ::= { unisevtPortSwitchType 44 }  -- 1000 Base-SX SFP Port
unisevtPortSw-1000BASE-LX-SFP        OBJECT IDENTIFIER ::= { unisevtPortSwitchType 45 }  -- 1000 Base-LX SFP Port
unisevtPortSw-1000BASE-T-AN-SFP      OBJECT IDENTIFIER ::= { unisevtPortSwitchType 46 }  -- 1000 Base-T AN SFP Port
unisevtPortSw-10GBASE-LX4-XENPAK     OBJECT IDENTIFIER ::= { unisevtPortSwitchType 47 }  -- 10G Base-LX4 XENPAK Port
unisevtPortSw-10GBASE-LR-XENPAK      OBJECT IDENTIFIER ::= { unisevtPortSwitchType 48 }  -- 10G Base-LR XENPAK Port
unisevtPortSw-10GBASE-CX4            OBJECT IDENTIFIER ::= { unisevtPortSwitchType 49 }  -- 10G Base-CX4 Port
unisevtPortSw-1000BASE-ZX-SFP        OBJECT IDENTIFIER ::= { unisevtPortSwitchType 50 }  -- 1000 Base-ZX SFP Port
unisevtPortSw-1000BASE-MM-SFP        OBJECT IDENTIFIER ::= { unisevtPortSwitchType 51 }  -- 1000 Base-MM SFP Port
unisevtPortSw-100BASE-SX-SFP         OBJECT IDENTIFIER ::= { unisevtPortSwitchType 52 }  -- 100 Base-SX SFP Port
unisevtPortSw-100BASE-LX-SFP         OBJECT IDENTIFIER ::= { unisevtPortSwitchType 53 }  -- 100 Base-LX SFP Port
unisevtPortSw-100BASE-T-AN-SFP       OBJECT IDENTIFIER ::= { unisevtPortSwitchType 54 }  -- 100 Base-T SFP Port
unisevtPortSw-100BASE-ZX-SFP         OBJECT IDENTIFIER ::= { unisevtPortSwitchType 55 }  -- 100 Base-ZX SFP Port
unisevtPortSw-100BASE-MM-SFP         OBJECT IDENTIFIER ::= { unisevtPortSwitchType 56 }  -- 100 Base-MM SFP Port
unisevtPortSw-SFP-NO-CONNECTOR       OBJECT IDENTIFIER ::= { unisevtPortSwitchType 57 }  -- No Connector SFP Port
unisevtPortSw-SFP-UNKNOWN-CONNECTOR  OBJECT IDENTIFIER ::= { unisevtPortSwitchType 58 }  -- Unknown SFP Port
unisevtPortSw-POS-NO-CONNECTOR       OBJECT IDENTIFIER ::= { unisevtPortSwitchType 59 }  -- POS no connector
unisevtPortSw-10G-BASE-SR            OBJECT IDENTIFIER ::= { unisevtPortSwitchType 60 }  -- 10GBASE-SR Fiber Optic Transceivers with SC Connector
unisevtPortSw-10G-BASE-ER            OBJECT IDENTIFIER ::= { unisevtPortSwitchType 61 }  -- 10GBASE-ER Fiber Optic Transceivers with SC Connector
unisevtPortSw-10G-BASE-LX4           OBJECT IDENTIFIER ::= { unisevtPortSwitchType 62 }  -- 10GBASE-LX4 Fiber Optic Transceivers with SC Connector
unisevtPortSw-10G-BASE-SW            OBJECT IDENTIFIER ::= { unisevtPortSwitchType 63 }  -- 10GBASE-SW Fiber Optic Transceivers with SC Connector
unisevtPortSw-10G-BASE-LW            OBJECT IDENTIFIER ::= { unisevtPortSwitchType 64 }  -- 10GBASE-LW Fiber Optic Transceivers with SC Connector
unisevtPortSw-10G-BASE-EW            OBJECT IDENTIFIER ::= { unisevtPortSwitchType 65 }  -- 10GBASE-EW Fiber Optic Transceivers with SC Connector
unisevtPortSw-10G-LR-SM-LC           OBJECT IDENTIFIER ::= { unisevtPortSwitchType 66 }  -- 10GBASE-LR Single Mode Fiber Optic Transceivers with LC Connector
unisevtPortSw-10G-SR-MM-LC           OBJECT IDENTIFIER ::= { unisevtPortSwitchType 67 }  -- 10GBASE-SR Multi Mode Fiber Optic Transceivers with LC Connector
unisevtPortSw-10G-ER-SM-LC           OBJECT IDENTIFIER ::= { unisevtPortSwitchType 68 }  -- 10GBASE-ER Single Mode Fiber Optic Transceivers with LC Connector
unisevtPortSw-10G-LW-SM-LC           OBJECT IDENTIFIER ::= { unisevtPortSwitchType 69 }  -- 10GBASE-LW Single Mode Fiber Optic Transceivers with LC Connector
unisevtPortSw-10G-SW-MM-LC           OBJECT IDENTIFIER ::= { unisevtPortSwitchType 70 }  -- 10GBASE-SW Multi Mode Fiber Optic Transceivers with LC Connector
unisevtPortSw-10G-EW-SM-LC           OBJECT IDENTIFIER ::= { unisevtPortSwitchType 71 }  -- 10GBASE-EW Single Mode Fiber Optic Transceivers with LC Connector
unisevtPortSw-100BASE-SM-MTRJ        OBJECT IDENTIFIER ::= { unisevtPortSwitchType 72 }  -- 100 Base-SM MTRJ Port
unisevtPortSw-100BASE-MM-MTRJ        OBJECT IDENTIFIER ::= { unisevtPortSwitchType 73 }  -- 100 Base-MM MTRJ Port
unisevtPortSw-XFP-NO-CONNECTOR       OBJECT IDENTIFIER ::= { unisevtPortSwitchType 74 }  -- XFP without Transceiver
unisevtPortSw-XFP-10GBASE-SR         OBJECT IDENTIFIER ::= { unisevtPortSwitchType 75 }  -- 10GBASE-SR XFP Transceiver
unisevtPortSw-XFP-10GBASE-LR         OBJECT IDENTIFIER ::= { unisevtPortSwitchType 76 }  -- 10GBASE-LR XFP Transceiver
unisevtPortSw-XFP-10GBASE-ER         OBJECT IDENTIFIER ::= { unisevtPortSwitchType 77 }  -- 10GBASE-ER XFP Transceiver
unisevtPortSw-XFP-10GBASE-SW         OBJECT IDENTIFIER ::= { unisevtPortSwitchType 78 }  -- 10GBASE-SW XFP Transceiver
unisevtPortSw-XFP-10GBASE-LW         OBJECT IDENTIFIER ::= { unisevtPortSwitchType 79 }  -- 10GBASE-LW XFP Transceiver
unisevtPortSw-XFP-10GBASE-EW         OBJECT IDENTIFIER ::= { unisevtPortSwitchType 80 }  -- 10GBASE-EW XFP Transceiver
unisevtPortSw-XFP-10GBASE-CX4        OBJECT IDENTIFIER ::= { unisevtPortSwitchType 81 }  -- 10GBASE-CX4 XFP Transceiver
unisevtPortSw-XFP-10GBASE-LX4        OBJECT IDENTIFIER ::= { unisevtPortSwitchType 82 }  -- 10GBASE-LX4 XFP Transceiver
unisevtPortSw-XFP-UNKNOWN            OBJECT IDENTIFIER ::= { unisevtPortSwitchType 83 }  -- Unknown  XFP Transceiver
unisevtPortSw-XPK-NOCONNECTOR        OBJECT IDENTIFIER ::= { unisevtPortSwitchType 84 }  -- Xenpak without Transceiver
unisevtPortSw-XPK-10GBASE-SR         OBJECT IDENTIFIER ::= { unisevtPortSwitchType 85 }  -- 10GBASE-SR Xenpak Transceiver
unisevtPortSw-XPK-10GBASE-LR         OBJECT IDENTIFIER ::= { unisevtPortSwitchType 86 }  -- 10GBASE-LR Xenpak Transceiver
unisevtPortSw-XPK-10GBASE-ER         OBJECT IDENTIFIER ::= { unisevtPortSwitchType 87 }  -- 10GBASE-ER Xenpak Transceiver
unisevtPortSw-XPK-10GBASE-SW         OBJECT IDENTIFIER ::= { unisevtPortSwitchType 88 }  -- 10GBASE-SW Xenpak Transceiver
unisevtPortSw-XPK-10GBASE-LW         OBJECT IDENTIFIER ::= { unisevtPortSwitchType 89 }  -- 10GBASE-LW Xenpak Transceiver
unisevtPortSw-XPK-10GBASE-EW         OBJECT IDENTIFIER ::= { unisevtPortSwitchType 90 }  -- 10GBASE-EW Xenpak Transceiver
unisevtPortSw-XPK-10GBASE-CX4        OBJECT IDENTIFIER ::= { unisevtPortSwitchType 91 }  -- 10GBASE-CX4 Xenpak Transceiver
unisevtPortSw-XPK-10GBASE-LX4        OBJECT IDENTIFIER ::= { unisevtPortSwitchType 92 }  -- 10GBASE-LX4 Xenpak Transceiver
unisevtPortSw-XPK-UNKNOWN            OBJECT IDENTIFIER ::= { unisevtPortSwitchType 93 }  -- Unknown Xenpak Transceiver
unisevtPortSw-POS-OC48-SR-SM-LC      OBJECT IDENTIFIER ::= { unisevtPortSwitchType 94 }  -- OC48-SR Single Mode Fiber Optic Transceivers with LC Connector
unisevtPortSw-POS-OC48-IR-SM-LC      OBJECT IDENTIFIER ::= { unisevtPortSwitchType 95 }  -- OC48-IR Single Mode Fiber Optic Transceivers with LC Connector
unisevtPortSw-POS-OC48-LR-SM-LC      OBJECT IDENTIFIER ::= { unisevtPortSwitchType 96 }  -- OC48-LR Single Mode Fiber Optic Transceivers with LC Connector
unisevtPortSw-10G-BASE-CX4           OBJECT IDENTIFIER ::= { unisevtPortSwitchType 97 }  -- 10G BASE-CX4 Electrical Interface
unisevtPortSw-OLT-1000BASE-BX-SFF-SC OBJECT IDENTIFIER ::= { unisevtPortSwitchType 98 }  -- 1000 BASE-BX SFF SC OLT Interface
unisevtPortSw-ONU-1000BASE-BX-SFF-SC OBJECT IDENTIFIER ::= { unisevtPortSwitchType 99 }  -- 1000 BASE-BX SFF SC ONU Interface
unisevtPortSw-24G-CASCADE            OBJECT IDENTIFIER ::= { unisevtPortSwitchType 100 }  -- 24G Cascade port
unisevtPortSw-POS-OC3-SR-MM          OBJECT IDENTIFIER ::= { unisevtPortSwitchType 101 }  -- STM1/OC3 Short Reach Multi Mode Fiber Optic Transceivers with LC Connector
unisevtPortSw-POS-OC3-IR-SM          OBJECT IDENTIFIER ::= { unisevtPortSwitchType 102 }  -- STM1/OC3 Intermediate Reach Single Mode Fiber Optic Transceivers with LC Connector
unisevtPortSw-POS-OC3-IR-1-SM        OBJECT IDENTIFIER ::= { unisevtPortSwitchType 103 }  -- STM1/OC3 Intermediate Reach Single Mode Fiber Optic Transceivers with LC Connector(variation 1)
unisevtPortSw-POS-OC3-IR-2-SM        OBJECT IDENTIFIER ::= { unisevtPortSwitchType 104 }  -- STM1/OC3 Intermediate Reach Single Mode Fiber Optic Transceivers with LC Connector(variation 2)
unisevtPortSw-POS-OC3-LR-SM          OBJECT IDENTIFIER ::= { unisevtPortSwitchType 105 }  -- STM1/OC3 Long Reach Single Mode Fiber Optic Transceivers with LC Connector
unisevtPortSw-POS-OC3-LR-1-SM        OBJECT IDENTIFIER ::= { unisevtPortSwitchType 106 }  -- STM1/OC3 Long Reach Single Mode Fiber Optic Transceivers with LC Connector(variation 1)
unisevtPortSw-POS-OC3-LR-2-SM        OBJECT IDENTIFIER ::= { unisevtPortSwitchType 107 }  -- STM1/OC3 Long Reach Single Mode Fiber Optic Transceivers with LC Connector(variation 2)
unisevtPortSw-POS-OC3-LR-3-SM        OBJECT IDENTIFIER ::= { unisevtPortSwitchType 108 }  -- STM1/OC3 Long Reach Single Mode Fiber Optic Transceivers with LC Connector(variation 3)
unisevtPortSw-POS-OC12-SR-MM         OBJECT IDENTIFIER ::= { unisevtPortSwitchType 109 }  -- STM4/OC12 Short Reach Multi Mode Fiber Optic Transceivers with LC Connector
unisevtPortSw-POS-OC12-IR-SM         OBJECT IDENTIFIER ::= { unisevtPortSwitchType 110 }  -- STM4/OC12 Intermediate Reach Single Mode Fiber Optic Transceivers with LC Connector
unisevtPortSw-POS-OC12-IR-1-SM       OBJECT IDENTIFIER ::= { unisevtPortSwitchType 111 }  -- STM4/OC12 Intermediate Reach Single Mode Fiber Optic Transceivers with LC Connector(variation 1)
unisevtPortSw-POS-OC12-IR-2-SM       OBJECT IDENTIFIER ::= { unisevtPortSwitchType 112 }  -- STM4/OC12 Intermediate Reach Single Mode Fiber Optic Transceivers with LC Connector(variation 2)
unisevtPortSw-POS-OC12-LR-SM         OBJECT IDENTIFIER ::= { unisevtPortSwitchType 113 }  -- STM4/OC12 Long Reach Single Mode Fiber Optic Transceivers with LC Connector
unisevtPortSw-POS-OC12-LR-1-SM       OBJECT IDENTIFIER ::= { unisevtPortSwitchType 114 }  -- STM4/OC12 Long Reach Single Mode Fiber Optic Transceivers with LC Connector(variation 1)
unisevtPortSw-POS-OC12-LR-2-SM       OBJECT IDENTIFIER ::= { unisevtPortSwitchType 115 }  -- STM4/OC12 Long Reach Single Mode Fiber Optic Transceivers with LC Connector(variation 2)
unisevtPortSw-POS-OC12-LR-3-SM       OBJECT IDENTIFIER ::= { unisevtPortSwitchType 116 }  -- STM4/OC12 Long Reach Single Mode Fiber Optic Transceivers with LC Connector(variation 3)
unisevtPortSw-POS-OC48-SR-SM         OBJECT IDENTIFIER ::= { unisevtPortSwitchType 117 }  -- STM16/OC48 Short Reach Single Mode Fiber Optic Transceivers with LC Connector
unisevtPortSw-POS-OC48-IR-SM         OBJECT IDENTIFIER ::= { unisevtPortSwitchType 118 }  -- STM16/OC48 Intermediate Reach Single Mode Fiber Optic Transceivers with LC Connector
unisevtPortSw-POS-OC48-IR-1-SM       OBJECT IDENTIFIER ::= { unisevtPortSwitchType 119 }  -- STM16/OC48 Intermediate Reach Single Mode Fiber Optic Transceivers with LC Connector(variation 1)
unisevtPortSw-POS-OC48-IR-2-SM       OBJECT IDENTIFIER ::= { unisevtPortSwitchType 120 }  -- STM16/OC48 Intermediate Reach Single Mode Fiber Optic Transceivers with LC Connector(variation 2)
unisevtPortSw-POS-OC48-LR-SM         OBJECT IDENTIFIER ::= { unisevtPortSwitchType 121 }  -- STM16/OC48 Long Reach Single Mode Fiber Optic Transceivers with LC Connector
unisevtPortSw-POS-OC48-LR-1-SM       OBJECT IDENTIFIER ::= { unisevtPortSwitchType 122 }  -- STM16/OC48 Long Reach Single Mode Fiber Optic Transceivers with LC Connector(variation 1)
unisevtPortSw-POS-OC48-LR-2-SM       OBJECT IDENTIFIER ::= { unisevtPortSwitchType 123 }  -- STM16/OC48 Long Reach Single Mode Fiber Optic Transceivers with LC Connector(variation 2)
unisevtPortSw-POS-OC48-LR-3-SM       OBJECT IDENTIFIER ::= { unisevtPortSwitchType 124 }  -- STM16/OC48 Long Reach Single Mode Fiber Optic Transceivers with LC Connector(variation 3)
unisevtPortSw-POS-I-64-1             OBJECT IDENTIFIER ::= { unisevtPortSwitchType 125 }  -- STM64/OC192 Interconnect Fiber Optic Transceivers with LC Connector(wavelength 1310nm G.652 fiber)
unisevtPortSw-POS-I-64-2             OBJECT IDENTIFIER ::= { unisevtPortSwitchType 126 }  -- STM64/OC192 Interconnect Fiber Optic Transceivers with LC Connector(wavelength 1550nm G.652 fiber)
unisevtPortSw-POS-I-64-3             OBJECT IDENTIFIER ::= { unisevtPortSwitchType 127 }  -- STM64/OC192 Interconnect Fiber Optic Transceivers with LC Connector(wavelength 1550nm G.653 fiber)
unisevtPortSw-POS-I-64-5             OBJECT IDENTIFIER ::= { unisevtPortSwitchType 128 }  -- STM64/OC192 Interconnect Fiber Optic Transceivers with LC Connector(wavelength 1550nm G.655 fiber)
unisevtPortSw-POS-S-64-1             OBJECT IDENTIFIER ::= { unisevtPortSwitchType 129 }  -- STM64/OC192 Short Haul Fiber Optic Transceivers with LC Connector(wavelength 1310nm G.652 fiber)
unisevtPortSw-POS-S-64-2             OBJECT IDENTIFIER ::= { unisevtPortSwitchType 130 }  -- STM64/OC192 Short Haul Fiber Optic Transceivers with LC Connector(wavelength 1550nm G.652 fiber)
unisevtPortSw-POS-S-64-3             OBJECT IDENTIFIER ::= { unisevtPortSwitchType 131 }  -- STM64/OC192 Short Haul Fiber Optic Transceivers with LC Connector(wavelength 1550nm G.653 fiber)
unisevtPortSw-POS-S-64-5             OBJECT IDENTIFIER ::= { unisevtPortSwitchType 132 }  -- STM64/OC192 Short Haul Fiber Optic Transceivers with LC Connector(wavelength 1550nm G.655 fiber)
unisevtPortSw-POS-L-64-1             OBJECT IDENTIFIER ::= { unisevtPortSwitchType 133 }  -- STM64/OC192 Long Haul Fiber Optic Transceivers with LC Connector(wavelength 1310nm G.652 fiber)
unisevtPortSw-POS-L-64-2             OBJECT IDENTIFIER ::= { unisevtPortSwitchType 134 }  -- STM64/OC192 Long Haul Fiber Optic Transceivers with LC Connector(wavelength 1550nm G.652 fiber)
unisevtPortSw-POS-L-64-3             OBJECT IDENTIFIER ::= { unisevtPortSwitchType 135 }  -- STM64/OC192 Long Haul Fiber Optic Transceivers with LC Connector(wavelength 1550nm G.653 fiber)
unisevtPortSw-POS-V-64-2             OBJECT IDENTIFIER ::= { unisevtPortSwitchType 136 }  -- STM64/OC192 Very Long Haul Fiber Optic Transceivers with LC Connector(wavelength 1550nm G.652 fiber)
unisevtPortSw-POS-V-64-3             OBJECT IDENTIFIER ::= { unisevtPortSwitchType 137 }  -- STM64/OC192 Very Long Haul Fiber Optic Transceivers with LC Connector(wavelength 1550nm G.653 fiber)
unisevtPortSw-100BASE-FX-BIDI        OBJECT IDENTIFIER ::= { unisevtPortSwitchType 138 }  -- 100 BASE-FX BIDI Port
unisevtPortSw-100BASE-BX10-U-SFP     OBJECT IDENTIFIER ::= { unisevtPortSwitchType 139 }  -- 100 BASE-BX10-U-SFP Port
unisevtPortSw-100BASE-BX10-D-SFP     OBJECT IDENTIFIER ::= { unisevtPortSwitchType 140 }  -- 100 BASE-BX10-D-SFP Port
unisevtPortSw-1000BASE-BX10-U-SFP    OBJECT IDENTIFIER ::= { unisevtPortSwitchType 141 }  -- 1000 BASE-BX10-U-SFP Port
unisevtPortSw-1000BASE-BX10-D-SFP    OBJECT IDENTIFIER ::= { unisevtPortSwitchType 142 }  -- 1000 BASE-BX10-D-SFP Port
unisevtPortSw-STK-1000BASE-T         OBJECT IDENTIFIER ::= { unisevtPortSwitchType 143 }  -- 1000 BASE-T Stack Port
unisevtPortSw-RPR-PHYPOS-CONNECTOR     OBJECT IDENTIFIER ::= { unisevtPortSwitchType 144 }  -- Resilient Packet Ring POS physical port
unisevtPortSw-RPR-PHY10GE-CONNECTOR    OBJECT IDENTIFIER ::= { unisevtPortSwitchType 145 }  -- 10G Resilient Packet Ring physical port
unisevtPortSw-RPR-LOGICPOS-CONNECTOR   OBJECT IDENTIFIER ::= { unisevtPortSwitchType 146 }  -- Resilient Packet Ring POS logical port
unisevtPortSw-RPR-LOGIC10GE-CONNECTOR  OBJECT IDENTIFIER ::= { unisevtPortSwitchType 147 }  -- 10G Resilient Packet Ring logical port
unisevtPortSw-10GBASE-ZR               OBJECT IDENTIFIER ::= { unisevtPortSwitchType 148 }  -- Fiber Optic Transceivers with SC Connector, XENPAK
unisevtPortSw-TYPE-ERROR-CONNECTOR     OBJECT IDENTIFIER ::= { unisevtPortSwitchType 149 }  -- Error Optic Transceivers type
unisevtPortSw-10G-STACK                OBJECT IDENTIFIER ::= { unisevtPortSwitchType 150 }  -- 10G Stack Port
unisevtPortSw-155-ATM-SX-MMF             OBJECT IDENTIFIER ::= { unisevtPortSwitchType 151 }  -- ATM OC-3 Multi-mode Short Reach Optical Transceiver
unisevtPortSw-155-ATM-LX-SMF             OBJECT IDENTIFIER ::= { unisevtPortSwitchType 152 }  -- ATM OC-3 Single Mode Long Reach Optical Transceiver
unisevtPortSw-622-ATM-SX-MMF             OBJECT IDENTIFIER ::= { unisevtPortSwitchType 153 }  -- ATM OC-12 Multi-mode Short Reach Optical Transceiver
unisevtPortSw-622-ATM-LX-SMF             OBJECT IDENTIFIER ::= { unisevtPortSwitchType 154 }  -- ATM OC-12 Single Mode Long Reach Optical Transceiver
unisevtPortSw-155-ATM-NO-CONNECTOR       OBJECT IDENTIFIER ::= { unisevtPortSwitchType 155 }  -- ATM OC-3 No Connector
unisevtPortSw-622-ATM-NO-CONNECTOR       OBJECT IDENTIFIER ::= { unisevtPortSwitchType 156 }  -- ATM OC-12 No Connector
unisevtPortSw-155-CPOS-E1-NO-CONNECTOR   OBJECT IDENTIFIER ::= { unisevtPortSwitchType 157 }  -- CPOS(E1) OC-3 No Connector
unisevtPortSw-155-CPOS-T1-NO-CONNECTOR   OBJECT IDENTIFIER ::= { unisevtPortSwitchType 158 }  -- CPOS(T1) OC-3 No Connector
unisevtPortSw-622-CPOS-E1-NO-CONNECTOR   OBJECT IDENTIFIER ::= { unisevtPortSwitchType 159 }  -- CPOS(E1) OC-12 No Connector
unisevtPortSw-622-CPOS-T1-NO-CONNECTOR   OBJECT IDENTIFIER ::= { unisevtPortSwitchType 160 }  -- CPOS(T1) OC-12 No Connector
unisevtPortSw-155-CPOS-E1-SX-MMF         OBJECT IDENTIFIER ::= { unisevtPortSwitchType 161 }  -- CPOS(E1) OC-3 Multi-mode Short Reach Optical Transceiver
unisevtPortSw-155-CPOS-T1-SX-MMF         OBJECT IDENTIFIER ::= { unisevtPortSwitchType 162 }  -- CPOS(T1) OC-3 Multi-mode Short Reach Optical Transceiver
unisevtPortSw-155-CPOS-E1-LX-SMF         OBJECT IDENTIFIER ::= { unisevtPortSwitchType 163 }  -- CPOS(E1) OC-3 Single Mode Long Reach Optical Transceiver
unisevtPortSw-155-CPOS-T1-LX-SMF         OBJECT IDENTIFIER ::= { unisevtPortSwitchType 164 }  -- CPOS(T1) OC-3 Single Mode Long Reach Optical Transceiver
unisevtPortSw-622-CPOS-E1-SX-MMF         OBJECT IDENTIFIER ::= { unisevtPortSwitchType 165 }  -- CPOS(E1) OC-12 Multi-mode Short Reach Optical Transceiver
unisevtPortSw-622-CPOS-T1-SX-MMF         OBJECT IDENTIFIER ::= { unisevtPortSwitchType 166 }  -- CPOS(T1) OC-12 Multi-mode Short Reach Optical Transceiver
unisevtPortSw-622-CPOS-E1-LX-SMF         OBJECT IDENTIFIER ::= { unisevtPortSwitchType 167 }  -- CPOS(E1) OC-12 Multi-mode Short Reach Optical Transceiver
unisevtPortSw-622-CPOS-T1-LX-SMF         OBJECT IDENTIFIER ::= { unisevtPortSwitchType 168 }  -- CPOS(T1) OC-12 Single Mode Long Reach Optical Transceiver
unisevtPortSw-E1-CONNECTOR               OBJECT IDENTIFIER ::= { unisevtPortSwitchType 169 }  -- E1 RJ45 Transceiver
unisevtPortSw-T1-CONNECTOR               OBJECT IDENTIFIER ::= { unisevtPortSwitchType 170 }  -- T1 RJ45 Transceiver
unisevtPortSw-1000BASE-STK-SFP           OBJECT IDENTIFIER ::= { unisevtPortSwitchType 171 }  -- 1-port 1000 Base-STK SFP Module
unisevtPortSw-1000BASE-BIDI-SFP          OBJECT IDENTIFIER ::= { unisevtPortSwitchType 172 }  -- 1-port 1000 Base-BIDI SFP Module
unisevtPortSw-1000BASE-CWDM-SFP          OBJECT IDENTIFIER ::= { unisevtPortSwitchType 173 }  -- 1-port 1000 Base-CWDM SFP Module
unisevtPortSw-100BASE-BIDI-SFP           OBJECT IDENTIFIER ::= { unisevtPortSwitchType 174 }  -- 1-port 100 Base-BIDI SFP Module
unisevtPortSw-OLT-1000BASE-PX-SFP        OBJECT IDENTIFIER ::= { unisevtPortSwitchType 175 }  -- 1000BASE-PX SFP OLT Interface
unisevtPortSw-OLT-1000BASE-NO-CONNECTOR  OBJECT IDENTIFIER ::= { unisevtPortSwitchType 176 }  -- 1000BASE OLT No Connector
unisevtPortSw-RPR-PHYGE-CONNECTOR        OBJECT IDENTIFIER ::= { unisevtPortSwitchType 177 }  -- Resilient Packet Ring GE physical port
unisevtPortSw-RPR-LOGICGE-CONNECTOR      OBJECT IDENTIFIER ::= { unisevtPortSwitchType 178 }  -- Resilient Packet Ring GE logical port
unisevtPortSw-100M-1550-BIDI             OBJECT IDENTIFIER ::= { unisevtPortSwitchType 179 }  -- Single Port 100M Ethernet Bi-direction Optical Interface Module(TX1550nm, RX1310nm, 15km, SC)
unisevtPortSw-100M-1310-BIDI             OBJECT IDENTIFIER ::= { unisevtPortSwitchType 180 }  -- Single Port 100M Ethernet Bi-direction Optical reverse Interface Module(TX1310nm, RX1550nm, 15km, SC)
unisevtPortSw-RPR-PHYOC48-CONNECTOR      OBJECT IDENTIFIER ::= { unisevtPortSwitchType 181 }  -- Resilient Packet Ring OC48 physical port
unisevtPortSw-RPR-LOGICOC48-CONNECTOR    OBJECT IDENTIFIER ::= { unisevtPortSwitchType 182 }  -- Resilient Packet Ring OC48 logical port
unisevtPortSw-100-1000-BASE-LX-SMF       OBJECT IDENTIFIER ::= { unisevtPortSwitchType 183 }  -- 100BASE-LX/1000BASE-LX Single Mode Fiber Optic Transceivers
unisevtPortSw-10G-ZW-SM-LC               OBJECT IDENTIFIER ::= { unisevtPortSwitchType 184 }  -- 10GBASE-ZW Single Mode Fiber Optic Transceivers with LC Connector
unisevtPortSw-10G-ZR-SM-LC               OBJECT IDENTIFIER ::= { unisevtPortSwitchType 185 }  -- 10GBASE-ZR Single Mode Fiber Optic Transceivers with LC Connector
unisevtPortSw-XPK-10GBASE-ZR             OBJECT IDENTIFIER ::= { unisevtPortSwitchType 186 }  -- 10GBASE-ZR Xenpak Transceiver:LH80,SM1550
unisevtPortSw-SGMII-100-BASE-LX-SFP      OBJECT IDENTIFIER ::= { unisevtPortSwitchType 187 }  -- SGMII-100-BASE-LX-SFP Transceiver
unisevtPortSw-SGMII-100-BASE-FX-SFP      OBJECT IDENTIFIER ::= { unisevtPortSwitchType 188 }  -- SGMII-100-BASE-FX-SFP Transceiver
unisevtPortSw-WLAN-RADIO                 OBJECT IDENTIFIER ::= { unisevtPortSwitchType 189 }  -- WLAN-RADIO Transceiver
unisevtPortSw-CABLE                      OBJECT IDENTIFIER ::= { unisevtPortSwitchType 190 }  -- Cable Port
unisevtPortSw-SFP-PLUS-NO-CONNECTOR      OBJECT IDENTIFIER ::= { unisevtPortSwitchType 191 }  -- SFP+ without Transceiver
unisevtPortSw-SFP-PLUS-10GBASE-SR        OBJECT IDENTIFIER ::= { unisevtPortSwitchType 192 }  -- 10GBASE-SR SFP+ Transceiver
unisevtPortSw-SFP-PLUS-10GBASE-LR        OBJECT IDENTIFIER ::= { unisevtPortSwitchType 193 }  -- 10GBASE-LR SFP+ Transceiver
unisevtPortSw-SFP-PLUS-10GBASE-LRM       OBJECT IDENTIFIER ::= { unisevtPortSwitchType 194 }  -- 10GBASE-LRM SFP+ Transceiver
unisevtPortSw-SFP-PLUS-10GBASE-Cu        OBJECT IDENTIFIER ::= { unisevtPortSwitchType 195 }  -- 10GBASE-Cu SFP+ Transceiver
unisevtPortSw-SFP-PLUS-UNKNOWN           OBJECT IDENTIFIER ::= { unisevtPortSwitchType 196 }  -- Unknown SFP+ Transceiver
unisevtPortSw-SFP-PLUS-STACK-CONNECTOR   OBJECT IDENTIFIER ::= { unisevtPortSwitchType 197 }  -- SFP+ STACK Transceiver
unisevtPortSw-POS-L-64-4                 OBJECT IDENTIFIER ::= { unisevtPortSwitchType 198 }  -- STM64/OC192 Long Haul Fiber Optic Transceivers with LC Connector(wavelength 1550nm G.653 fiber)
unisevtPortSw-MINISAS-HD-STACK-CONNECTOR OBJECT IDENTIFIER ::= { unisevtPortSwitchType 199 }  -- MiniSAS HD STACK Transceiver
unisevtPortSw-ONU-1000BASE-PX-SFF        OBJECT IDENTIFIER ::= { unisevtPortSwitchType 200 }  -- 1000BASE-PX SFF ONU Interface
unisevtPortSw-RS485                      OBJECT IDENTIFIER ::= { unisevtPortSwitchType 201 }  -- RS-485 Interface
unisevtPortSw-SFP-PLUS-10GBASE-ER        OBJECT IDENTIFIER ::= { unisevtPortSwitchType 202 }  -- 10GBASE-ER SFP+ Transceiver
unisevtPortSw-SFP-PLUS-10GBASE-ZR        OBJECT IDENTIFIER ::= { unisevtPortSwitchType 203 }  -- 10GBASE-ZR SFP+ Transceiver
unisevtPortSw-XFP-10GBASE-ZR             OBJECT IDENTIFIER ::= { unisevtPortSwitchType 204 }  -- 10GBASE-ZR XFP Transceiver
unisevtPortSw-QSFP-PLUS-40GBASE-SR4      OBJECT IDENTIFIER ::= { unisevtPortSwitchType 205 }  -- 40BASE-SR4 QSFP+ Optical Transceiver
unisevtPortSw-QSFP-PLUS-STACK-CONNECTOR  OBJECT IDENTIFIER ::= { unisevtPortSwitchType 206 }  -- QSFP+ STACK Transceiver
unisevtPortSw-QSFP-PLUS-TO-4SFP-PLUS-STACK-CONNECTOR OBJECT IDENTIFIER ::= { unisevtPortSwitchType 207 }  -- QSFP+ to 4 SFP+ STACK Transceiver
unisevtPortSw-SFP-STACK-CONNECTOR        OBJECT IDENTIFIER ::= { unisevtPortSwitchType 208 }  -- SFP STACK Transceiver
unisevtPortSw-QSFP-NO-CONNECTOR          OBJECT IDENTIFIER ::= { unisevtPortSwitchType 209 }  -- QSFP No Connector
unisevtPortSw-10GBase-T                  OBJECT IDENTIFIER ::= { unisevtPortSwitchType 210 }  -- 10G Base-T Port
unisevtPortSw-CFP-NO-CONNECTOR           OBJECT IDENTIFIER ::= { unisevtPortSwitchType 211 }  -- CFP No Connector
unisevtPortSw-CFP-40GBASE-LR4            OBJECT IDENTIFIER ::= { unisevtPortSwitchType 212 }  -- 40GBASE-LR4 CFP Transceiver
unisevtPortSw-QSFP-PLUS-NO-CONNECTOR     OBJECT IDENTIFIER ::= { unisevtPortSwitchType 213 }  -- QSFP+ No Connector
unisevtPortSw-QSFP-PLUS-40GBASE-LR4      OBJECT IDENTIFIER ::= { unisevtPortSwitchType 214 }  -- 40GBASE-LR4 QSFP+ Optical Transceiver
unisevtPortSw-CFP-40GBASE-SR4            OBJECT IDENTIFIER ::= { unisevtPortSwitchType 215 }  -- 40GBASE-SR4 CFP Optical Transceiver
unisevtPortSw-CFP-100GBASE-LR4           OBJECT IDENTIFIER ::= { unisevtPortSwitchType 216 }  -- 100GBASE-LR4 CFP Optical Transceiver
unisevtPortSw-CFP-100GBASE-SR10          OBJECT IDENTIFIER ::= { unisevtPortSwitchType 217 }  -- 100GBASE-SR10 CFP Optical Transceiver
unisevtPortSw-CXP-100GBASE-SR10          OBJECT IDENTIFIER ::= { unisevtPortSwitchType 218 }  -- 100GBASE-SR10 CXP Optical Transceiver
unisevtPortSw-CXP-NO-CONNECTOR           OBJECT IDENTIFIER ::= { unisevtPortSwitchType 219 }  -- CXP No Connector
unisevtPortSw-TRANSCEIVER-UNKNOWN        OBJECT IDENTIFIER ::= { unisevtPortSwitchType 220 }  -- Unknown Transceiver
unisevtPortSw-QSFP-PLUS-UNKNOWN          OBJECT IDENTIFIER ::= { unisevtPortSwitchType 221 }  -- Unknown QSFP+ Transceiver
unisevtPortSw-CFP-UNKNOWN                OBJECT IDENTIFIER ::= { unisevtPortSwitchType 222 }  -- Unknown CFP Transceiver
unisevtPortSw-QSFP-PLUS-40GBASE-CSR4     OBJECT IDENTIFIER ::= { unisevtPortSwitchType 223 }  -- 40GBASE-CSR4 QSFP+ Optical Transceiver
unisevtPortSw-CFP-40GBASE-ER4            OBJECT IDENTIFIER ::= { unisevtPortSwitchType 224 }  -- 40GBASE-ER4 CFP Optical Transceiver
unisevtPortSw-SFP-1000BASE-BIDI          OBJECT IDENTIFIER ::= { unisevtPortSwitchType 225 }  -- 1000BASE SFP Bi-direction Optical Transceiver
unisevtPortSw-SFP-PLUS-10GBASE-ZR-DWDM   OBJECT IDENTIFIER ::= { unisevtPortSwitchType 226 }  -- 10GBase-ZR SFP+ DWDM Optical Transceiver
unisevtPortSw-QSFP-PLUS-40GBASE-PSM      OBJECT IDENTIFIER ::= { unisevtPortSwitchType 227 }  -- 40GBASE QSFP+ Parallel SingleMode Optical Transceiver
unisevtPortSw-SFP-8GFC-SW                OBJECT IDENTIFIER ::= { unisevtPortSwitchType 228 }  -- SFP 8G FC Optical Transceiver short wave
unisevtPortSw-SFP-8GFC-LW                OBJECT IDENTIFIER ::= { unisevtPortSwitchType 229 }  -- SFP 8G FC Optical Transceiver long wave
unisevtPortSw-CXP-100GBASE-AOC           OBJECT IDENTIFIER ::= { unisevtPortSwitchType 230 }  -- 100GBASE CXP Active Optical Cable
unisevtPortSw-QSFP-PLUS-ACTIVE-STACK-CONNECTOR  OBJECT IDENTIFIER ::= { unisevtPortSwitchType 231 }  -- QSFP+ Active STACK Transceiver
unisevtPortSw-QSFP-PLUS-TO-4SFP-PLUS-ACTIVE-STACK-CONNECTOR  OBJECT IDENTIFIER ::= { unisevtPortSwitchType 232 }  -- QSFP+ to 4 SFP+ Active STACK Transceiver
unisevtPortSw-CFP2-100GBASE-LR4          OBJECT IDENTIFIER ::= { unisevtPortSwitchType 233 }  -- 100GBASE-LR4 CFP2 Optical Transceiver
unisevtPortSw-CFP2-100GBASE-SR10         OBJECT IDENTIFIER ::= { unisevtPortSwitchType 234 }  -- 100GBASE-SR10 CFP2 Optical Transceiver
unisevtPortSw-QSFP-PLUS-ACTIVE-OPTICAL-CABLE  OBJECT IDENTIFIER ::= { unisevtPortSwitchType 235 }  -- QSFP+ AOC
unisevtPortSw-QSFP-PLUS-TO-4SFP-PLUS-ACTIVE-OPTICAL-CABLE OBJECT IDENTIFIER ::= { unisevtPortSwitchType 236 }  -- QSFP+ to 4 SFP+ AOC
unisevtPortSw-SFP-PLUS-ACTIVE-OPTICAL-CABLE   OBJECT IDENTIFIER ::= { unisevtPortSwitchType 237 }  -- SFP+ AOC
unisevtPortSw-CFP2-NO-CONNECTOR         OBJECT IDENTIFIER ::= { unisevtPortSwitchType 238 }  -- CFP2 No Connector
unisevtPortSw-QSFP28-NO-CONNECTOR       OBJECT IDENTIFIER ::= { unisevtPortSwitchType 239 }  -- QSFP28 No Connector
unisevtPortSw-QSFP28-100GBASE-SR4       OBJECT IDENTIFIER ::= { unisevtPortSwitchType 240 }  -- 100BASE-SR4 QSFP28 Optical Transceiver
unisevtPortSw-QSFP28-100GBASE-LR4       OBJECT IDENTIFIER ::= { unisevtPortSwitchType 241 }  -- 100GBASE-LR4 QSFP28 Optical Transceiver
unisevtPortSw-QSFP28-100GBASE-ER4       OBJECT IDENTIFIER ::= { unisevtPortSwitchType 242 }  -- 100GBASE-ER4 QSFP28 Optical Transceiver
unisevtPortSw-QSFP28-100GBASE-PSM4      OBJECT IDENTIFIER ::= { unisevtPortSwitchType 243 }  -- 100GBASE-PSM4 QSFP28 Optical Transceiver
unisevtPortSw-QSFP28-100GBASE-CWDM4     OBJECT IDENTIFIER ::= { unisevtPortSwitchType 244 }  -- 100GBASE-CWDM4 QSFP28 Optical Transceiver
unisevtPortSw-QSFP28-STACK-CONNECTOR    OBJECT IDENTIFIER ::= { unisevtPortSwitchType 245 }  -- QSFP28 STACK Transceiver
unisevtPortSw-QSFP28-TO-4SFP28-STACK-CONNECTOR  OBJECT IDENTIFIER ::= { unisevtPortSwitchType 246 }  -- QSFP28 to 4 SFP28 STACK Transceiver
unisevtPortSw-QSFP28-ACTIVE-STACK-CONNECTOR     OBJECT IDENTIFIER ::= { unisevtPortSwitchType 247 }  -- QSFP28 Active STACK Transceiver
unisevtPortSw-QSFP28-TO-4SFP28-ACTIVE-STACK-CONNECTOR   OBJECT IDENTIFIER ::= { unisevtPortSwitchType 248 }  -- QSFP28 to 4 SFP28 Active STACK Transceiver
unisevtPortSw-QSFP28-ACTIVE-OPTICAL-CABLE       OBJECT IDENTIFIER ::= { unisevtPortSwitchType 249 }  -- QSFP28 AOC
unisevtPortSw-QSFP28-TO-4SFP28-ACTIVE-OPTICAL-CABLE OBJECT IDENTIFIER ::= { unisevtPortSwitchType 250 }  -- QSFP28 to 4 SFP28 AOC
unisevtPortSw-QSFP-PLUS-40GBASE-LM4     OBJECT IDENTIFIER ::= { unisevtPortSwitchType 251 }  -- 40BASE-LM4 QSFP+ Optical Transceiver
unisevtPortSw-QSFP-PLUS-40GBASE-SWDM4   OBJECT IDENTIFIER ::= { unisevtPortSwitchType 252 }  -- 40BASE-SWDM4 QSFP+ Optical Transceiver
unisevtPortSw-CFP-100GBASE-ER4          OBJECT IDENTIFIER ::= { unisevtPortSwitchType 253 }  -- 100GBASE-ER4 CFP Transceiver
unisevtPortSw-QSFP-PLUS-40GBASE-ER4     OBJECT IDENTIFIER ::= { unisevtPortSwitchType 254 }  -- 40BASE-ER4 QSFP+ Optical Transceiver
unisevtPortSw-QSFP-PLUS-40GBASE-ER4L    OBJECT IDENTIFIER ::= { unisevtPortSwitchType 255 }  -- 40BASE-ER4L QSFP+ Optical Transceiver
unisevtPortSw-QSFP-PLUS-40GBASE-BIDI    OBJECT IDENTIFIER ::= { unisevtPortSwitchType 256 }  -- 40BASE-BIDI QSFP+ Optical Transceiver
unisevtPortSw-QSFP-PLUS-40GBASE-LR4L    OBJECT IDENTIFIER ::= { unisevtPortSwitchType 257 }  -- 40BASE-LR4L QSFP+ Optical Transceiver
unisevtPortSw-CFP2-100GBASE-eSR10       OBJECT IDENTIFIER ::= { unisevtPortSwitchType 258 }  -- 100GBASE-eSR10 CFP2 Optical Transceiver
unisevtPortSw-TUNABLE-SFP-PLUS-10GBASE-ZR-DWDM  OBJECT IDENTIFIER ::= { unisevtPortSwitchType 259 }  -- 10GBase-ZR Tunable SFP+ DWDM Optical Transceiver
unisevtPortSw-SFP28-25GBASE-SR          OBJECT IDENTIFIER ::= { unisevtPortSwitchType 260 }  -- 25GBASE-SR SFP28 Optical Transceiver
unisevtPortSw-SFP28-ACTIVE-OPTICAL-CABLE    OBJECT IDENTIFIER ::= { unisevtPortSwitchType 261 }  -- SFP28 AOC
unisevtPortSw-SFP28-STACK-CONNECTOR     OBJECT IDENTIFIER ::= { unisevtPortSwitchType 262 }  -- SFP28 STACK Transceiver
unisevtPortSw-2DOT5GBASE-T              OBJECT IDENTIFIER ::= { unisevtPortSwitchType 263 }  -- 2dot5G Base-T Port
unisevtPortSw-QSFP28-100GBASE-SWDM4     OBJECT IDENTIFIER ::= { unisevtPortSwitchType 264 }  -- 100GBASE-SWDM4 QSFP28 Optical Transceiver
unisevtPortSw-QSFP28-100GBASE-eSWDM4    OBJECT IDENTIFIER ::= { unisevtPortSwitchType 265 }  -- 100GBASE-eSWDM4 QSFP28 Optical Transceiver
unisevtPortSw-SFP-PLUS-10GBASE-T        OBJECT IDENTIFIER ::= { unisevtPortSwitchType 266 }  -- 10GBase-T SFP+ Transceiver
unisevtPortSw-QSFP28-100GBASE-eSR4       OBJECT IDENTIFIER ::= { unisevtPortSwitchType 267 }  -- 100BASE-eSR4 QSFP28 Optical Transceiver
unisevtPortSw-QSFP28-100GBASE-BIDI       OBJECT IDENTIFIER ::= { unisevtPortSwitchType 268 }  -- 100GBASE-BIDI QSFP28 Optical Transceiver
unisevtPortSw-QSFP28-100GBASE-WDM2       OBJECT IDENTIFIER ::= { unisevtPortSwitchType 269 }  -- 100GBASE-WDM2 QSFP28 Optical Transceiver
unisevtPortSw-SFP28-25GBASE-LR           OBJECT IDENTIFIER ::= { unisevtPortSwitchType 270 }  -- 25GBASE-LR SFP28 Optical Transceiver
unisevtPortSw-CFP2-100GBASE-ER4          OBJECT IDENTIFIER ::= { unisevtPortSwitchType 271 }  -- 100GBASE-ER4 CFP2 Optical Transceiver
unisevtPortSw-CFP2-DCO-200GBASE-ZR          OBJECT IDENTIFIER ::= { unisevtPortSwitchType 272 }  -- 200GBASE-ZR CFP2-DCO Optical Transceiver
unisevtPortSw-CFP2-100GBASE-ER4L          OBJECT IDENTIFIER ::= { unisevtPortSwitchType 273 }  -- 100GBASE-ER4L CFP2 Optical Transceiver
unisevtPortSw-SFP-16GFC-SW                OBJECT IDENTIFIER ::= { unisevtPortSwitchType 274 }  -- SFP 16G FC Optical Transceiver short wave
unisevtPortSw-SFP-16GFC-LW                OBJECT IDENTIFIER ::= { unisevtPortSwitchType 275 }  -- SFP 16G FC Optical Transceiver long wave
unisevtPortSw-SFP-32GFC-SW                OBJECT IDENTIFIER ::= { unisevtPortSwitchType 276 }  -- SFP 32G FC Optical Transceiver short wave
unisevtPortSw-SFP-32GFC-LW                OBJECT IDENTIFIER ::= { unisevtPortSwitchType 277 }  -- SFP 32G FC Optical Transceiver long wave
unisevtPortSw-XFP-10GBASE-PR-D3               OBJECT IDENTIFIER ::= { unisevtPortSwitchType 278 }  -- XFP 10GBase PR-D3 Optical Transceiver
unisevtPortSw-XFP-10GBASE-PRX-D3               OBJECT IDENTIFIER ::= { unisevtPortSwitchType 279 }  -- XFP 10GBase PRX-D3 Optical Transceiver
unisevtPortSw-5GBASE-T                    OBJECT IDENTIFIER ::= { unisevtPortSwitchType 280 }  -- 5G Base-T Port
unisevtPortSw-QSFP28-UNKNOWN              OBJECT IDENTIFIER ::= { unisevtPortSwitchType 281 }  -- Unknown QSFP28 Transceiver
unisevtPortSw-SFP28-UNKNOWN               OBJECT IDENTIFIER ::= { unisevtPortSwitchType 282 }  -- Unknown SFP28 Transceiver
unisevtPortSw-SFP28-NO-CONNECTOR          OBJECT IDENTIFIER ::= { unisevtPortSwitchType 283 }  -- SFP28 No Connector
unisevtPortSw-SFP-PLUS-9-8GCRPI-IR        OBJECT IDENTIFIER ::= { unisevtPortSwitchType 284 }  -- 9.8GCRPI-IR SFP+ Transceiver
unisevtPortSw-SFP-PLUS-9-8GCRPI-LR        OBJECT IDENTIFIER ::= { unisevtPortSwitchType 285 }  -- 9.8GCRPI-LR SFP+ Transceiver
unisevtPortSw-50GBase-F                   OBJECT IDENTIFIER ::= { unisevtPortSwitchType 286 }  -- 50G Ethernet port with QSFP28
unisevtPortSw-QSFP28-50GBASE-PAM4-LR       OBJECT IDENTIFIER ::= { unisevtPortSwitchType 287 }  -- 50GBASE-PAM4-LR QSFP28 Optical Transceiver
unisevtPortSw-10GBASE-BIDI-SFP             OBJECT IDENTIFIER ::= { unisevtPortSwitchType 288 }  -- 10GBASE  SFP+ BIDI Optical Transceiver

unisevtPortSw-10GBASE-BIDI-U-SFP-PLUS     OBJECT IDENTIFIER ::= { unisevtPortSwitchType 291 }  -- 10GBASE  SFP+ BIDI Up Optical Transceiver
unisevtPortSw-10GBASE-BIDI-D-SFP-PLUS     OBJECT IDENTIFIER ::= { unisevtPortSwitchType 292 }  -- 10GBASE  SFP+ BIDI Down Optical Transceiver
unisevtPortSw-QSFPDD-STACK-CONNECTOR      OBJECT IDENTIFIER ::= { unisevtPortSwitchType 293 }  -- QSFPDD-STACK-Transceiver
unisevtPortSw-QSFPDD-400GBASE-SR8         OBJECT IDENTIFIER ::= { unisevtPortSwitchType 294 }  -- 400GBASE-SR8  QSFP-DD Optical Transceiver
unisevtPortSw-QSFP28-100GBASE-ZR2         OBJECT IDENTIFIER ::= { unisevtPortSwitchType 295 }   -- 100GBASE-ZR2 QSFP28 Optical Transceiver
unisevtPortSw-QSFP28-50GBASE-ER           OBJECT IDENTIFIER ::= { unisevtPortSwitchType 296 }  -- 50GBASE ER QSFP28 Optical Transceiver Module
unisevtPortSw-SFP28-25GBASE-eLR           OBJECT IDENTIFIER ::= { unisevtPortSwitchType 297 }  -- 25GBASE-eLR SFP28 Optical Transceiver
unisevtPortSw-QSFP28-100GBASE-ER4-NO-FEC   OBJECT IDENTIFIER ::= { unisevtPortSwitchType 298 }  -- 100GBASE-ER4 QSFP28 Optical Transceiver Module
unisevtPortSw-QSFP28-100GBASE-ZR4         OBJECT IDENTIFIER ::= { unisevtPortSwitchType 299 }  -- 100GBASE-ZR4 QSFP28 Optical Transceiver Module
--
-- unisevtStack section:
--
unisevtStack     OBJECT IDENTIFIER ::= { unisEntityVendortypeObjects 11 }


END
