-- ==================================================================
-- Copyright (c) 2020 Unisyue Technologies Co., Ltd.  All rights reserved.
--
-- Description: Lan Switch VLAN MIB
-- Reference:
-- Version: V2.3
-- History:
-- (1) Created by Zhangshilin, 2001.06.29
-- (2) Revised by Qi Zhenglin, 2002.01.08
--   V1.1 2004-09-08 modify STATUS of unisLswVlanProtoObject from mandatory to current by gaolong.
--   V1.2 2004-09-23 add ifEntry IMPORT clause by gaolong
--   V1.3 2004-10-12 updated by gaolong
--        Import TEXTUAL-CONVENTION and OBJECT-IDENTITY.
--        Relocate unisLswVlan MODULE-IDENTITY.
--        Change MAX-ACCESS clause value of unisVLANMibSwitchGarpStatClear to read-write.
--   V1.4 2004-12-28 modified by jiaoyi
--          Add unisdot1qVlanMulticast in unisdot1qVlanMIBTable
--        2005-01-22 update by wangyingxia
--          Add all objects of unisLswVlanMngObject from UNIS-LswINF-MIB into this MIB
--          Add TruthValue, RowStatus, TimeTicks, IpAddress, SnmpAdminString, VlanIndex, PortList
--          Remove InterfaceIndex and import it from UNIS-LswINF-MIB
--   V1.5 2005-01-22
--        Add superVlan to unisdot1qVlanType by sunqiang
--   V1.6 2005-05-18
--        Add unisDot1qVlanBatchMIBTable by lipei
--   V1.7 2005-08-08
--        Add UnisVlanIndex and modified all VlanIndex to UnisVlanIndex by longyin
--   V1.8 2006-02-14
--        Modify description of unisVlanInterfaceID, unisifIsolateSecondaryVlanlistLow
--        and unisifIsolateSecondaryVlanlistHigh by wangyong
--        Adjust the format of the file by wangyong
--        Add the object unisdot1qVlanTaggedPorts, unisdot1qVlanUntaggedPorts by jiliyan
--        Add unisifSuperVlanMappingTable, unisifSuperVlanMappingEntry, unisifSuperVlanID,
--        unisifSubVlanlistLow, unisifSubVlanlistHigh by hejunwei
--        Add unisdot1qVlanBatchSetOperate, change the description of
--        unisDot1qVlanBatchMIBTable and unisDot1qVlanBatchMIBEntry by hejunwei
--   V1.9 2007-12-18 Add enmu 'vrrp' for unisVlanInterfaceIpType by Zhangyinfei
--   V2.0 2010-01-18 Add unisdot1qVlanPortIndexs and unisVlanInterfaceIfIndex by duyanbing
--   V2.1 2012-06-11 Modify unisVlanInterfaceIpAddr, unisVlanInterfaceIpMask and unisVlanInterfaceIpType by liuxibo
--        2012-08-13
--        Add unisPrivateVlanMappingTable by chenkaiping
--        Add primaryVlan for unisdot1qVlanType by xiedong
--   V2.2 2015-11-12 Modify unisdot1qVlanName by yuhaiyan
--   V2.3 2016-08-29 Modify unisdot1qVlanMIBTable,add VLAN statistics related entries by niuchuanzheng
-- ==================================================================
UNIS-LswVLAN-MIB DEFINITIONS ::= BEGIN
IMPORTS
    TimeInterval, TEXTUAL-CONVENTION, TruthValue, RowStatus
        FROM SNMPv2-TC
    MODULE-IDENTITY, OBJECT-TYPE, Counter32, Integer32, OBJECT-IDENTITY, TimeTicks, IpAddress, Counter64
        FROM SNMPv2-SMI
    SnmpAdminString
        FROM SNMP-FRAMEWORK-MIB
    unislswCommon
        FROM UNIS-OID-MIB
    ifEntry
        FROM RFC1213-MIB
    unisifVLANTrunkStatusEntry, PortList
        FROM UNIS-LswINF-MIB;

    unisLswVlan MODULE-IDENTITY
            LAST-UPDATED "201608310000Z"
            ORGANIZATION
                "Unisyue Technologies Co., Ltd."
            CONTACT-INFO
                ""
            DESCRIPTION ""
            REVISION        "201608310000Z"
            DESCRIPTION
                "To modify size of unisdot1qVlanName."
            ::= { unislswCommon 2 }

    UnisVlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Integer32(0..2147483647)

-- ==================================================================
--
-- ======================= definition begin =========================
--
-- ==================================================================

    unisLswVlanMngObject OBJECT-IDENTITY
            STATUS current
            DESCRIPTION
                "Description."
            ::= { unisLswVlan 1 }

    unisdot1qVlanMIBTable OBJECT-TYPE
        SYNTAX SEQUENCE OF UnisDot1qVlanMIBEntry
        MAX-ACCESS not-accessible
        STATUS current
        DESCRIPTION
            "VLAN MIB table"
        ::= { unisLswVlanMngObject  1 }


    unisdot1qVlanMIBEntry OBJECT-TYPE
        SYNTAX UnisDot1qVlanMIBEntry
        MAX-ACCESS not-accessible
        STATUS current
        DESCRIPTION
            "Entries of VLAN MIB table"
        INDEX   { unisdot1qVlanIndex }
        ::= { unisdot1qVlanMIBTable 1}

    UnisDot1qVlanMIBEntry ::=
    SEQUENCE {
        unisdot1qVlanIndex    UnisVlanIndex,
        unisdot1qVlanName     SnmpAdminString,
        unisdot1qVlanPorts    PortList,
        unisdot1qVlanType     INTEGER,
        unisdot1qVlanMacFilter    TruthValue,
        unisdot1qVlanMcastUnknownProtos   TruthValue,
        unisExistInterface    TruthValue,
        unisVlanInterfaceIndex    INTEGER,
        unisdot1qVlanMacLearn TruthValue,
        unisdot1qVlanStatus   INTEGER,
        unisdot1qVlanCreationTime TimeTicks,
        unisdot1qVlanPriority INTEGER,
        unisdot1qVlanRowStatus    RowStatus,
        unisdot1qVlanBroadcastSuppression INTEGER,
        unisdot1qVlanBcastSuppressionPPS   INTEGER,
        unisdot1qVlanMulticast INTEGER,
        unisdot1qVlanTaggedPorts    PortList,
        unisdot1qVlanUntaggedPorts    PortList,
        unisdot1qVlanPortIndexs    OCTET STRING,
        unisdot1qVlanStatisticStatus    TruthValue,
        unisdot1qVlanStatisticClear    INTEGER,
        unisdot1qVlanStatisticInTotalPkts    Counter64,
        unisdot1qVlanStatisticInTotalBytes    Counter64,
        unisdot1qVlanStatisticInPPS    Counter64,
        unisdot1qVlanStatisticInBPS    Counter64,
        unisdot1qVlanStatisticOutTotalPkts    Counter64,
        unisdot1qVlanStatisticOutTotalBytes    Counter64,
        unisdot1qVlanStatisticOutPPS    Counter64,
        unisdot1qVlanStatisticOutBPS    Counter64
        }



    unisdot1qVlanIndex OBJECT-TYPE
        SYNTAX  UnisVlanIndex
        MAX-ACCESS read-only
        STATUS current
        DESCRIPTION
            "The VLAN-ID."
        ::= { unisdot1qVlanMIBEntry 1 }


    unisdot1qVlanName  OBJECT-TYPE
        SYNTAX  SnmpAdminString (SIZE (0..80))
        MAX-ACCESS read-write
        STATUS current
        DESCRIPTION
            "Name of the VLAN."
        ::= { unisdot1qVlanMIBEntry 2 }


    unisdot1qVlanPorts OBJECT-TYPE
        SYNTAX  PortList
        MAX-ACCESS read-write
        STATUS current
        DESCRIPTION
            "Port list of the VLAN."
        ::= { unisdot1qVlanMIBEntry 3 }


    unisdot1qVlanType  OBJECT-TYPE
        SYNTAX  INTEGER
        {
        superVlan   (1),
        common-vlan (2),
        sub-vlan    (3),
        isolate-user-vlan(4),
        secondary-vlan(5),
        primaryVlan(6)
        }
        MAX-ACCESS read-write
        STATUS current
        DESCRIPTION
            "Vlan types: SuperVlan(1), Common vlan(2), and Sub-vlan(3)."
        ::= { unisdot1qVlanMIBEntry 4 }


    unisdot1qVlanMacFilter OBJECT-TYPE
        SYNTAX  TruthValue
        MAX-ACCESS read-only
        STATUS current
        DESCRIPTION
            "Whether to filter MAC addresses."
        ::= { unisdot1qVlanMIBEntry 5 }


    unisdot1qVlanMcastUnknownProtos OBJECT-TYPE
        SYNTAX  TruthValue
        MAX-ACCESS read-only
        STATUS current
        DESCRIPTION
            "Whether to broadcast the unknown packets."
        ::= { unisdot1qVlanMIBEntry 6 }


    unisExistInterface OBJECT-TYPE
        SYNTAX  TruthValue
        MAX-ACCESS read-only
        STATUS current
        DESCRIPTION
            "Whether there is virtual interface."
        ::= { unisdot1qVlanMIBEntry 7 }


    unisVlanInterfaceIndex OBJECT-TYPE
        SYNTAX  INTEGER
        MAX-ACCESS read-only
        STATUS current
        DESCRIPTION
            "Whether vlan interface is configured on vlan. If vlan interface is
            configured, the value of the node is vlan id, else the value is 0."
        ::= { unisdot1qVlanMIBEntry 8 }


    unisdot1qVlanMacLearn OBJECT-TYPE
        SYNTAX  TruthValue
        MAX-ACCESS read-only
        STATUS current
        DESCRIPTION
            "MAC address learning identity. (common vlan/Sub-vlan)"
        ::= { unisdot1qVlanMIBEntry 9 }


    unisdot1qVlanStatus OBJECT-TYPE
        SYNTAX  INTEGER
        {
        other       (1),
        static   (2),
        dynamic (3)
        }
        MAX-ACCESS read-only
        STATUS current
        DESCRIPTION
            "Status of the VLAN."
        ::= { unisdot1qVlanMIBEntry 10 }


    unisdot1qVlanCreationTime OBJECT-TYPE
        SYNTAX  TimeTicks
        MAX-ACCESS read-only
        STATUS current
        DESCRIPTION
            "The sysUPTime when the VLAN is created."
        ::= { unisdot1qVlanMIBEntry 11 }


    unisdot1qVlanPriority OBJECT-TYPE
        SYNTAX  INTEGER (0..7)
        MAX-ACCESS read-write
        STATUS current
        DESCRIPTION
            "Priority of the VLAN."
        DEFVAL  {0}
        ::= { unisdot1qVlanMIBEntry 12 }


    unisdot1qVlanRowStatus  OBJECT-TYPE
        SYNTAX  RowStatus
        MAX-ACCESS read-create
        STATUS current
        DESCRIPTION
            "Operation status."
        ::= { unisdot1qVlanMIBEntry 13 }

    unisdot1qVlanBroadcastSuppression  OBJECT-TYPE
        SYNTAX  INTEGER (0..100)
        MAX-ACCESS read-write
        STATUS current
        DESCRIPTION
            "Whether broadcast suppression of vlan be supported pro rata.
            The vlaue of 100 indicates no broadcast suppression. If the
            function is not supported, this object cannot be written,
            and 100 will be returned when reading"
        DEFVAL { 100 }
        ::= { unisdot1qVlanMIBEntry 14 }

    unisdot1qVlanBcastSuppressionPPS   OBJECT-TYPE
        SYNTAX  INTEGER (0..148800)
        MAX-ACCESS read-write
        STATUS current
        DESCRIPTION
            "If the broadcast can be controlled with pps(packet per second)type,
            the value of 0 indicates no suppression. This node is conflicted
            with unisdot1qVlanBroadcastSuppression. If the mode is set,
            unisdot1qVlanBroadcastSuppression is unavailable. And vice versa."
        ::= { unisdot1qVlanMIBEntry 15 }

    unisdot1qVlanMulticast  OBJECT-TYPE
        SYNTAX  INTEGER
        {
        disable  (0),
        enable   (1)
        }
        MAX-ACCESS read-write
        STATUS current
        DESCRIPTION
            "Multicast vlan. The default value is disable(0)."
        ::= { unisdot1qVlanMIBEntry 16 }

    unisdot1qVlanTaggedPorts OBJECT-TYPE
        SYNTAX  PortList
        MAX-ACCESS read-only
        STATUS current
        DESCRIPTION
            "Tagged port list of the VLAN."
        ::= { unisdot1qVlanMIBEntry 17 }

    unisdot1qVlanUntaggedPorts OBJECT-TYPE
        SYNTAX  PortList
        MAX-ACCESS read-only
        STATUS current
        DESCRIPTION
            "Untagged port list of the VLAN."
        ::= { unisdot1qVlanMIBEntry 18 }

    unisdot1qVlanPortIndexs OBJECT-TYPE
        SYNTAX  OCTET STRING
        MAX-ACCESS read-write
        STATUS current
        DESCRIPTION
            "PortIndex list of the VLAN, that delimited by comma, such as 1,3,4,7."
        ::= { unisdot1qVlanMIBEntry 19 }

    unisdot1qVlanStatisticStatus OBJECT-TYPE
        SYNTAX  TruthValue
        MAX-ACCESS read-write
        STATUS current
        DESCRIPTION
            "VLAN traffic statistics switch.
            The default value is false, which means the switch is off."
        ::= { unisdot1qVlanMIBEntry 20 }

    unisdot1qVlanStatisticClear  OBJECT-TYPE
        SYNTAX  INTEGER
        {
            clear(1)
        }
        MAX-ACCESS read-write
        STATUS current
        DESCRIPTION
            "Clear statistics for the specified VLANs. Operation read is not supported."
        ::= { unisdot1qVlanMIBEntry 21 }

    unisdot1qVlanStatisticInTotalPkts OBJECT-TYPE
        SYNTAX      Counter64
        MAX-ACCESS  read-only
        STATUS      current
        DESCRIPTION
            "The total number of inbound packets."
        ::= { unisdot1qVlanMIBEntry 22 }

    unisdot1qVlanStatisticInTotalBytes OBJECT-TYPE
        SYNTAX      Counter64
        MAX-ACCESS  read-only
        STATUS      current
        DESCRIPTION
            "The total number of inbound bytes."
        ::= { unisdot1qVlanMIBEntry 23 }

    unisdot1qVlanStatisticInPPS OBJECT-TYPE
        SYNTAX      Counter64
        MAX-ACCESS  read-only
        STATUS      current
        DESCRIPTION
            "The number of inbound packets per second."
        ::= { unisdot1qVlanMIBEntry 24 }

    unisdot1qVlanStatisticInBPS OBJECT-TYPE
        SYNTAX      Counter64
        MAX-ACCESS  read-only
        STATUS      current
        DESCRIPTION
            "The number of inbound bytes per second."
        ::= { unisdot1qVlanMIBEntry 25 }

    unisdot1qVlanStatisticOutTotalPkts OBJECT-TYPE
        SYNTAX      Counter64
        MAX-ACCESS  read-only
        STATUS      current
        DESCRIPTION
            "The total number of outbound packets."
        ::= { unisdot1qVlanMIBEntry 26 }

    unisdot1qVlanStatisticOutTotalBytes OBJECT-TYPE
        SYNTAX      Counter64
        MAX-ACCESS  read-only
        STATUS      current
        DESCRIPTION
            "The total number of outbound bytes."
        ::= { unisdot1qVlanMIBEntry 27 }

    unisdot1qVlanStatisticOutPPS OBJECT-TYPE
        SYNTAX      Counter64
        MAX-ACCESS  read-only
        STATUS      current
        DESCRIPTION
            "The number of outbound packets per second."
        ::= { unisdot1qVlanMIBEntry 28 }

    unisdot1qVlanStatisticOutBPS OBJECT-TYPE
        SYNTAX      Counter64
        MAX-ACCESS  read-only
        STATUS      current
        DESCRIPTION
            "The number of outbound bytes per second."
        ::= { unisdot1qVlanMIBEntry 29 }

    unisVlanInterfaceTable OBJECT-TYPE
        SYNTAX SEQUENCE OF UnisVlanInterfaceEntry
        MAX-ACCESS not-accessible
        STATUS current
        DESCRIPTION
            "Virtual interface configuration table"
        ::= { unisLswVlanMngObject  2}


    unisVlanInterfaceEntry OBJECT-TYPE
        SYNTAX UnisVlanInterfaceEntry
        MAX-ACCESS not-accessible
        STATUS current
        DESCRIPTION
            "Entries of virtual interface configuration table"
        INDEX   { unisVlanInterfaceID }
        ::= {unisVlanInterfaceTable 1}

    UnisVlanInterfaceEntry    ::=
    SEQUENCE {
        unisVlanInterfaceID       INTEGER,
        unisdot1qVlanID       UnisVlanIndex,
        unisdot1qVlanIpAddress        IpAddress,
        unisdot1qVlanIpAddressMask    IpAddress,
        unisVlanInterfaceAdminStatus  INTEGER,
        unisVlanInterfaceFrameType    INTEGER,
        unisInterfaceRowStatus        RowStatus,
        unisVlanInterfaceIpMethod     INTEGER,
        unisVlanInterfaceIfIndex      INTEGER
        }

    unisVlanInterfaceID OBJECT-TYPE
        SYNTAX  INTEGER
        MAX-ACCESS read-only
        STATUS current
        DESCRIPTION
            "Index of the vlan interface table."
        ::= { unisVlanInterfaceEntry 1 }


    unisdot1qVlanID OBJECT-TYPE
        SYNTAX  UnisVlanIndex
        MAX-ACCESS read-only
        STATUS current
        DESCRIPTION
            "VLAN-ID"
        ::= { unisVlanInterfaceEntry 2 }


    unisdot1qVlanIpAddress OBJECT-TYPE
        SYNTAX  IpAddress
        MAX-ACCESS read-write
        STATUS current
        DESCRIPTION
            "IP address of interface."
        ::= { unisVlanInterfaceEntry 3 }


    unisdot1qVlanIpAddressMask OBJECT-TYPE
        SYNTAX  IpAddress
        MAX-ACCESS read-write
        STATUS current
        DESCRIPTION
            "IP address mask of interface."
        ::= { unisVlanInterfaceEntry 4 }

    unisVlanInterfaceAdminStatus OBJECT-TYPE
        SYNTAX  INTEGER
        {
        up      (1),
        down    (2)
        }
        MAX-ACCESS read-write
        STATUS current
        DESCRIPTION
            "Status of VLAN virtual interfaces."
        ::= { unisVlanInterfaceEntry 5 }

    unisVlanInterfaceFrameType OBJECT-TYPE
        SYNTAX  INTEGER
        {
        ethernet-ii     (1),
        ethernet-snap   (2),
        ethernet-8022   (3),
        ethernet-8023   (4)
        }
        MAX-ACCESS read-only
        STATUS current
        DESCRIPTION
            "Frame type accepted by VLAN virtual interfaces."
        ::= { unisVlanInterfaceEntry 6 }


    unisInterfaceRowStatus OBJECT-TYPE
        SYNTAX  RowStatus
        MAX-ACCESS read-create
        STATUS current
        DESCRIPTION
            "Operation status."
        ::= { unisVlanInterfaceEntry 7 }


    unisVlanInterfaceIpMethod OBJECT-TYPE
        SYNTAX  INTEGER
        {
        assigned-ip    (1),
        dhcp-ip        (2),
        bootp-ip       (3)
        }
        MAX-ACCESS read-write
        STATUS current
        DESCRIPTION
            "Vlan interface ip address acquiring method which is manual, dhcp or bootp."
        ::= { unisVlanInterfaceEntry 8 }

    unisVlanInterfaceIfIndex OBJECT-TYPE
        SYNTAX  INTEGER
        MAX-ACCESS read-only
        STATUS current
        DESCRIPTION
            "IfIndex of VLAN interface."
        ::= { unisVlanInterfaceEntry 9 }

    unisifIsolateMappingTable OBJECT-TYPE
        SYNTAX SEQUENCE OF UnisifIsolateMappingEntry
        MAX-ACCESS not-accessible
        STATUS current
        DESCRIPTION
            "Secondary vlan lists of Isolate-VLANs."
        ::= { unisLswVlanMngObject  4 }


    unisifIsolateMappingEntry OBJECT-TYPE
        SYNTAX UnisifIsolateMappingEntry
        MAX-ACCESS not-accessible
        STATUS current
        DESCRIPTION
             "Secondary vlan lists of Isolate-VLANs."
        INDEX   { unisifIsolatePrimaryVlanID }
        ::= { unisifIsolateMappingTable 1}

    UnisifIsolateMappingEntry   ::=
    SEQUENCE {
        unisifIsolatePrimaryVlanID  UnisVlanIndex,
        unisifIsolateSecondaryVlanlistLow   OCTET STRING,
        unisifIsolateSecondaryVlanlistHigh OCTET STRING
        }

    unisifIsolatePrimaryVlanID OBJECT-TYPE
        SYNTAX  UnisVlanIndex
        MAX-ACCESS read-only
        STATUS current
        DESCRIPTION
            "Primary VLAN-ID."
        ::= { unisifIsolateMappingEntry 1 }


    unisifIsolateSecondaryVlanlistLow OBJECT-TYPE
        SYNTAX  OCTET STRING(SIZE(0..256))
        MAX-ACCESS read-write
        STATUS current
        DESCRIPTION
            "Each octet within this value specifies a set of eight
            VLANs, with the first octet specifying VLANs 1 through
            8, the second octet specifying VLANs 9 through 16, etc.
            Within each octet, the most significant bit represents
            the highest numbered VLAN, and the least significant bit
            represents the lowest numbered VLAN. Thus, each secondary
            VLAN of the primary VLAN is represented by a single bit
            within the value of this object. If that bit has a value
            of '1' then that VLAN is secondary VLAN in the set of VLANs;
            the VLAN is not secondary VLAN if its bit has a value of
            '0'."
        ::= { unisifIsolateMappingEntry 2 }

    unisifIsolateSecondaryVlanlistHigh OBJECT-TYPE
        SYNTAX  OCTET STRING(SIZE(0..256))
        MAX-ACCESS read-write
        STATUS current
        DESCRIPTION
            "Each octet within this value specifies a set of eight
            VLANs, with the first octet specifying VLANs 2049 through
            2056, the second octet specifying VLANs 2057 through 2064,
            etc. Within each octet, the most significant bit represents
            the highest numbered VLAN, and the least significant bit
            represents the lowest numbered VLAN. Thus, each secondary
            VLAN of the primary VLAN is represented by a single bit
            within the value of this object. If that bit has a value
            of '1' then that VLAN is secondary VLAN in the set of VLANs;
            the VLAN is not secondary VLAN if its bit has a value of
            '0'."
        ::= { unisifIsolateMappingEntry 3 }

    unisVlanInterfaceAddrTable OBJECT-TYPE
        SYNTAX SEQUENCE OF UnisVlanInterfaceAddrEntry
        MAX-ACCESS not-accessible
        STATUS current
        DESCRIPTION
            "VLAN interface IP address configuration table"
        ::= { unisLswVlanMngObject 5 }

    unisVlanInterfaceAddrEntry OBJECT-TYPE
        SYNTAX UnisVlanInterfaceAddrEntry
        MAX-ACCESS not-accessible
        STATUS current
        DESCRIPTION
            "Entries of VLAN interface IP address configuration table"
        INDEX   { unisVlanInterfaceIpIfIndex, unisVlanInterfaceIpAddr }
        ::= { unisVlanInterfaceAddrTable 1 }

    UnisVlanInterfaceAddrEntry ::=
    SEQUENCE {
        unisVlanInterfaceIpIfIndex     INTEGER,
        unisVlanInterfaceIpAddr        IpAddress,
        unisVlanInterfaceIpMask        IpAddress,
        unisVlanInterfaceIpType        INTEGER,
        unisVlanInterfaceIpRowStatus   RowStatus
        }

    unisVlanInterfaceIpIfIndex OBJECT-TYPE
        SYNTAX  INTEGER
        MAX-ACCESS read-only
        STATUS current
        DESCRIPTION
            "Index of VLAN interfaces."
        ::= { unisVlanInterfaceAddrEntry 1 }

    unisVlanInterfaceIpAddr OBJECT-TYPE
        SYNTAX  IpAddress
        MAX-ACCESS read-only
        STATUS current
        DESCRIPTION
            "IP address of VLAN interface."
        ::= { unisVlanInterfaceAddrEntry 2 }

    unisVlanInterfaceIpMask OBJECT-TYPE
        SYNTAX  IpAddress
        MAX-ACCESS read-create
        STATUS current
        DESCRIPTION
            "IP address mask of VLAN interface. When destory single IP address,
            you must set it correct to relative IP address."
        ::= { unisVlanInterfaceAddrEntry 3 }

    unisVlanInterfaceIpType OBJECT-TYPE
        SYNTAX  INTEGER
        {
        primary     (1),
        sub         (2),
        cluster     (3),
        vrrp        (4)
        }
        MAX-ACCESS read-create
        STATUS current
        DESCRIPTION
            "IP address type."
        ::= { unisVlanInterfaceAddrEntry 4 }

    unisVlanInterfaceIpRowStatus OBJECT-TYPE
        SYNTAX  RowStatus
        MAX-ACCESS read-create
        STATUS current
        DESCRIPTION
            "Operation status. active(1) will only be set when taking GET or
            GET NEXT operation. createAndGo(4) and destory(6) is valid when
            taking SET operation."
        ::= { unisVlanInterfaceAddrEntry 5 }


    unisDot1qVlanBatchMIBTable  OBJECT-TYPE
        SYNTAX SEQUENCE OF UnisDot1qVlanBatchMIBEntry
        MAX-ACCESS not-accessible
        STATUS current
        DESCRIPTION
            "VLAN batch configuration table.
            In the case of VLAN batch creation, unisdot1qVlanBatchSetOperate should
            be set to 1.
            For example, if creating a row is for creating VLANs 2 to 4, the value
            of the objects should be set as follows:
            unisdot1qVlanBatchStartIndex 2,
            unisdot1qVlanBatchEndIndex 4,
            unisdot1qVlanBatchSetOperate create(1),
            unisdot1qVlanBatchRowStatus createAndGo(4).

            In the case of VLAN batch deletion, unisdot1qVlanBatchSetOperate should
            be set to 2.
            For example, if creating a row is for deleting VLANs 10 to 20, the value
            of the objects should be set as follows:
            unisdot1qVlanBatchStartIndex 10,
            unisdot1qVlanBatchEndIndex 20,
            unisdot1qVlanBatchSetOperate delete(2),
            unisdot1qVlanBatchRowStatus createAndGo(4).

            When the action of batch VLANs deleting or creating is done, one row
            will be existent until it is deleted manually or ages out, but the VLANs
            of it won't disappear with the deletion of the row."
        ::= { unisLswVlanMngObject  6 }

    unisDot1qVlanBatchMIBEntry OBJECT-TYPE
        SYNTAX UnisDot1qVlanBatchMIBEntry
        MAX-ACCESS not-accessible
        STATUS current
        DESCRIPTION
            "VLAN batch configuration entry."
        INDEX   { unisdot1qVlanBatchOperIndex }
        ::= { unisDot1qVlanBatchMIBTable 1}

    UnisDot1qVlanBatchMIBEntry ::=
        SEQUENCE {
            unisdot1qVlanBatchOperIndex
                Integer32,
            unisdot1qVlanBatchStartIndex
                UnisVlanIndex,
            unisdot1qVlanBatchEndIndex
                UnisVlanIndex,
            unisdot1qVlanBatchOperStatus
                INTEGER,
            unisdot1qVlanBatchRowStatus
                RowStatus,
            unisdot1qVlanBatchSetOperate
                INTEGER
        }

    unisdot1qVlanBatchOperIndex OBJECT-TYPE
        SYNTAX  Integer32
        MAX-ACCESS read-only
        STATUS current
        DESCRIPTION
            "The consequence of operation."
        ::= { unisDot1qVlanBatchMIBEntry 1 }

    unisdot1qVlanBatchStartIndex OBJECT-TYPE
        SYNTAX  UnisVlanIndex
        MAX-ACCESS read-write
        STATUS current
        DESCRIPTION
            "The value of start VLAN-ID."
        ::= { unisDot1qVlanBatchMIBEntry 2 }

    unisdot1qVlanBatchEndIndex OBJECT-TYPE
        SYNTAX  UnisVlanIndex
        MAX-ACCESS read-write
        STATUS current
        DESCRIPTION
            "The value of end VLAN-ID."
        ::= { unisDot1qVlanBatchMIBEntry 3 }

    unisdot1qVlanBatchOperStatus OBJECT-TYPE
        SYNTAX  INTEGER
        {
            opInprogress      (1), -- If the operation is running, the system
                                   -- will return OpInprogress.
            opfailure         (2), -- If the operation is failure, the system
                                   -- will return Opfailure.
            opsuccess         (3), -- If the operation is success, the system
                                   -- will return Opsuccess.
            opsuccesspartial  (4)  -- If the operation is success partially,
                                   -- the system will return Opsuccesspartial.
        }
        MAX-ACCESS read-only
        STATUS current
        DESCRIPTION
            "The status of operation."
        ::= { unisDot1qVlanBatchMIBEntry 4 }

    unisdot1qVlanBatchRowStatus OBJECT-TYPE
        SYNTAX  RowStatus
        MAX-ACCESS read-create
        STATUS current
        DESCRIPTION
            "The row status of UnisDot1qVlanBatchMIBEntry."
        ::= { unisDot1qVlanBatchMIBEntry 5 }

    unisdot1qVlanBatchSetOperate OBJECT-TYPE
         SYNTAX  INTEGER
         {
            create(1),
            delete(2)
         }
        MAX-ACCESS read-create
        STATUS current
        DESCRIPTION
            "VLAN batch creation or deletion."
        ::= { unisDot1qVlanBatchMIBEntry 6 }

    unisifSuperVlanMappingTable OBJECT-TYPE
        SYNTAX SEQUENCE OF UnisifSuperVlanMappingEntry
        MAX-ACCESS not-accessible
        STATUS current
        DESCRIPTION
            "Sub VLAN lists of super-VLANs."
        ::= { unisLswVlanMngObject  7 }

    unisifSuperVlanMappingEntry OBJECT-TYPE
        SYNTAX UnisifSuperVlanMappingEntry
        MAX-ACCESS not-accessible
        STATUS current
        DESCRIPTION
            "Sub VLAN lists of super-VLANs."
        INDEX   { unisifSuperVlanID }
        ::= { unisifSuperVlanMappingTable 1}

    UnisifSuperVlanMappingEntry   ::=
    SEQUENCE {
        unisifSuperVlanID  UnisVlanIndex,
        unisifSubVlanlistLow   OCTET STRING,
        unisifSubVlanlistHigh  OCTET STRING
        }

    unisifSuperVlanID OBJECT-TYPE
        SYNTAX  UnisVlanIndex
        MAX-ACCESS read-only
        STATUS current
        DESCRIPTION
            "Super VLAN ID."
        ::= { unisifSuperVlanMappingEntry 1 }

    unisifSubVlanlistLow OBJECT-TYPE
        SYNTAX  OCTET STRING(SIZE(0..256))
        MAX-ACCESS read-write
        STATUS current
        DESCRIPTION
            "Each octet within this value specifies a set of eight
            VLANs, with the first octet specifying VLANs 1 through
            8, the second octet specifying VLANs 9 through 16, etc.
            Within each octet, the most significant bit represents
            the highest numbered VLAN, and the least significant bit
            represents the lowest numbered VLAN. Thus, each sub
            VLAN of the super VLAN is represented by a single bit
            within the value of this object. If that bit has a value
            of '1' then that VLAN is a sub VLAN of the super VLAN; the
            VLAN is not a sub VLAN of the super VLAN if its bit has
            a value of '0'."
        ::= { unisifSuperVlanMappingEntry 2 }

    unisifSubVlanlistHigh OBJECT-TYPE
        SYNTAX  OCTET STRING(SIZE(0..256))
        MAX-ACCESS read-write
        STATUS current
        DESCRIPTION
            "Each octet within this value specifies a set of eight
            VLANs, with the first octet specifying VLANs 2049 through
            2056, the second octet specifying VLANs 2057 through 2064,
            etc. Within each octet, the most significant bit represents
            the highest numbered VLAN, and the least significant bit
            represents the lowest numbered VLAN. Thus, each sub
            VLAN of the super VLAN is represented by a single bit
            within the value of this object. If that bit has a value of
            '1' then that VLAN is a sub VLAN of the super VLAN; the
            VLAN is not a sub VLAN of the super VLAN if its bit has
            a value of '0'."
        ::= { unisifSuperVlanMappingEntry 3 }

    unisPrivateVlanMappingTable OBJECT-TYPE
        SYNTAX SEQUENCE OF UnisPrivateVlanMappingEntry
        MAX-ACCESS not-accessible
        STATUS current
        DESCRIPTION
            "Secondary vlan lists of Primary-VLANs."
        ::= { unisLswVlanMngObject  8 }

    unisPrivateVlanMappingEntry OBJECT-TYPE
        SYNTAX UnisPrivateVlanMappingEntry
        MAX-ACCESS not-accessible
        STATUS current
        DESCRIPTION
             "Secondary vlan lists of Primary-VLANs."
        INDEX   { unisPrimaryVlanID }
        ::= { unisPrivateVlanMappingTable 1}

    UnisPrivateVlanMappingEntry   ::=
    SEQUENCE {
        unisPrimaryVlanID  UnisVlanIndex,
        unisSecondaryVlanlistLow   OCTET STRING,
        unisSecondaryVlanlistHigh OCTET STRING
        }

    unisPrimaryVlanID OBJECT-TYPE
        SYNTAX  UnisVlanIndex
        MAX-ACCESS read-only
        STATUS current
        DESCRIPTION
            "Primary VLAN-ID."
        ::= { unisPrivateVlanMappingEntry 1 }

    unisSecondaryVlanlistLow OBJECT-TYPE
        SYNTAX  OCTET STRING(SIZE(0..256))
        MAX-ACCESS read-write
        STATUS current
        DESCRIPTION
            "Each octet within this value specifies a set of eight
            VLANs, with the first octet specifying VLANs 1 through
            8, the second octet specifying VLANs 9 through 16, etc.
            Within each octet, the most significant bit represents
            the highest numbered VLAN, and the least significant bit
            represents the lowest numbered VLAN.  Thus, each secondary
            VLAN of the primary VLAN is represented by a single bit
            within the value of this object.  If that bit has a value
            of '1' then that VLAN is secondary VLAN in the set of VLANs;
            the VLAN is not secondary VLAN if its bit has a value of
            '0'."
        ::= { unisPrivateVlanMappingEntry 2 }

    unisSecondaryVlanlistHigh OBJECT-TYPE
        SYNTAX  OCTET STRING(SIZE(0..256))
        MAX-ACCESS read-write
        STATUS current
        DESCRIPTION
            "Each octet within this value specifies a set of eight
            VLANs, with the first octet specifying VLANs 2049 through
            2056, the second octet specifying VLANs 2057 through 2064,
            etc.  Within each octet, the most significant bit represents
            the highest numbered VLAN, and the least significant bit
            represents the lowest numbered VLAN.  Thus, each secondary
            VLAN of the primary VLAN is represented by a single bit
            within the value of this object.  If that bit has a value
            of '1' then that VLAN is secondary VLAN in the set of VLANs;
            the VLAN is not secondary VLAN if its bit has a value of
            '0'."
        ::= { unisPrivateVlanMappingEntry 3 }

    unisLswVlanProtoObject OBJECT-IDENTITY
            STATUS current
            DESCRIPTION
                "Description."
            ::= { unisLswVlan 2 }

     unisVLANMibGarpLeaveAllTime OBJECT-TYPE
        SYNTAX      TimeInterval
        MAX-ACCESS  read-write
        STATUS      current
        DESCRIPTION
            "The GARP LeaveAll time, in centiseconds."
        DEFVAL      { 1000 }
        ::= { unisLswVlanProtoObject 14 }

     unisvLANMibSwitchCountTable OBJECT-TYPE
        SYNTAX  SEQUENCE OF UnisVLANMibSwitchCountEntry
        MAX-ACCESS not-accessible
        STATUS   current
        DESCRIPTION
            "A table containing the information various statistics of switch."
        ::= {unisLswVlanProtoObject 15 }


     unisvLANMibSwitchCountEntry OBJECT-TYPE
        SYNTAX  UnisVLANMibSwitchCountEntry
        MAX-ACCESS not-accessible
        STATUS current
        DESCRIPTION
            "A table containing the information various statistics of switch."
        AUGMENTS    {unisifVLANTrunkStatusEntry  }
        ::= {unisvLANMibSwitchCountTable 1}

    UnisVLANMibSwitchCountEntry   ::=
    SEQUENCE {
        unisVLANMibSwitchGMRPRXPkt    Counter32,
        unisVLANMibSwitchGVRPRXPkt    Counter32,
        unisVLANMibSwitchGMRPTXPkt    Counter32,
        unisVLANMibSwitchGVRPTXPkt    Counter32,
        unisVLANMibSwitchDiscardedPkt Counter32,
        unisVLANMibSwitchGarpStatClear INTEGER
        }



     unisVLANMibSwitchGMRPRXPkt OBJECT-TYPE
        SYNTAX  Counter32
        MAX-ACCESS read-only
        STATUS current
        DESCRIPTION
            "Number of GMRP frames received."
        ::= { unisvLANMibSwitchCountEntry 1 }


     unisVLANMibSwitchGVRPRXPkt OBJECT-TYPE
        SYNTAX  Counter32
        MAX-ACCESS read-only
        STATUS current
        DESCRIPTION
            "Number of GVRP frames received."
        ::= { unisvLANMibSwitchCountEntry 2 }


     unisVLANMibSwitchGMRPTXPkt OBJECT-TYPE
        SYNTAX  Counter32
        MAX-ACCESS read-only
        STATUS current
        DESCRIPTION
            "Number of GMRP frames transmitted."
        ::= { unisvLANMibSwitchCountEntry 3 }


     unisVLANMibSwitchGVRPTXPkt  OBJECT-TYPE
         SYNTAX  Counter32
         MAX-ACCESS read-only
         STATUS current
        DESCRIPTION
            "Number of GVRP frames transmitted."
         ::= { unisvLANMibSwitchCountEntry 4 }

     unisVLANMibSwitchDiscardedPkt  OBJECT-TYPE
         SYNTAX  Counter32
         MAX-ACCESS read-only
         STATUS current
        DESCRIPTION
            "Number of discarded frames."
         ::= { unisvLANMibSwitchCountEntry 5 }


     unisVLANMibSwitchGarpStatClear OBJECT-TYPE
        SYNTAX  INTEGER {clear(1)}
        MAX-ACCESS read-write
        STATUS current
        DESCRIPTION
            "Clear various Statistics viz. read operation not supported."
        ::= { unisvLANMibSwitchCountEntry 6 }


     unisvLANMibHoldTimeTable OBJECT-TYPE
        SYNTAX  SEQUENCE OF UnisVLANMibHoldTimeEntry
        MAX-ACCESS not-accessible
        STATUS   current
        DESCRIPTION
            "A table for setting/getting the Hold Time for a particular port."
        ::= {unisLswVlanProtoObject 16 }


     unisvLANMibHoldTimeEntry OBJECT-TYPE
        SYNTAX UnisVLANMibHoldTimeEntry
        MAX-ACCESS not-accessible
        STATUS   current
        DESCRIPTION
            "A table for setting/getting the HoldTime of the port."
         AUGMENTS    { ifEntry }
        ::= {unisvLANMibHoldTimeTable 1 }


    UnisVLANMibHoldTimeEntry  ::=
    SEQUENCE {
        unisVLANMibHoldTime   INTEGER
        }


     unisVLANMibHoldTime OBJECT-TYPE
        SYNTAX  INTEGER  (10..32765)
        MAX-ACCESS read-write
        STATUS current
        DESCRIPTION
            "HoldTime of the port."
        DEFVAL  {10}
        ::= { unisvLANMibHoldTimeEntry 1 }


END
