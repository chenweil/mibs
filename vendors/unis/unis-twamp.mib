-- =================================================================
-- Copyright (c) 2020 Unisyue Technologies Co., Ltd.  All rights reserved.
--
-- Description: The MIB is designed to configure the Two-Way Active Measurement Protocol.
-- Reference:
-- Version: V1.2
-- History:
-- V1.0 2019-06-22, Lv zhanbaobin, Initial Version
-- V1.1 2019-12-04 Modified by zhangzheng
--      Add interval10s in unisTwamplightSendAdminTxPeriod.
-- V1.2 2020-09-10 Modified by zhanbaobin
--      Complement the MIB of TWAMP-light according to the NETCONF.
--      Contains UnisTwamplightClientEntry,unisTwamplightReactionTable.
-- =================================================================
UNIS-TWAMP-MIB DEFINITIONS ::= BEGIN

IMPORTS
    MODULE-IDENTITY, OBJECT-TYPE,
    Integer32, Gauge32, Unsigned32
        FROM SNMPv2-SMI
    DateAndTime, DisplayString, RowStatus, TruthValue, MacAddress
        FROM SNMPv2-TC
    InetAddressType, InetAddress
        FROM INET-ADDRESS-MIB
    unisCommon
        FROM UNIS-OID-MIB;


unisTwamp MODULE-IDENTITY
    LAST-UPDATED "202009100000Z"
    ORGANIZATION
        "Unisyue Technologies Co., Ltd."
    CONTACT-INFO
        ""
    DESCRIPTION
        "The private MIB file includes the test information of the
        device.  It is to configure the Two-Way Active Measurement Protocol."
    REVISION "202009100000Z"
    DESCRIPTION
        "Complement the MIB of TWAMP-light according to the NETCONF.  Contains
         UnisTwamplightClientEntry,unisTwamplightReactionTable."
    REVISION "201912040000Z"
    DESCRIPTION
        "Add interval10s in unisTwamplightSendAdminTxPeriod."
    ::= { unisCommon 184 }


unisTwampNotifications OBJECT IDENTIFIER ::= { unisTwamp 1 }
unisTwamplightObjects OBJECT IDENTIFIER ::= { unisTwamp 2 }

unisTwamplightController            OBJECT IDENTIFIER ::= { unisTwamplightObjects 1 }
unisTwamplightReponsder             OBJECT IDENTIFIER ::= { unisTwamplightObjects 2 }




unisTwamplightClientEnable OBJECT-TYPE
    SYNTAX      TruthValue
    MAX-ACCESS  read-write
    STATUS      current
    DESCRIPTION
        "Control TWAMP-light control-client function.
            true: Enable TWAMP-light control-client function.
            false: Delete the TWAMP-light client and all its sessions and statistics."
    DEFVAL      { false }
    ::= {unisTwamplightController 1 }


unisTwamplightSenderEnable OBJECT-TYPE
    SYNTAX      TruthValue
    MAX-ACCESS  read-write
    STATUS      current
    DESCRIPTION
        "Control TWAMP-light control-sender function.
            true: Enable TWAMP-light control-sender function.
            false: Stop all TWAMP-light test sessions."
    DEFVAL      { false }
    ::= {unisTwamplightController 2 }


unisTwamplightClientTable OBJECT-TYPE
    SYNTAX      SEQUENCE OF UnisTwamplightClientEntry
    MAX-ACCESS  not-accessible
    STATUS      current
    DESCRIPTION
        "Defines TWAMP-light control-client test session parameter configuration."
    ::= { unisTwamplightController 3 }

unisTwamplightClientEntry OBJECT-TYPE
    SYNTAX      UnisTwamplightClientEntry
    MAX-ACCESS  not-accessible
    STATUS      current
    DESCRIPTION
        "Defines an entry in the unisTwamplightClientTable."
    INDEX {
              unisTwamplightControllerID
          }
    ::= { unisTwamplightClientTable 1 }

UnisTwamplightClientEntry ::=
    SEQUENCE {
        unisTwamplightControllerID           Integer32,
        unisTwamplightClientSrcAddrType      InetAddressType,
        unisTwamplightClientSrcAddr          InetAddress,
        unisTwamplightClientTrgtAddrType     InetAddressType,
        unisTwamplightClientTrgtAddr         InetAddress,
        unisTwamplightClientSrcPort          Integer32,
        unisTwamplightClientTrgtPort         Integer32,
        unisTwamplightClientVPN              DisplayString,
        unisTwamplightClientDscp             Integer32,
        unisTwamplightClientDataSize         Integer32,
        unisTwamplightClientDescription      DisplayString,
        unisTwamplightClientRowStatus        RowStatus,
        unisTwamplightClientSrcIfName        DisplayString,
        unisTwamplightClientServiceID        Unsigned32,
        unisTwamplightClientDesMac           MacAddress,
        unisTwamplightClientSrcMac           MacAddress,
        unisTwamplightClientTimeFormat       INTEGER,
        unisTwamplightClientDataFill         DisplayString,
        unisTwamplightClientDataFillType     INTEGER,
        unisTwamplightClientSVlanID          Unsigned32,
        unisTwamplightClientCVlanID          Unsigned32,
        unisTwamplightClientVlanPriority     Unsigned32,
        unisTwamplightClientBindIfName       DisplayString
    }

unisTwamplightControllerID OBJECT-TYPE
    SYNTAX      Integer32
    MAX-ACCESS  not-accessible
    STATUS      current
    DESCRIPTION
       "The session ID of the TWAMP-light test."
    ::= { unisTwamplightClientEntry 1 }

unisTwamplightClientSrcAddrType OBJECT-TYPE
    SYNTAX      InetAddressType
    MAX-ACCESS  read-create
    STATUS      current
    DESCRIPTION
        "Specifies the type of the source address,
        unisTwamplightClientSrcAddr, to be used at a remote host
        when performing the TWAMP-light test."
    ::= { unisTwamplightClientEntry 2 }

unisTwamplightClientSrcAddr OBJECT-TYPE
    SYNTAX      InetAddress
    MAX-ACCESS  read-create
    STATUS      current
    DESCRIPTION
        "Use the specified IP address (which must be given
        in numeric form, not as a hostname) as the source
        address in outgoing probe packets.  On hosts with
        more than one IP address, this option can be used
        to force the source address to be something other
        than the primary IP address of the interface the
        probe packet is sent on.  A zero length octet string
        value for this object disables source address
        specification.

        The address type (InetAddressType) that relates to
        this object is specified by the corresponding value
        of unisTwamplightClientSrcAddrType."
    DEFVAL { ''H }
    ::= { unisTwamplightClientEntry 3 }

unisTwamplightClientTrgtAddrType OBJECT-TYPE
    SYNTAX      InetAddressType
    MAX-ACCESS  read-create
    STATUS      current
    DESCRIPTION
        "Specifies the type of host address to be used at a remote
        host for performing a TWAMP-light test."
    ::= { unisTwamplightClientEntry 4 }

unisTwamplightClientTrgtAddr OBJECT-TYPE
    SYNTAX      InetAddress
    MAX-ACCESS  read-create
    STATUS      current
    DESCRIPTION
        "Specifies the host address to be used at a remote host for
        performing a TWAMP-light test.  The host address type is
        determined by the object value of corresponding
        unisTwamplightClientTrgtAddrType."
    DEFVAL { ''H }
    ::= { unisTwamplightClientEntry 5 }

unisTwamplightClientSrcPort          OBJECT-TYPE
    SYNTAX      Integer32 (0..65535)
    MAX-ACCESS  read-create
    STATUS      current
    DESCRIPTION
        "The source port be used by a TWAMP-light test."
    DEFVAL      { 0 }
    ::= { unisTwamplightClientEntry 6 }

unisTwamplightClientTrgtPort          OBJECT-TYPE
    SYNTAX      Integer32 (0..65535)
    MAX-ACCESS  read-create
    STATUS      current
    DESCRIPTION
        "The destination port that be used by a TWAMP-light test."
    DEFVAL      { 0 }
    ::= { unisTwamplightClientEntry 7 }

unisTwamplightClientVPN OBJECT-TYPE
    SYNTAX      DisplayString (SIZE (0..31))
    MAX-ACCESS  read-create
    STATUS      current
    DESCRIPTION
        "VPN name by which system finds route in the specified VPN
        to send TWAMP probe packets."
    DEFVAL      { "" }
    ::= { unisTwamplightClientEntry 8 }

unisTwamplightClientDscp OBJECT-TYPE
    SYNTAX      Integer32 (0..63)
    MAX-ACCESS  read-create
    STATUS      current
    DESCRIPTION
        "Specifies the value to store in the Differentiated
        Services Code Point (DSCP) in the IP packet used to
        encapsulate the TWAMP probe.  The DSCP field is defined
        as the Type of Service (TOS) octet in a IPv4 header
        or as the Traffic Class octet in a IPv6 header.

        The value of this object must be a decimal integer
        in the range from 0 to 63.  This option can be used
        to determine what effect an explicit DSCP field setting
        has on a TWAMP response."
    DEFVAL { 0 }
    ::= { unisTwamplightClientEntry 9 }

unisTwamplightClientDataSize OBJECT-TYPE
    SYNTAX      Integer32 (44..1518)
    UNITS       "octets"
    MAX-ACCESS  read-create
    STATUS      current
    DESCRIPTION
        "Specifies the size of the data portion to be
        transmitted in a TWAMP operation in octets."
    DEFVAL { 142 }
    ::= { unisTwamplightClientEntry 10 }

unisTwamplightClientDescription OBJECT-TYPE
    SYNTAX      DisplayString (SIZE (0..200))
    MAX-ACCESS  read-create
    STATUS      current
    DESCRIPTION
        "A comment describing this session."
    DEFVAL      { "" }
    ::= { unisTwamplightClientEntry 11 }

unisTwamplightClientRowStatus OBJECT-TYPE
    SYNTAX      RowStatus
    MAX-ACCESS  read-create
    STATUS      current
    DESCRIPTION
        "This object allows entries to be created and deleted
        in the unisTwamplightClientTable.  Deletion of an entry
        in this table results in deletion of all corresponding (same
        unisTwamplightControllerID index values)
        unisTwamplightSenderAdminTable and all related representations
        entries."
    REFERENCE
        "See definition of RowStatus in RFC 2579, 'Textual
        Conventions for SMIv2.'"
    ::= { unisTwamplightClientEntry 12 }

unisTwamplightClientSrcIfName OBJECT-TYPE
    SYNTAX      DisplayString (SIZE (0..47))
    MAX-ACCESS  read-create
    STATUS      current
    DESCRIPTION
        "The source interface for the probe packets."
    DEFVAL      { "" }
    ::= { unisTwamplightClientEntry 13 }

unisTwamplightClientServiceID OBJECT-TYPE
    SYNTAX      Unsigned32 (1..4096)
    UNITS       "octets"
    MAX-ACCESS  read-create
    STATUS      current
    DESCRIPTION
        "An Ethernet service instance by its ID for test."
    ::= { unisTwamplightClientEntry 14 }

unisTwamplightClientDesMac OBJECT-TYPE
    SYNTAX      MacAddress
    MAX-ACCESS  read-create
    STATUS      current
    DESCRIPTION
        "The destination MAC address for the TWAMP-light test."
    ::= { unisTwamplightClientEntry 15 }

unisTwamplightClientSrcMac OBJECT-TYPE
    SYNTAX      MacAddress
    MAX-ACCESS  read-create
    STATUS      current
    DESCRIPTION
        "The source MAC address for the TWAMP-light test."
    ::= { unisTwamplightClientEntry 16 }

unisTwamplightClientTimeFormat OBJECT-TYPE
    SYNTAX      INTEGER {
                            ntp (1),
                            ptp (2)
                        }
    MAX-ACCESS  read-create
    STATUS      current
    DESCRIPTION
        "The timestamp format for probe packets in
        the TWAMP-light test."
    ::= { unisTwamplightClientEntry 17 }

unisTwamplightClientDataFill OBJECT-TYPE
    SYNTAX      DisplayString (SIZE (1..200))
    MAX-ACCESS  read-create
    STATUS      current
    DESCRIPTION
        "The payload fill string for each probe packet in the TWAMP-light
         test.  If the unisTwamplightClientDataFillType is string,
         the string length is 1 to 200.  When unisTwamplightClientDataFillType
         is hex, the datafill should contain any even number of characters in
         the range of 2 to 200."
    ::= { unisTwamplightClientEntry 18 }

unisTwamplightClientDataFillType OBJECT-TYPE
    SYNTAX      INTEGER {
                            string (1),
                            hex (2)
                        }
    MAX-ACCESS  read-create
    STATUS      current
    DESCRIPTION
        "Specify the type of unisTwamplightClientDataFill."
    ::= { unisTwamplightClientEntry 19 }

unisTwamplightClientSVlanID OBJECT-TYPE
    SYNTAX      Unsigned32 (1..4094)
    MAX-ACCESS  read-create
    STATUS      current
    DESCRIPTION
        "Specify the ID of the VLAN to which the
         probe packets belong."
    ::= { unisTwamplightClientEntry 20 }

unisTwamplightClientCVlanID OBJECT-TYPE
    SYNTAX      Unsigned32 (1..4094)
    MAX-ACCESS  read-create
    STATUS      current
    DESCRIPTION
        "Specify the ID of the custom VLAN to which the
         probe packets belong.
         The unisTwamplightClientSVlanID must be specified
         first before the unisTwamplightClientCVlanID."
    ::= { unisTwamplightClientEntry 21 }

unisTwamplightClientVlanPriority OBJECT-TYPE
    SYNTAX      Unsigned32 (0..7)
    MAX-ACCESS  read-create
    STATUS      current
    DESCRIPTION
        "Specify set the 802.1p priority for the probe
         packets."
    ::= { unisTwamplightClientEntry 22 }

unisTwamplightClientBindIfName OBJECT-TYPE
    SYNTAX      DisplayString (SIZE (0..47))
    MAX-ACCESS  read-create
    STATUS      current
    DESCRIPTION
        "Associate the TWAMP-light test with an interface."
    DEFVAL      { "" }
    ::= { unisTwamplightClientEntry 23 }


unisTwamplightSenderAdminTable OBJECT-TYPE
    SYNTAX      SEQUENCE OF UnisTwamplightSenderAdminEntry
    MAX-ACCESS  not-accessible
    STATUS      current
    DESCRIPTION
        "Defines TWAMP-light control-sender's management table,
        starts or stops TWAMP light test function.  When the
        RowStatus is CreatAndGo, only one among unisTwamplightSendAdminContinual,
        unisTwamplightSendAdminDuration, and unisTwamplightSendAdminPktCount
        must be configured."
    ::= { unisTwamplightController 4 }

unisTwamplightSenderAdminEntry OBJECT-TYPE
    SYNTAX      UnisTwamplightSenderAdminEntry
    MAX-ACCESS  not-accessible
    STATUS      current
    DESCRIPTION
        "Defines an entry in the unisTwamplightSenderAdminTable."
    INDEX {
              unisTwamplightControllerID
          }
    ::= { unisTwamplightSenderAdminTable 1 }

UnisTwamplightSenderAdminEntry ::=
    SEQUENCE {
        unisTwamplightSendAdminContinual              TruthValue,
        unisTwamplightSendAdminDuration               Integer32,
        unisTwamplightSendAdminPktCount               Integer32,
        unisTwamplightSendAdminTxPeriod               INTEGER,
        unisTwamplightSendAdminTimeOut                Integer32,
        unisTwamplightSendAdminRowStatus              RowStatus
    }

unisTwamplightSendAdminContinual OBJECT-TYPE
    SYNTAX      TruthValue
    MAX-ACCESS  read-create
    STATUS      current
    DESCRIPTION
        "Defineds to control the TWAMP test type.
           true:  Permanent test.
           false: On demand test."
    ::= { unisTwamplightSenderAdminEntry 1 }

unisTwamplightSendAdminDuration OBJECT-TYPE
    SYNTAX      Integer32 (60..300)
    MAX-ACCESS  read-create
    STATUS      current
    DESCRIPTION
        "Defines the duration the session runs for TWAMP test
        before being stopped."
        ::= { unisTwamplightSenderAdminEntry 2 }

unisTwamplightSendAdminPktCount OBJECT-TYPE
    SYNTAX      Integer32 (100..30000)
    MAX-ACCESS  read-create
    STATUS      current
    DESCRIPTION
        "Defines the number of packets to send for TWAMP
        test before the session is stopped."
        ::= { unisTwamplightSenderAdminEntry 3 }

unisTwamplightSendAdminTxPeriod OBJECT-TYPE
    SYNTAX      INTEGER {
                          interval10ms(1),
                          interval100ms(2),
                          interval1s(3),
                          interval30s(4),
                          interval10s(5)
                        }
    MAX-ACCESS  read-create
    STATUS      current
    DESCRIPTION
        "Defines the interval at which probe packets are sent
        for TWAMP test."
    DEFVAL      { interval100ms }
    ::= { unisTwamplightSenderAdminEntry 4 }

unisTwamplightSendAdminTimeOut OBJECT-TYPE
    SYNTAX      Integer32 (1..10)
    MAX-ACCESS  read-create
    STATUS      current
    DESCRIPTION
        "Defines the timeout time for TWAMP response packets."
    DEFVAL      { 5 }
        ::= { unisTwamplightSenderAdminEntry 5 }

unisTwamplightSendAdminRowStatus OBJECT-TYPE
    SYNTAX      RowStatus
    MAX-ACCESS  read-create
    STATUS      current
    DESCRIPTION
        "This object allows entries to be created and deleted
        in the unisTwamplightSenderAdminTable."
    REFERENCE
        "See definition of RowStatus in RFC 2579, 'Textual
        Conventions for SMIv2.'"
    ::= { unisTwamplightSenderAdminEntry 6 }

unisTwamplightSenderStatusTable OBJECT-TYPE
    SYNTAX      SEQUENCE OF UnisTwamplightSenderStatusEntry
    MAX-ACCESS  not-accessible
    STATUS      current
    DESCRIPTION
        "Defines TWAMP-light control-sender's status table."
    ::= { unisTwamplightController 5 }

unisTwamplightSenderStatusEntry OBJECT-TYPE
    SYNTAX      UnisTwamplightSenderStatusEntry
    MAX-ACCESS  not-accessible
    STATUS      current
    DESCRIPTION
        "Defines an entry in the unisTwamplightSenderStatusTable."
    INDEX {
              unisTwamplightControllerID
          }
    ::= { unisTwamplightSenderStatusTable 1 }

UnisTwamplightSenderStatusEntry ::=
    SEQUENCE {
        unisTwamplightSenderStatus         INTEGER,
        unisTwamplightSenderStatusType     INTEGER,
        unisTwamplightLastStartTime        DateAndTime,
        unisTwamplightLastStopTime         DateAndTime
    }

unisTwamplightSenderStatus OBJECT-TYPE
    SYNTAX      INTEGER {
                            inactive(1),
                            active(2)
                        }
    MAX-ACCESS  read-only
    STATUS      current
    DESCRIPTION
        "Reflects the operational state of a TWAMP test:
           inactive: TWAMP test is in progress.
           active: TWAMP test has stopped."
    ::= { unisTwamplightSenderStatusEntry 1 }

unisTwamplightSenderStatusType OBJECT-TYPE
    SYNTAX      INTEGER {
                            init(0),
                            continual(1),
                            onDemand(2)
                        }
    MAX-ACCESS  read-only
    STATUS      current
    DESCRIPTION
        "Reflects the operational start type of a TWAMP test:
           init: Initial status.
           continual: Permanent test.
           onDemand: On demand test."
    ::= { unisTwamplightSenderStatusEntry 2 }

unisTwamplightLastStartTime OBJECT-TYPE
    SYNTAX      DateAndTime (SIZE (8))
    MAX-ACCESS  read-only
    STATUS      current
    DESCRIPTION
        "Date and time when the last test started."
    ::= { unisTwamplightSenderStatusEntry 4 }

unisTwamplightLastStopTime OBJECT-TYPE
    SYNTAX      DateAndTime (SIZE (8))
    MAX-ACCESS  read-only
    STATUS      current
    DESCRIPTION
        "Date and time when the last test stopped."
    ::= { unisTwamplightSenderStatusEntry 5 }



unisTwamplightTwoWayDelayTable OBJECT-TYPE
    SYNTAX      SEQUENCE OF UnisTwamplightTwoWayDelayEntry
    MAX-ACCESS  not-accessible
    STATUS      current
    DESCRIPTION
        "Defines the statistics result table for TWAMP test."
    ::= { unisTwamplightController 6 }

unisTwamplightTwoWayDelayEntry OBJECT-TYPE
    SYNTAX      UnisTwamplightTwoWayDelayEntry
    MAX-ACCESS  not-accessible
    STATUS      current
    DESCRIPTION
        "Defines an entry in the unisTwamplightTwoWayDelayTable."
    INDEX {
              unisTwamplightControllerID,
              unisTwamplightTWDelaySeq
          }
    ::= { unisTwamplightTwoWayDelayTable 1 }

UnisTwamplightTwoWayDelayEntry ::=
    SEQUENCE {
        unisTwamplightTWDelaySeq                   Gauge32,
        unisTwamplightTWDelayAvgDelay              Integer32,
        unisTwamplightTWDelayMaxDelay              Integer32,
        unisTwamplightTWDelayMinDelay              Integer32,
        unisTwamplightTWDelayAvgJitter             Integer32,
        unisTwamplightTWDelayMaxJitter             Integer32,
        unisTwamplightTWDelayMinJitter             Integer32,
        unisTwamplightTWDelayAvgJitterSD           Integer32,
        unisTwamplightTWDelayMaxJitterSD           Integer32,
        unisTwamplightTWDelayMinJitterSD           Integer32,
        unisTwamplightTWDelayAvgJitterDS           Integer32,
        unisTwamplightTWDelayMaxJitterDS           Integer32,
        unisTwamplightTWDelayMinJitterDS           Integer32
        }

unisTwamplightTWDelaySeq OBJECT-TYPE
    SYNTAX      Gauge32 (1..4294967295)
    MAX-ACCESS  read-only
    STATUS      current
    DESCRIPTION
        "An entry in this table is created when the statistics
        result of a TWAMP test is determined.

        An implementation MUST start assigning
        unisTwamplightTWDelaySeq values at 1 and
        wrap after exceeding the maximum possible value as
        defined by the limit of this object ('ffffffff'h)."
    ::= { unisTwamplightTwoWayDelayEntry 1 }

unisTwamplightTWDelayAvgDelay OBJECT-TYPE
    SYNTAX      Integer32
    MAX-ACCESS  read-only
    STATUS      current
    DESCRIPTION
        "The value of time that records the average two-way-delay
        value in the TWAMP test."
    ::= { unisTwamplightTwoWayDelayEntry 2 }

unisTwamplightTWDelayMaxDelay OBJECT-TYPE
    SYNTAX      Integer32
    MAX-ACCESS  read-only
    STATUS      current
    DESCRIPTION
        "The value of time that records the maximum two-way-delay
        value in the TWAMP test."
    ::= { unisTwamplightTwoWayDelayEntry 3 }

unisTwamplightTWDelayMinDelay OBJECT-TYPE
    SYNTAX      Integer32
    MAX-ACCESS  read-only
    STATUS      current
    DESCRIPTION
        "The value of time that records the minimum two-way-delay
        value in the TWAMP test."
    ::= { unisTwamplightTwoWayDelayEntry 4 }

unisTwamplightTWDelayAvgJitter OBJECT-TYPE
    SYNTAX      Integer32
    MAX-ACCESS  read-only
    STATUS      current
    DESCRIPTION
        "The value of time that records the average jitter value
        in the TWAMP test."
    ::= { unisTwamplightTwoWayDelayEntry 5 }

unisTwamplightTWDelayMaxJitter OBJECT-TYPE
    SYNTAX      Integer32
    MAX-ACCESS  read-only
    STATUS      current
    DESCRIPTION
        "The value of time that records the maximum jitter value
        in the TWAMP test."
    ::= { unisTwamplightTwoWayDelayEntry 6 }

unisTwamplightTWDelayMinJitter OBJECT-TYPE
    SYNTAX      Integer32
    MAX-ACCESS  read-only
    STATUS      current
    DESCRIPTION
        "The value of time that records the minimum jitter value
        in the TWAMP test."
    ::= { unisTwamplightTwoWayDelayEntry 7 }

unisTwamplightTWDelayAvgJitterSD OBJECT-TYPE
    SYNTAX      Integer32
    MAX-ACCESS  read-only
    STATUS      current
    DESCRIPTION
        "The value of time that records the average jitter value from
        source to destination in the TWAMP test."
    ::= { unisTwamplightTwoWayDelayEntry 8 }

unisTwamplightTWDelayMaxJitterSD OBJECT-TYPE
    SYNTAX      Integer32
    MAX-ACCESS  read-only
    STATUS      current
    DESCRIPTION
        "The value of time that records the maximum jitter value from
        source to destination in the TWAMP test."
    ::= { unisTwamplightTwoWayDelayEntry 9 }

unisTwamplightTWDelayMinJitterSD OBJECT-TYPE
    SYNTAX      Integer32
    MAX-ACCESS  read-only
    STATUS      current
    DESCRIPTION
        "The value of time that records the minimum jitter value from
        source to destination in the TWAMP test."
    ::= { unisTwamplightTwoWayDelayEntry 10 }

unisTwamplightTWDelayAvgJitterDS OBJECT-TYPE
    SYNTAX      Integer32
    MAX-ACCESS  read-only
    STATUS      current
    DESCRIPTION
        "The value of time that records the average jitter value from
        destination to source in the TWAMP test."
    ::= { unisTwamplightTwoWayDelayEntry 11 }

unisTwamplightTWDelayMaxJitterDS OBJECT-TYPE
    SYNTAX      Integer32
    MAX-ACCESS  read-only
    STATUS      current
    DESCRIPTION
        "The value of time that records the maximum jitter value from
        destination to source in the TWAMP test."
    ::= { unisTwamplightTwoWayDelayEntry 12 }

unisTwamplightTWDelayMinJitterDS OBJECT-TYPE
    SYNTAX      Integer32
    MAX-ACCESS  read-only
    STATUS      current
    DESCRIPTION
        "The value of time that records the minimum jitter value from
        destination to source in the TWAMP test."
    ::= { unisTwamplightTwoWayDelayEntry 13 }

unisTwamplightTwoWayLossTable OBJECT-TYPE
    SYNTAX      SEQUENCE OF UnisTwamplightTwoWayLossEntry
    MAX-ACCESS  not-accessible
    STATUS      current
    DESCRIPTION
        "Defines the TWAMP-light loss statistics result Table for providing,
        via SNMP."
    ::= { unisTwamplightController 7 }

unisTwamplightTwoWayLossEntry OBJECT-TYPE
    SYNTAX      UnisTwamplightTwoWayLossEntry
    MAX-ACCESS  not-accessible
    STATUS      current
    DESCRIPTION
        "Defines an entry in the unisTwamplightTwoWayLossTable."
    INDEX {
              unisTwamplightControllerID,
              unisTwamplightTWLossSeq
          }
    ::= { unisTwamplightTwoWayLossTable 1 }

UnisTwamplightTwoWayLossEntry ::=
    SEQUENCE {
        unisTwamplightTWLossSeq                     Gauge32,
        unisTwamplightTWLossValue                   Integer32,
        unisTwamplightTWSentCount                   Integer32,
        unisTwamplightTWTotalLossValue              Integer32,
        unisTwamplightTWTotalSentCount              Integer32,
        unisTwamplightTWErrorCount                  Unsigned32,
        unisTwamplightTWTotalErrorCount             Unsigned32
        }

unisTwamplightTWLossSeq OBJECT-TYPE
    SYNTAX      Gauge32 (1..4294967295)
    MAX-ACCESS  read-only
    STATUS      current
    DESCRIPTION
        "An entry in this table is created when statistics
        result of a TWAMP test is determined.

        An implementation MUST start assigning
        unisTwamplightTWLossSeq values at 1 and
        wrap after exceeding the maximum possible value as
        defined by the limit of this object ('ffffffff'h)."
    ::= { unisTwamplightTwoWayLossEntry 1 }

unisTwamplightTWLossValue OBJECT-TYPE
    SYNTAX      Integer32
    MAX-ACCESS  read-only
    STATUS      current
    DESCRIPTION
        "The number of lost packets in a statistical cycle
        of a TWAMP test."
    ::= { unisTwamplightTwoWayLossEntry 2 }

unisTwamplightTWSentCount OBJECT-TYPE
    SYNTAX      Integer32
    MAX-ACCESS  read-only
    STATUS      current
    DESCRIPTION
        "The number of packets were sent in a statistical cycle
        of a TWAMP test."
    ::= { unisTwamplightTwoWayLossEntry 3 }

unisTwamplightTWTotalLossValue OBJECT-TYPE
    SYNTAX      Integer32
    MAX-ACCESS  read-only
    STATUS      current
    DESCRIPTION
        "The number of lost packets number in last 30 statistical
        cycle of a TWAMP test."
    ::= { unisTwamplightTwoWayLossEntry 4 }

unisTwamplightTWTotalSentCount OBJECT-TYPE
    SYNTAX      Integer32
    MAX-ACCESS  read-only
    STATUS      current
    DESCRIPTION
        "The number of packets sent in last 30 statistical
        cycle of a TWAMP test."
    ::= { unisTwamplightTwoWayLossEntry 5 }

unisTwamplightTWErrorCount OBJECT-TYPE
    SYNTAX      Unsigned32
    MAX-ACCESS  read-only
    STATUS      current
    DESCRIPTION
        "The number of error packets received in a statistical cycle
        of a TWAMP-light test."
    ::= { unisTwamplightTwoWayLossEntry 6 }

unisTwamplightTWTotalErrorCount OBJECT-TYPE
    SYNTAX      Unsigned32
    MAX-ACCESS  read-only
    STATUS      current
    DESCRIPTION
        "The number of error packets received in last 30 statistical
        cycles of a TWAMP-light test."
    ::= { unisTwamplightTwoWayLossEntry 7 }


unisTwamplightSenderLossSeqTable OBJECT-TYPE
    SYNTAX      SEQUENCE OF UnisTwamplightSenderLossSeqEntry
    MAX-ACCESS  not-accessible
    STATUS      current
    DESCRIPTION
        "The largest index value in TWAMP Loss results.

        When a TWAMP test starts, TWAMP will generats
        a set of statistics at regular intervals, and the
        index information will be incremented by one for each result."
    ::= { unisTwamplightController 8 }

unisTwamplightSenderLossSeqEntry OBJECT-TYPE
    SYNTAX      UnisTwamplightSenderLossSeqEntry
    MAX-ACCESS  not-accessible
    STATUS      current
    DESCRIPTION
        "Defines an entry in the unisTwamplightSenderLossSeqTable."
    INDEX {
              unisTwamplightControllerID
          }
    ::= { unisTwamplightSenderLossSeqTable 1 }

UnisTwamplightSenderLossSeqEntry ::=
    SEQUENCE {
        unisTwamplightLossSeqNumValue                   Gauge32
        }

unisTwamplightLossSeqNumValue OBJECT-TYPE
    SYNTAX      Gauge32 (1..4294967295)
    MAX-ACCESS  read-only
    STATUS      current
    DESCRIPTION
        "The largest index value in a TWAMP packet Loss test session."
    ::= { unisTwamplightSenderLossSeqEntry 1 }


unisTwamplightSendDelaySeqTable OBJECT-TYPE
    SYNTAX      SEQUENCE OF UnisTwamplightSendDelaySeqEntry
    MAX-ACCESS  not-accessible
    STATUS      current
    DESCRIPTION
        "The largest index value in TWAMP delay results.

        When a TWAMP test startes, TWAMP will generates
        a set of statistics at regular intervals, and the
        index information will be incremented by one for each result."
    ::= { unisTwamplightController 9 }

unisTwamplightSendDelaySeqEntry OBJECT-TYPE
    SYNTAX      UnisTwamplightSendDelaySeqEntry
    MAX-ACCESS  not-accessible
    STATUS      current
    DESCRIPTION
        "Defines an entry in the unisTwamplightSendDelaySeqTable.  The
        operation of this table is same as that of pingResultsTable."
    INDEX {
              unisTwamplightControllerID
          }
    ::= { unisTwamplightSendDelaySeqTable 1 }

UnisTwamplightSendDelaySeqEntry ::=
    SEQUENCE {
        unisTwamplightSenderDelaySeqNum                   Gauge32
        }

unisTwamplightSenderDelaySeqNum OBJECT-TYPE
    SYNTAX      Gauge32 (1..4294967295)
    MAX-ACCESS  read-only
    STATUS      current
    DESCRIPTION
        "The largest index value in a TWAMP packet delay test session."
    ::= { unisTwamplightSendDelaySeqEntry 1 }



unisTwamplightResetStatTable OBJECT-TYPE
    SYNTAX      SEQUENCE OF UnisTwamplightResetStatEntry
    MAX-ACCESS  not-accessible
    STATUS      current
    DESCRIPTION
        "Defines to clear TWAMP test statistics."
    ::= { unisTwamplightController 10 }

unisTwamplightResetStatEntry OBJECT-TYPE
    SYNTAX      UnisTwamplightResetStatEntry
    MAX-ACCESS  not-accessible
    STATUS      current
    DESCRIPTION
        "Defines an entry in the unisTwamplightResetStatTable."
    INDEX {
              unisTwamplightControllerID
          }
    ::= { unisTwamplightResetStatTable 1 }

UnisTwamplightResetStatEntry ::=
    SEQUENCE {
        unisTwamplightResetStatistics                   INTEGER
        }

unisTwamplightResetStatistics OBJECT-TYPE
    SYNTAX      INTEGER {
                          single(1),
                          all(2)
                        }
    MAX-ACCESS  read-create
    STATUS      current
    DESCRIPTION
        "Clear TWAMP test statistics.
          single: reset single.
          all: reset all."
    ::= { unisTwamplightResetStatEntry 1 }


unisTwamplightReactionTable OBJECT-TYPE
    SYNTAX      SEQUENCE OF UnisTwamplightReactionEntry
    MAX-ACCESS  not-accessible
    STATUS      current
    DESCRIPTION
        "Defines TWAMP-light control-client test session reaction
         configuration."
    ::= { unisTwamplightController 11 }

unisTwamplightReactionEntry OBJECT-TYPE
    SYNTAX      UnisTwamplightReactionEntry
    MAX-ACCESS  not-accessible
    STATUS      current
    DESCRIPTION
        "Defines an entry in the unisTwamplightReactionTable."
    INDEX {
              unisTwamplightControllerID,
              unisTwamplightReactItemIndex
          }
    ::= { unisTwamplightReactionTable 1 }

UnisTwamplightReactionEntry ::=
    SEQUENCE {
        unisTwamplightReactItemIndex           Unsigned32,
        unisTwamplightReactCheckElement        INTEGER,
        unisTwamplightReactUpperLimit          Unsigned32,
        unisTwamplightReactLowerLimit          Unsigned32,
        unisTwamplightReactActionType          INTEGER,
        unisTwamplightReactRowStatus           RowStatus
    }

unisTwamplightReactItemIndex OBJECT-TYPE
    SYNTAX      Unsigned32 (1..10)
    MAX-ACCESS  not-accessible
    STATUS      current
    DESCRIPTION
        "The second index of unisTwamplightReactionTable, It definitely
        identifies one of the reaction configurations for TWAMP-light test."
    ::= { unisTwamplightReactionEntry 1 }

unisTwamplightReactCheckElement OBJECT-TYPE
    SYNTAX      INTEGER {
                          twoWayDelay(1),
                          twoWayJitter(2),
                          twoWayLoss(3)
                        }
    MAX-ACCESS  read-create
    STATUS      current
    DESCRIPTION
        "A list of reaction condition type."
    ::= { unisTwamplightReactionEntry 2 }

unisTwamplightReactUpperLimit OBJECT-TYPE
    SYNTAX      Unsigned32 (2..1000000)
    MAX-ACCESS  read-create
    STATUS      current
    DESCRIPTION
        "This object defines an administrative upper-threshold value for
        unisTwamplightReactCheckElement."
    ::= { unisTwamplightReactionEntry 3 }

unisTwamplightReactLowerLimit OBJECT-TYPE
    SYNTAX      Unsigned32 (1..999999)
    MAX-ACCESS  read-create
    STATUS      current
    DESCRIPTION
        "This object defines an administrative lower-threshold value for
        unisTwamplightReactCheckElement."
    ::= { unisTwamplightReactionEntry 4 }

unisTwamplightReactActionType OBJECT-TYPE
    SYNTAX      INTEGER {
                           none(0),
                           trapOnly(1)
                        }
    MAX-ACCESS  read-create
    STATUS      current
    DESCRIPTION
        "Specifies the type of reaction to generate if the specified
         violation type occurs for the monitored element:

        none               - No reaction is generated
        trapOnly           - A trap is generated"
    DEFVAL { none }
    ::= { unisTwamplightReactionEntry 5 }

unisTwamplightReactRowStatus OBJECT-TYPE
    SYNTAX      RowStatus
    MAX-ACCESS  read-create
    STATUS      current
    DESCRIPTION
        "This object allows entries to be created and deleted
        in the unisTwamplightReactionTable.  Deletion of an entry
        in this table results in deletion of all corresponding (same
        unisTwamplightControllerID index values)
        unisTwamplightSenderAdminTable and all related representations
        entries."
    REFERENCE
        "See definition of RowStatus in RFC 2579, 'Textual
        Conventions for SMIv2.'"
    ::= { unisTwamplightReactionEntry 6 }


unisTwamplightResponderEnable OBJECT-TYPE
    SYNTAX      TruthValue
    MAX-ACCESS  read-write
    STATUS      current
    DESCRIPTION
        "Control TWAMP-light responder function.
            true: Enable TWAMP-light responder function.
            false: Disable TWAMP-light responder function."
    DEFVAL      { false }
    ::= { unisTwamplightReponsder 1 }

unisTwamplightResponderTable OBJECT-TYPE
    SYNTAX      SEQUENCE OF UnisTwamplightResponderEntry
    MAX-ACCESS  not-accessible
    STATUS      current
    DESCRIPTION
        "Defines the TWAMP-light reflector Table, and configures
        TWAMP test session.  When the RowStatus is Active or CreatAndGo,
        the source address and target address, source port,
        target  port must be configured.  When the RowStatus
        is Destroy, Except for fields ResponderID and RowStatus,
        The rest can't be configured."
    ::= { unisTwamplightReponsder 2 }

unisTwamplightResponderEntry OBJECT-TYPE
    SYNTAX      UnisTwamplightResponderEntry
    MAX-ACCESS  not-accessible
    STATUS      current
    DESCRIPTION
        "Defines an entry in the unisTwamplightResponderTable."
    INDEX {
              unisTwamplightRespID
          }
    ::= { unisTwamplightResponderTable 1 }

UnisTwamplightResponderEntry ::=
    SEQUENCE {
        unisTwamplightRespID               Integer32,
        unisTwamplightRespSrcAddrType      InetAddressType,
        unisTwamplightRespSrcAddr          InetAddress,
        unisTwamplightRespTrgtAddrType     InetAddressType,
        unisTwamplightRespTrgtAddr         InetAddress,
        unisTwamplightRespSrcPort          Integer32,
        unisTwamplightRespTrgtPort         Integer32,
        unisTwamplightRespVPN              DisplayString,
        unisTwamplightRespDescription      DisplayString,
        unisTwamplightRespRowStatus        RowStatus,
        unisTwamplightRespSrcIfName        DisplayString,
        unisTwamplightRespServiceID        Unsigned32,
        unisTwamplightRespDesMac           MacAddress,
        unisTwamplightRespSrcMac           MacAddress,
        unisTwamplightRespTimeFormat       INTEGER,
        unisTwamplightRespSVlanID          Unsigned32,
        unisTwamplightRespCVlanID          Unsigned32
    }

unisTwamplightRespID OBJECT-TYPE
    SYNTAX      Integer32
    MAX-ACCESS  not-accessible
    STATUS      current
    DESCRIPTION
       "TWAMP test session reflector index."
    ::= { unisTwamplightResponderEntry 1 }

unisTwamplightRespSrcAddrType OBJECT-TYPE
    SYNTAX      InetAddressType
    MAX-ACCESS  read-create
    STATUS      current
    DESCRIPTION
        "Specifies the type of the source address,
        unisTwamplightClientSrcAddr, to be used at a remote host
        when performing the TWAMP-light test."
    ::= { unisTwamplightResponderEntry 2 }

unisTwamplightRespSrcAddr OBJECT-TYPE
    SYNTAX      InetAddress
    MAX-ACCESS  read-create
    STATUS      current
    DESCRIPTION
        "Use the specified IP address (which must be given
        in numeric form, not as a hostname) as the source
        address for outgoing probe packets.  On hosts with
        more than one IP address, this option can be used
        to force the source address to be something other
        than the primary IP address of the interface the
        probe packet is sent on.  A zero length octet string
        value for this object disables source address
        specification.

        The address type (InetAddressType) that relates to
        this object is specified by the corresponding value
        of unisTwamplightClientSrcAddrType."
    DEFVAL { ''H }
    ::= { unisTwamplightResponderEntry 3 }

unisTwamplightRespTrgtAddrType OBJECT-TYPE
    SYNTAX      InetAddressType
    MAX-ACCESS  read-create
    STATUS      current
    DESCRIPTION
        "Specifies the type of host address to be used at a remote
        host for performing a TWAMP-light test."
    ::= { unisTwamplightResponderEntry 4 }

unisTwamplightRespTrgtAddr OBJECT-TYPE
    SYNTAX      InetAddress
    MAX-ACCESS  read-create
    STATUS      current
    DESCRIPTION
        "Specifies the host address to be used at a remote host for
        performing a TWAMP-light test.  The host address type is
        determined by the object value of corresponding
        unisTwamplightClientTrgtAddrType."
    DEFVAL { ''H }
    ::= { unisTwamplightResponderEntry 5 }

unisTwamplightRespSrcPort          OBJECT-TYPE
    SYNTAX      Integer32 (1..65535)
    MAX-ACCESS  read-create
    STATUS      current
    DESCRIPTION
        "The source port be used by a TWAMP-light test."
    ::= { unisTwamplightResponderEntry 6 }

unisTwamplightRespTrgtPort          OBJECT-TYPE
    SYNTAX      Integer32 (1..65535)
    MAX-ACCESS  read-create
    STATUS      current
    DESCRIPTION
        "The destination port to be used by a TWAMP-light test."
    ::= { unisTwamplightResponderEntry 7 }

unisTwamplightRespVPN OBJECT-TYPE
    SYNTAX      DisplayString (SIZE (1..31))
    MAX-ACCESS  read-create
    STATUS      current
    DESCRIPTION
        "VPN name by which the system finds route in the specified VPN
        to send TWAMP probe packets."
    DEFVAL      { "" }
    ::= { unisTwamplightResponderEntry 8 }

unisTwamplightRespDescription OBJECT-TYPE
    SYNTAX      DisplayString (SIZE (1..200))
    MAX-ACCESS  read-create
    STATUS      current
    DESCRIPTION
        "A comment describing this session."
    DEFVAL      { "" }
    ::= { unisTwamplightResponderEntry 9 }

unisTwamplightRespRowStatus OBJECT-TYPE
    SYNTAX      RowStatus
    MAX-ACCESS  read-create
    STATUS      current
    DESCRIPTION
        "This object allows entries to be created and deleted
        in the UnisTwamplightResponderEntry."
    REFERENCE
        "See definition of RowStatus in RFC 2579, 'Textual
        Conventions for SMIv2.'"
    ::= { unisTwamplightResponderEntry 10 }


unisTwamplightRespSrcIfName OBJECT-TYPE
    SYNTAX      DisplayString (SIZE (0..47))
    MAX-ACCESS  read-create
    STATUS      current
    DESCRIPTION
        "The source interface for the response packets."
    DEFVAL      { "" }
    ::= { unisTwamplightResponderEntry 11 }

unisTwamplightRespServiceID OBJECT-TYPE
    SYNTAX      Unsigned32 (1..4096)
    UNITS       "octets"
    MAX-ACCESS  read-create
    STATUS      current
    DESCRIPTION
        "An Ethernet service instance by its ID for test."
    ::= { unisTwamplightResponderEntry 12 }

unisTwamplightRespDesMac OBJECT-TYPE
    SYNTAX      MacAddress
    MAX-ACCESS  read-create
    STATUS      current
    DESCRIPTION
        "The destination MAC address for the TWAMP-light test."
    ::= { unisTwamplightResponderEntry 13 }

unisTwamplightRespSrcMac OBJECT-TYPE
    SYNTAX      MacAddress
    MAX-ACCESS  read-create
    STATUS      current
    DESCRIPTION
        "The source MAC address for the TWAMP-light response message."
    ::= { unisTwamplightResponderEntry 14 }

unisTwamplightRespTimeFormat OBJECT-TYPE
    SYNTAX      INTEGER {
                            auto (0),
                            ntp  (1),
                            ptp  (2)
                        }
    MAX-ACCESS  read-create
    STATUS      current
    DESCRIPTION
        "The timestamp format for probe packets in the TWAMP-light test."
    ::= { unisTwamplightResponderEntry 15 }

unisTwamplightRespSVlanID OBJECT-TYPE
    SYNTAX      Unsigned32 (1..4094)
    MAX-ACCESS  read-create
    STATUS      current
    DESCRIPTION
        "Specify the ID of the VLAN to which the
         probe packets belong."
    ::= { unisTwamplightResponderEntry 16 }

unisTwamplightRespCVlanID OBJECT-TYPE
    SYNTAX      Unsigned32 (1..4094)
    MAX-ACCESS  read-create
    STATUS      current
    DESCRIPTION
        "Specify the ID of the custom vlan to which the
         probe packets belong.
         The unisTwamplightRespSVlanID must be specified
         first before the unisTwamplightRespCVlanID."
    ::= { unisTwamplightResponderEntry 17 }

END
