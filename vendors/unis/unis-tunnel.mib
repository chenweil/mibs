-- =================================================================
-- Copyright (c) 2020 Unisyue Technologies Co., Ltd.  All rights reserved.
--
-- Description: Generic Routing Encapsulation configuration MIB
-- Reference: INET-ADDRESS-MIB, IPV6-FLOW-LABEL-MIB, IF-MIB
-- Version: V1.4
-- History:
-- V1.0 created by Sun Ludong
--   2005-06-04 Initial version
-- V1.1 modified by Zhao Chongri
--   2012-10-23 add table unisTunnelEviTable and unisTunnelEviLinkTable
--      modified by Zhao Wenpeng
--   2013-02-28 add table unisTunnelGreTable
-- V1.2 modified by Yang Chao
--   2013-11-22 added tables unisTunnelVxlanIfTable, unisTunnelVxlanConfigGroup,
--      unisTunnelAvailableIDGroup and unisTunnelTotalNumTable
--      modified by Zhao Chongri
--   2014-4-9 added table unisTunnelNvgreIfTable
-- V1.3 modified by Lei Lei
--   2018-6-13 added table unisTunnelDestinationTable
-- V1.4 modified by Geng Shi Xin
--   2019-04-08 added table unisTunnelGrep2mpStatsTable
-- =================================================================
UNIS-TUNNEL-MIB DEFINITIONS ::= BEGIN

IMPORTS
    unisCommon
        FROM UNIS-OID-MIB
    MODULE-IDENTITY, OBJECT-TYPE, Integer32, Unsigned32, Counter64
        FROM SNMPv2-SMI
    RowStatus, TruthValue, TEXTUAL-CONVENTION
        FROM SNMPv2-TC
    InetAddressType, InetAddress, InetAddressIPv4
        FROM INET-ADDRESS-MIB
    IPv6FlowLabelOrAny
        FROM IPV6-FLOW-LABEL-MIB
    ifIndex, InterfaceIndexOrZero, InterfaceIndex
        FROM IF-MIB;

unisTunnel MODULE-IDENTITY
    LAST-UPDATED
        "201806130000Z"                              -- Jun 13, 2018 at 00:00 GMT
    ORGANIZATION
        "Unisyue Technologies Co., Ltd."
    CONTACT-INFO
        ""
    DESCRIPTION
        "Added unisTunnelDestinationTable."
    REVISION
        "201806130000Z"                              -- Jun 13, 2018 at 00:00 GMT
    DESCRIPTION
        "This MIB contains objects to Manage configuration and Monitor tunnel.
        "
    REVISION
        "201302280000Z"                              -- Feb 28, 2013 at 00:00 GMT
    DESCRIPTION
        "The initial revision of this MIB module.
        "
    ::= { unisCommon 53 }

UnisTunnelType ::= TEXTUAL-CONVENTION
    STATUS current
    DESCRIPTION
        "Tunnel type definition.
        "
    SYNTAX INTEGER {
        other(1),                            -- none of the following
        direct(2),                           -- no intermediate header
        gre(3),                              -- GRE encapsulation
        minimal(4),                          -- Minimal encapsulation
        l2tp(5),                             -- L2TP encapsulation
        pptp(6),                             -- PPTP encapsulation
        l2f(7),                              -- L2F encapsulation
        udp(8),                              -- UDP encapsulation
        atmp(9),                             -- ATMP encapsulation
        msdp(10),                            -- MSDP encapsulation
        sixToFour(11),                       -- 6to4 encapsulation
        sixOverFour(12),                     -- 6over4 encapsulation
        isatap(13),                          -- ISATAP encapsulation
        teredo(14),                          -- Teredo encapsulation
        tunnelModeReserve(35),               -- 15 to 35 are reserved
        tunnelModeIPv4Gre(36),               -- GRE tunnel, IPv4 as transport protocol
        tunnelModeIPv6Gre(37),               -- GRE tunnel, IPv6 as transport protocol
        tunnelModeIPv4IPv4(38),             -- IPv4 over IPv4 tunnel
        tunnelModeIPv4IPv6Config(39),        -- IPv6 over IPv4 manual tunnel
        tunnelModeIPv4IPv6Auto(40),          -- IPv6 over IPv4 auto tunnel
        tunnelModeIPv4IPv66to4(41),          -- IPv6 over IPv4 6to4 tunnel
        tunnelModeIPv4IPv6Isatap(42),        -- IPv6 over IPv4 isatap tunnel
        tunnelModeIPv6IPv4(43),              -- IPv4 over IPv6
        tunnelModeIPv6IPv6(44),              -- IPv6 over IPv6 tunnel
        tunnelModeIPv4UdpDVPN(45),           -- IPv4 DVPN tunnel，UDP method
        tunnelModeIPv4GreDVPN(46),           -- IPv4 DVPN tunnel，GRE method
        tunnelModeIPv6UdpDVPN(47),           -- IPv6 DVPN tunnel，UDP method
        tunnelModeIPv6GreDVPN(48),           -- IPv6 DVPN tunnel，GRE method
        tunnelModeCrLsp(49),                 -- IPv4 CRLSP tunnel
        tunnelModeMax(50),
        tunnelModeIPv4UdpVxlan(51),          -- IPv4 VXLAN tunnel, UDP method
        tunnelModeIPv6UdpVxlan(52),          -- IPv6 VXLAN tunnel, UDP method
        tunnelModeIPv4NVGRE(53),             -- IPv4 NVGRE tunnel
        tunnelModeIPv6NVGRE(54)              -- IPv6 NVGRE tunnel
    }

unisTunnelMIBObjects OBJECT IDENTIFIER ::= { unisTunnel 1 }

unisTunnelTables      OBJECT IDENTIFIER ::= { unisTunnelMIBObjects 1 }

unisTunnelIfTable OBJECT-TYPE
    SYNTAX     SEQUENCE OF UnisTunnelIfEntry
    MAX-ACCESS not-accessible
    STATUS     current
    DESCRIPTION
        "The (conceptual) table containing information on configured tunnels.
        "
    ::= { unisTunnelTables 1 }

unisTunnelIfEntry OBJECT-TYPE
    SYNTAX     UnisTunnelIfEntry
    MAX-ACCESS not-accessible
    STATUS     current
    DESCRIPTION
        "An entry (conceptual row) containing the information on a
        particular configured tunnel.
        "
    INDEX      { ifIndex }
    ::= { unisTunnelIfTable 1 }

UnisTunnelIfEntry ::= SEQUENCE {
    unisTunnelIfEncapsMethod         UnisTunnelType,
    unisTunnelIfHopLimit             Integer32,
    unisTunnelIfSecurity             INTEGER,
    unisTunnelIfTOS                  Integer32,
    unisTunnelIfFlowLabel            IPv6FlowLabelOrAny,
    unisTunnelIfAddressType          InetAddressType,
    unisTunnelIfLocalInetAddress     InetAddress,
    unisTunnelIfRemoteInetAddress    InetAddress,
    unisTunnelIfEncapsLimit          Integer32
}

unisTunnelIfEncapsMethod OBJECT-TYPE
    SYNTAX     UnisTunnelType
    MAX-ACCESS read-write
    STATUS     current
    DESCRIPTION
        "The encapsulation method used by the tunnel.
        "
    ::= { unisTunnelIfEntry 3 }

unisTunnelIfHopLimit OBJECT-TYPE
    SYNTAX     Integer32 (0 | 1..255)
    MAX-ACCESS read-only
    STATUS     current
    DESCRIPTION
        "The IPv4 TTL or IPv6 Hop Limit to use in the outer IP
        header.  A value of 0 indicates that the value is
        copied from the payload's header.
        "
    ::= { unisTunnelIfEntry 4 }

unisTunnelIfSecurity OBJECT-TYPE
    SYNTAX     INTEGER {
        none(1),   -- no security
        ipsec(2),  -- IPsec security
        other(3)
    }
    MAX-ACCESS read-only
    STATUS     current
    DESCRIPTION
        "The method used by the tunnel to secure the outer IP
        header.  The value ipsec indicates that IPsec is used
        between the tunnel endpoints for authentication or
        encryption or both.  More specific security-related
        information may be available in a MIB module for the
        security protocol in use.
        "
    ::= { unisTunnelIfEntry 5 }

unisTunnelIfTOS OBJECT-TYPE
    SYNTAX     Integer32 (-2..63)
    MAX-ACCESS read-only
    STATUS     current
    DESCRIPTION
        "The method used to set the high 6 bits (the
        differentiated services codepoint) of the IPv4 TOS or
        IPv6 Traffic Class in the outer IP header.  A value of
        -1 indicates that the bits are copied from the
        payload's header.  A value of -2 indicates that a
        traffic conditioner is invoked and more information
        may be available in a traffic conditioner MIB module.
        A value between 0 and 63 inclusive indicates that the
        bit field is set to the indicated value.
        "
    ::= { unisTunnelIfEntry 6 }

unisTunnelIfFlowLabel OBJECT-TYPE
    SYNTAX     IPv6FlowLabelOrAny
    MAX-ACCESS read-only
    STATUS     current
    DESCRIPTION
        "The method used to set the IPv6 Flow Label value.
        This object need not be present in rows where
        unisTunnelIfAddressType indicates the tunnel is not over
        IPv6.  A value of -1 indicates that a traffic
        conditioner is invoked and more information may be
        available in a traffic conditioner MIB.  Any other
        value indicates that the Flow Label field is set to
        the indicated value.
        "
    ::= { unisTunnelIfEntry 7 }

unisTunnelIfAddressType OBJECT-TYPE
    SYNTAX     InetAddressType
    MAX-ACCESS read-write
    STATUS     current
    DESCRIPTION
        "The type of address in the corresponding
        unisTunnelIfLocalInetAddress and unisTunnelIfRemoteInetAddress
        objects.
        "
    ::= { unisTunnelIfEntry 8 }

unisTunnelIfLocalInetAddress OBJECT-TYPE
    SYNTAX     InetAddress
    MAX-ACCESS read-write
    STATUS     current
    DESCRIPTION
        "The address of the local endpoint of the tunnel
        (i.e., the source address used in the outer IP
        header).  If the address is unknown, the value is
        0.0.0.0 for IPv4 or :: for IPv6.  The type of this
        object is given by unisTunnelIfAddressType.
        "
    ::= { unisTunnelIfEntry 9 }

unisTunnelIfRemoteInetAddress OBJECT-TYPE
    SYNTAX     InetAddress
    MAX-ACCESS read-write
    STATUS     current
    DESCRIPTION
        "The address of the remote endpoint of the tunnel
        (i.e., the destination address used in the outer IP
        header).  If the address is unknown or the tunnel is
        not a point-to-point link (e.g., if it is a 6to4
        tunnel), the value is 0.0.0.0 for tunnels over IPv4 or
        :: for tunnels over IPv6.  The type of this object is
        given by unisTunnelIfAddressType.
        "
    ::= { unisTunnelIfEntry 10 }

unisTunnelIfEncapsLimit OBJECT-TYPE
    SYNTAX     Integer32 (-1 | 0..255)
    MAX-ACCESS read-only
    STATUS     current
    DESCRIPTION
        "The maximum number of additional encapsulations
        permitted for packets undergoing encapsulation at this
        node.  A value of -1 indicates that no limit is
        present (except as a result of the packet size).
        "
    REFERENCE
        "RFC 2473, section 4.1.1
        "
    ::= { unisTunnelIfEntry 11 }

unisTunnelInetConfigTable OBJECT-TYPE
    SYNTAX     SEQUENCE OF UnisTunnelInetConfigEntry
    MAX-ACCESS not-accessible
    STATUS     current
    DESCRIPTION
        "The (conceptual) table containing information on
        configured tunnels.  This table can be used to map a
        set of tunnel endpoints to the associated ifIndex
        value.  It can also be used for row creation.  Note
        that every row in the unisTunnelIfTable with a fixed
        destination address should have a corresponding row in
        the unisTunnelInetConfigTable, regardless of whether it
        was created via SNMP.
        "
    ::= { unisTunnelTables 3 }

unisTunnelInetConfigEntry OBJECT-TYPE
    SYNTAX     UnisTunnelInetConfigEntry
    MAX-ACCESS not-accessible
    STATUS     current
    DESCRIPTION
        "An entry (conceptual row) containing the information
        on a particular configured tunnel.
        "
    INDEX {
        unisTunnelInetConfigSlot,
        unisTunnelInetConfigSubSlot,
        unisTunnelInetConfigTunnNum
    }
    ::= { unisTunnelInetConfigTable 1 }

UnisTunnelInetConfigEntry ::= SEQUENCE {
    unisTunnelInetConfigSlot                Integer32,
    unisTunnelInetConfigSubSlot             Integer32,
    unisTunnelInetConfigTunnNum             Integer32,
    unisTunnelInetConfigIfIndex             InterfaceIndexOrZero,
    unisTunnelInetConfigStatus              RowStatus
}

unisTunnelInetConfigSlot OBJECT-TYPE
    SYNTAX     Integer32 (0..255)
    MAX-ACCESS not-accessible
    STATUS     current
    DESCRIPTION
        "Slot number.  unisTunnelInetConfigSlot, unisTunnelInetConfigSubSlot
        and unisTunnelInetConfigTunnNum describe a tunnel interface.
        For Example, interface tunnel 0/0/25 would be configured as:
        unisTunnelInetConfigSlot          0
        unisTunnelInetConfigSubSlot       0
        unisTunnelInetConfigTunnNum      25
        "
    ::= { unisTunnelInetConfigEntry 1 }

unisTunnelInetConfigSubSlot OBJECT-TYPE
    SYNTAX     Integer32 (0..255)
    MAX-ACCESS not-accessible
    STATUS     current
    DESCRIPTION
        "Sub slot number.  As described in unisTunnelInetConfigSlot's description.
        "
    ::= { unisTunnelInetConfigEntry 2 }

unisTunnelInetConfigTunnNum OBJECT-TYPE
    SYNTAX     Integer32 (0..65535)
    MAX-ACCESS not-accessible
    STATUS     current
    DESCRIPTION
        "Tunnel number.  As described in unisTunnelInetConfigSlot's description.
        "
    ::= { unisTunnelInetConfigEntry 3 }

unisTunnelInetConfigIfIndex OBJECT-TYPE
    SYNTAX     InterfaceIndexOrZero
    MAX-ACCESS read-only
    STATUS     current
    DESCRIPTION
        "If the value of unisTunnelInetConfigStatus for this row
        is active, then this object contains the value of
        ifIndex corresponding to the tunnel interface.  A
        value of 0 is not legal in the active state, and means
        that the interface index has not yet been assigned.
        "
    ::= { unisTunnelInetConfigEntry 6 }

unisTunnelInetConfigStatus OBJECT-TYPE
    SYNTAX     RowStatus
    MAX-ACCESS read-create
    STATUS     current
    DESCRIPTION
        "The status of this row, by which new entries may be
        created, or old entries deleted from this table.  The
        agent need not support setting this object to
        createAndWait or notInService since there are no other
        writable objects in this table, and writable objects
        in rows of corresponding tables such as the
        unisTunnelIfTable may be modified while this row is
        active.

        To create a row in this table, the management
        station should set unisTunnelInetConfigSlot,
        unisTunnelInetConfigSubSlot, unisTunnelInetConfigTunnNum,
        and set unisTunnelInetConfigStatus to createAndGo.

        Creating a row in this table will cause an interface
        index to be assigned by the agent in an
        implementation-dependent manner, and corresponding
        rows will be instantiated in the ifTable and the
        unisTunnelIfTable.  The status of this row will become
        active as soon as the agent assigns the interface
        index, regardless of whether the interface is
        operationally up.

        Deleting a row in this table will likewise delete the
        corresponding row in the ifTable and in the unisTunnelIfTable.
        "
    ::= { unisTunnelInetConfigEntry 7 }

unisTunnelEviTable OBJECT-TYPE
    SYNTAX     SEQUENCE OF UnisTunnelEviEntry
    MAX-ACCESS not-accessible
    STATUS     current
    DESCRIPTION
        "The (conceptual) table containing information on configured EVI-Tunnel.
        "
    ::= { unisTunnelTables 4 }

unisTunnelEviEntry OBJECT-TYPE
    SYNTAX     UnisTunnelEviEntry
    MAX-ACCESS not-accessible
    STATUS     current
    DESCRIPTION
        "An entry (conceptual row) containing the information on a
        particular configured EVI-Tunnel.
        "
    INDEX      { unisTunnelEviTunnNum }
    ::= { unisTunnelEviTable 1 }

UnisTunnelEviEntry ::= SEQUENCE {
    unisTunnelEviTunnNum              Integer32,
    unisTunnelEviIfIndex              InterfaceIndex,
    unisTunnelEviStatus               RowStatus,
    unisTunnelEviAddressType          InetAddressType,
    unisTunnelEviLocalAddr            InetAddress,
    unisTunnelEviNetworkID            Integer32,
    unisTunnelEviKeepaliveInterval    Integer32,
    unisTunnelEviKeepaliveTimes       Integer32
}

unisTunnelEviTunnNum OBJECT-TYPE
    SYNTAX     Integer32 (1..2147483647)
    MAX-ACCESS not-accessible
    STATUS     current
    DESCRIPTION
        "Tunnel number.  An identifier used to distinguish
         between multiple tunnels.
        "
    ::= { unisTunnelEviEntry 1 }

unisTunnelEviIfIndex OBJECT-TYPE
    SYNTAX     InterfaceIndex
    MAX-ACCESS read-only
    STATUS     current
    DESCRIPTION
        "A unique value, greater than zero, for each
         interface.  It is recommended that values are assigned
         contiguously starting from 1.  The value for each
         interface sub-layer must remain constant at least from
         one re-initialization of the entity's network
         management system to the next re-initialization.
        "
    ::= { unisTunnelEviEntry 2 }

unisTunnelEviStatus OBJECT-TYPE
    SYNTAX     RowStatus
    MAX-ACCESS read-create
    STATUS     current
    DESCRIPTION
        "The status of this row, by which new entries may be
        created, or old entries deleted from this table.  The
        agent need not support setting this object to
        createAndWait or notInService since there are no other
        writable objects in this table, and writable objects
        in rows of corresponding tables such as the
        unisTunnelEviTable may be modified while this row is
        active.

        Creating a row in this table will cause an interface
        index to be assigned by the agent in an
        implementation-dependent manner, and corresponding
        rows will be instantiated in the ifTable.
        The status of this row will become
        active as soon as the agent assigns the interface
        index, regardless of whether the interface is
        operationally up.

        Deleting a row in this table will likewise delete the
        corresponding row in the ifTable.
        "
    ::= { unisTunnelEviEntry 3 }

unisTunnelEviAddressType OBJECT-TYPE
    SYNTAX     InetAddressType
    MAX-ACCESS read-create
    STATUS     current
    DESCRIPTION
        "The type of address in the corresponding
         unisTunnelEviLocalAddr objects.
         Can not be modified after creation.
        "
    ::= { unisTunnelEviEntry 4 }

unisTunnelEviLocalAddr OBJECT-TYPE
    SYNTAX     InetAddress
    MAX-ACCESS read-create
    STATUS     current
    DESCRIPTION
        "The address of the local endpoint of the tunnel
        (i.e., the source address used in the outer IP
        header).  The type of this object is given by
        unisTunnelEviAddressType.
        "
    ::= { unisTunnelEviEntry 5 }

unisTunnelEviNetworkID OBJECT-TYPE
    SYNTAX     Integer32 (0..16777215)
    MAX-ACCESS read-create
    STATUS     current
    DESCRIPTION
        "The method used to assign a network ID to an EVI-Tunnel interface.
         Assign the same network ID to the EVI-Tunnel interfaces of
         all edge devices in an EVI network.  A value of 0 indicates that
         no network ID is assigned to any EVI-Tunnel interface.
        "
    ::= { unisTunnelEviEntry 6 }

unisTunnelEviKeepaliveInterval OBJECT-TYPE
    SYNTAX     Integer32 (1..32767)
    MAX-ACCESS read-create
    STATUS     current
    DESCRIPTION
        "The method used to assign the keepalive interval.
        "
    ::= { unisTunnelEviEntry 7 }

unisTunnelEviKeepaliveTimes OBJECT-TYPE
    SYNTAX     Integer32 (1..255)
    MAX-ACCESS read-create
    STATUS     current
    DESCRIPTION
        "The method used to assign the keepalive maximum number
         of consecutive keepalive failures that are allowed.
        "
    ::= { unisTunnelEviEntry 8 }

unisTunnelEviLinkTable OBJECT-TYPE
    SYNTAX     SEQUENCE OF UnisTunnelEviLinkEntry
    MAX-ACCESS not-accessible
    STATUS     current
    DESCRIPTION
        "The (conceptual) table containing information on configured EVI-Link.
        "
    ::= { unisTunnelTables 5 }

unisTunnelEviLinkEntry OBJECT-TYPE
    SYNTAX     UnisTunnelEviLinkEntry
    MAX-ACCESS not-accessible
    STATUS     current
    DESCRIPTION
        "An entry (conceptual row) containing the information on a
        particular configured EVI-Link.
        "
    INDEX      { unisTunnelEviTunnNum, unisTunnelEviLinkNum }
    ::= { unisTunnelEviLinkTable 1 }

UnisTunnelEviLinkEntry ::= SEQUENCE {
    unisTunnelEviLinkNum                Integer32,
    unisTunnelEviLinkIfIndex            InterfaceIndex,
    unisTunnelEviLinkAddressType        InetAddressType,
    unisTunnelEviLinkRemoteAddr         InetAddress
}

unisTunnelEviLinkNum OBJECT-TYPE
    SYNTAX     Integer32 (1..2147483647)
    MAX-ACCESS not-accessible
    STATUS     current
    DESCRIPTION
        "EVI-Link number.
        "
    ::= { unisTunnelEviLinkEntry 1 }

unisTunnelEviLinkIfIndex OBJECT-TYPE
    SYNTAX     InterfaceIndex
    MAX-ACCESS read-only
    STATUS     current
    DESCRIPTION
        "A unique value, greater than zero, for each
         interface.  It is recommended that values are assigned
         contiguously starting from 1.  The value for each
         interface sub-layer must remain constant at least from
         one re-initialization of the entity's network
         management system to the next re-initialization.
        "
    ::= { unisTunnelEviLinkEntry 2 }

    unisTunnelEviLinkAddressType OBJECT-TYPE
    SYNTAX     InetAddressType
    MAX-ACCESS read-only
    STATUS     current
    DESCRIPTION
        "The type of address in the corresponding
         unisTunnelEviLinkRemoteAddr objects.
         Can not be modified after creation.
        "
    ::= { unisTunnelEviLinkEntry 3 }

unisTunnelEviLinkRemoteAddr OBJECT-TYPE
    SYNTAX     InetAddress
    MAX-ACCESS read-only
    STATUS     current
    DESCRIPTION
        "The address of the remote endpoint of the tunnel
        (i.e., the destination address used in the outer IP
        header).
        "
    ::= { unisTunnelEviLinkEntry 4}

unisTunnelGreTable OBJECT-TYPE
    SYNTAX     SEQUENCE OF UnisTunnelGreEntry
    MAX-ACCESS not-accessible
    STATUS     current
    DESCRIPTION
        "The (conceptual) table containing information on configured Gre-Tunnel.
        "
    ::= { unisTunnelTables 6 }

unisTunnelGreEntry OBJECT-TYPE
    SYNTAX     UnisTunnelGreEntry
    MAX-ACCESS not-accessible
    STATUS     current
    DESCRIPTION
        "An entry (conceptual row) containing the information on a
        particular configured Gre-Tunnel.
        "
    INDEX      { unisTunnelGreTunnNum }
    ::= { unisTunnelGreTable 1 }

UnisTunnelGreEntry ::= SEQUENCE {
    unisTunnelGreTunnNum                  Integer32,
    unisTunnelGreTunnIfIndex              InterfaceIndex,
    unisTunnelGreAddressType              InetAddressType,
    unisTunnelGreLocalAddr                InetAddress,
    unisTunnelGreRemoteAddr               InetAddress,
    unisTunnelGreKeepaliveEnabled         TruthValue,
    unisTunnelGreKeepaliveInterval        Integer32,
    unisTunnelGreKeepaliveTimes           Integer32,
    unisTunnelGreSlbgGroupNum             Unsigned32,
    unisTunnelGreTunnStatus               RowStatus
}

unisTunnelGreTunnNum OBJECT-TYPE
    SYNTAX     Integer32 (1..2147483647)
    MAX-ACCESS not-accessible
    STATUS     current
    DESCRIPTION
        "Tunnel number.  An identifier used to distinguish
         between multiple tunnels.
        "
    ::= { unisTunnelGreEntry 1 }

unisTunnelGreTunnIfIndex OBJECT-TYPE
    SYNTAX     InterfaceIndex
    MAX-ACCESS read-only
    STATUS     current
    DESCRIPTION
        "A unique value, greater than zero, for each
         interface.  It is recommended that values are assigned
         contiguously starting from 1.  The value for each
         interface sub-layer must remain constant at least from
         one re-initialization of the entity's network
         management system to the next re-initialization.
        "
    ::= { unisTunnelGreEntry 2 }

unisTunnelGreAddressType OBJECT-TYPE
    SYNTAX     InetAddressType
    MAX-ACCESS read-create
    STATUS     current
    DESCRIPTION
        "The type of address in the corresponding
         unisTunnelGreLocalAddr and unisTunnelGreRemoteAddr objects.
        "
    ::= { unisTunnelGreEntry 3 }

unisTunnelGreLocalAddr OBJECT-TYPE
    SYNTAX     InetAddress
    MAX-ACCESS read-create
    STATUS     current
    DESCRIPTION
        "The address of the local endpoint of the tunnel
         (i.e., the source address used in the outer IP
         header).
        "
    ::= { unisTunnelGreEntry 4 }

unisTunnelGreRemoteAddr OBJECT-TYPE
    SYNTAX     InetAddress
    MAX-ACCESS read-create
    STATUS     current
    DESCRIPTION
        "The address of the remote endpoint of the tunnel
         (i.e., the destination address used in the outer IP
         header).
        "
    ::= { unisTunnelGreEntry 5 }

unisTunnelGreKeepaliveEnabled OBJECT-TYPE
    SYNTAX      TruthValue
    MAX-ACCESS  read-create
    STATUS      current
    DESCRIPTION
        "This MIB object specifies whether or not keepalive is used.
         A value of true indicates that keepalive SHOULD be used.
         When keepalive is not be used, the value of
         unisTunnelGreKeepaliveInterval and unisTunnelGreKeepaliveTimes
         MUST be zero.
        "
    DEFVAL { false }
    ::= { unisTunnelGreEntry 6 }

unisTunnelGreKeepaliveInterval OBJECT-TYPE
    SYNTAX     Integer32 (0..32767)
    MAX-ACCESS read-create
    STATUS     current
    DESCRIPTION
        "The method used to assign the keepalive interval.
         The value is zero when keepalive is not used.
         The valid value is from 1 to 32767, when keepalive is used.
        "
    DEFVAL { 0 }
    ::= { unisTunnelGreEntry 7 }

unisTunnelGreKeepaliveTimes OBJECT-TYPE
    SYNTAX     Integer32 (0..255)
    MAX-ACCESS read-create
    STATUS     current
    DESCRIPTION
        "The method used to assign the keepalive maximum number
         of consecutive keepalive failures that are allowed.
         The value is zero when keepalive is not used.
         The valid value is from 1 to 255, when keepalive is used.
        "
    DEFVAL { 0 }
    ::= { unisTunnelGreEntry 8 }

unisTunnelGreSlbgGroupNum OBJECT-TYPE
    SYNTAX     Unsigned32 (0..4294967295)
    MAX-ACCESS read-create
    STATUS     current
    DESCRIPTION
        "The method used to assign the service-loopback-group.
        "
    ::= { unisTunnelGreEntry 9 }

unisTunnelGreTunnStatus OBJECT-TYPE
    SYNTAX     RowStatus
    MAX-ACCESS read-create
    STATUS     current
    DESCRIPTION
        "The status of this row, by which new entries may be
         created, or old entries deleted from this table.  The
         agent need not support setting this object to
         createAndWait or notInService since there are no other
         writable objects in this table, and writable objects
         in rows of corresponding tables such as the
         unisTunnelGreTable may be modified while this row is
         active.

         Creating a row in this table will cause an interface
         index to be assigned by the agent in an
         implementation-dependent manner, and corresponding
         rows will be instantiated in the ifTable.
         The status of this row will become
         active as soon as the agent assigns the interface
         index, regardless of whether the interface is
         operationally up.

         Deleting a row in this table will likewise delete the
         corresponding row in the ifTable.
        "
    ::= { unisTunnelGreEntry 10 }

unisTunnelVxlanIfTable OBJECT-TYPE
    SYNTAX     SEQUENCE OF UnisTunnelVxlanIfEntry
    MAX-ACCESS not-accessible
    STATUS     current
    DESCRIPTION
        "The (conceptual) table containing information on configured Vxlan-Tunnel.
        "
    ::= { unisTunnelTables 7 }

unisTunnelVxlanIfEntry OBJECT-TYPE
    SYNTAX     UnisTunnelVxlanIfEntry
    MAX-ACCESS not-accessible
    STATUS     current
    DESCRIPTION
        "An entry (conceptual row) containing the information on a
        particular configured Vxlan-Tunnel.
        "
    INDEX      { unisTunnelVxlanIfTunnNum }
    ::= { unisTunnelVxlanIfTable 1 }

UnisTunnelVxlanIfEntry ::= SEQUENCE {
    unisTunnelVxlanIfTunnNum              Integer32,
    unisTunnelVxlanTunnIfIndex            InterfaceIndex,
    unisTunnelVxlanIfAddressType          InetAddressType,
    unisTunnelVxlanIfLocalAddr            InetAddress,
    unisTunnelVxlanIfRemoteAddr           InetAddress,
    unisTunnelVxlanIfStatus               RowStatus
}

unisTunnelVxlanIfTunnNum OBJECT-TYPE
    SYNTAX     Integer32 (1..2147483647)
    MAX-ACCESS not-accessible
    STATUS     current
    DESCRIPTION
        "Tunnel number.  An identifier used to distinguish
         between multiple tunnels.
        "
    ::= { unisTunnelVxlanIfEntry 1 }

unisTunnelVxlanTunnIfIndex OBJECT-TYPE
    SYNTAX     InterfaceIndex
    MAX-ACCESS read-only
    STATUS     current
    DESCRIPTION
        "A unique value, greater than zero, for each
         interface.  It is recommended that values are assigned
         contiguously starting from 1.  The value for each
         interface sub-layer must remain constant at least from
         one re-initialization of the entity's network
         management system to the next re-initialization.
        "
    ::= { unisTunnelVxlanIfEntry 2 }

unisTunnelVxlanIfAddressType OBJECT-TYPE
    SYNTAX     InetAddressType
    MAX-ACCESS read-create
    STATUS     current
    DESCRIPTION
        "The type of address in the corresponding
         unisTunnelVxlanIfLocalAddr and unisTunnelVxlanIfRemoteAddr objects.
        "
    ::= { unisTunnelVxlanIfEntry 3 }

unisTunnelVxlanIfLocalAddr OBJECT-TYPE
    SYNTAX     InetAddress
    MAX-ACCESS read-create
    STATUS     current
    DESCRIPTION
        "The address of the local endpoint of the tunnel
         (i.e., the source address used in the outer IP
         header).
        "
    ::= { unisTunnelVxlanIfEntry 4 }

unisTunnelVxlanIfRemoteAddr OBJECT-TYPE
    SYNTAX     InetAddress
    MAX-ACCESS read-create
    STATUS     current
    DESCRIPTION
        "The address of the remote endpoint of the tunnel
         (i.e., the destination address used in the outer IP
         header).
        "
    ::= { unisTunnelVxlanIfEntry 5 }

unisTunnelVxlanIfStatus OBJECT-TYPE
    SYNTAX     RowStatus
    MAX-ACCESS read-create
    STATUS     current
    DESCRIPTION
        "The status of this row, by which new entries may be
         created, or old entries deleted from this table.  The
         agent need not support setting this object to
         createAndWait or notInService since there are no other
         writable objects in this table, and writable objects
         in rows of corresponding tables such as the
         unisTunnelVxlanIfTable may be modified while this row is
         active.

         Creating a row in this table will cause an interface
         index to be assigned by the agent in an
         implementation-dependent manner, and corresponding
         rows will be instantiated in the ifTable.
         The status of this row will become
         active as soon as the agent assigns the interface
         index, regardless of whether the interface is
         operationally up.

         Deleting a row in this table will likewise delete the
         corresponding row in the ifTable.
        "
    ::= { unisTunnelVxlanIfEntry 6 }

unisTunnelVxlanConfigGroup OBJECT IDENTIFIER ::= { unisTunnelTables 8 }

unisTunnelVxlanUdpPort OBJECT-TYPE
    SYNTAX Integer32 (1..65535)
    MAX-ACCESS read-write
    STATUS current
    DESCRIPTION
        "The UDP port number for Vxlan Tunnels."
    ::= { unisTunnelVxlanConfigGroup 1 }

unisTunnelVxlanDropWrongCksmPkt OBJECT-TYPE
    SYNTAX TruthValue
    MAX-ACCESS read-write
    STATUS current
    DESCRIPTION
        "Whether or not dropping invalid UDP chesksum Vxlan packet."
    ::= { unisTunnelVxlanConfigGroup 2 }

unisTunnelVxlanDropVlanTagPkt OBJECT-TYPE
    SYNTAX TruthValue
    MAX-ACCESS read-write
    STATUS current
    DESCRIPTION
        "Whether or not dropping Vxlan packet with inner VLAN tag."
    ::= { unisTunnelVxlanConfigGroup 3 }

unisTunnelAvailableIDGroup OBJECT IDENTIFIER ::= { unisTunnelTables 9 }

unisTunnelAvailableID OBJECT-TYPE
    SYNTAX Integer32 (-1 | 1..2147483647)
    MAX-ACCESS read-only
    STATUS current
    DESCRIPTION
        "The available tunnel ID.  A value of -1 indicates that
         there is no available tunnel ID."
    ::= { unisTunnelAvailableIDGroup 1 }

unisTunnelTotalNumTable OBJECT-TYPE
    SYNTAX     SEQUENCE OF UnisTunnelTotalNumEntry
    MAX-ACCESS not-accessible
    STATUS     current
    DESCRIPTION
        "Total number of a particular method tunnel."
    ::= { unisTunnelTables 10 }

unisTunnelTotalNumEntry OBJECT-TYPE
    SYNTAX     UnisTunnelTotalNumEntry
    MAX-ACCESS not-accessible
    STATUS     current
    DESCRIPTION
        "Total number of a particular method tunnel."
    INDEX      { unisTunnelEncapsMethod }
    ::= { unisTunnelTotalNumTable 1 }

UnisTunnelTotalNumEntry ::= SEQUENCE {
    unisTunnelEncapsMethod              UnisTunnelType,
    unisTunnelTotalNum                  Unsigned32
}

unisTunnelEncapsMethod OBJECT-TYPE
    SYNTAX     UnisTunnelType
    MAX-ACCESS not-accessible
    STATUS     current
    DESCRIPTION
        "The encapsulation method used by the tunnel."
    ::= { unisTunnelTotalNumEntry 1 }

unisTunnelTotalNum OBJECT-TYPE
    SYNTAX     Unsigned32
    MAX-ACCESS read-only
    STATUS     current
    DESCRIPTION
        "Total number of a particular method tunnel.
        "
    ::= { unisTunnelTotalNumEntry 2 }

unisTunnelNvgreIfTable OBJECT-TYPE
    SYNTAX     SEQUENCE OF UnisTunnelNvgreIfEntry
    MAX-ACCESS not-accessible
    STATUS     current
    DESCRIPTION
        "The (conceptual) table containing information on configured Nvgre-Tunnel.
        "
    ::= { unisTunnelTables 11 }

unisTunnelNvgreIfEntry OBJECT-TYPE
    SYNTAX     UnisTunnelNvgreIfEntry
    MAX-ACCESS not-accessible
    STATUS     current
    DESCRIPTION
        "An entry (conceptual row) containing the information on a
        particular configured Nvgre-Tunnel.
        "
    INDEX      { unisTunnelNvgreIfTunnNum }
    ::= { unisTunnelNvgreIfTable 1 }

UnisTunnelNvgreIfEntry ::= SEQUENCE {
    unisTunnelNvgreIfTunnNum              Integer32,
    unisTunnelNvgreTunnIfIndex            InterfaceIndex,
    unisTunnelNvgreIfAddressType          InetAddressType,
    unisTunnelNvgreIfLocalAddr            InetAddress,
    unisTunnelNvgreIfRemoteAddr           InetAddress,
    unisTunnelNvgreIfStatus               RowStatus
}

unisTunnelNvgreIfTunnNum OBJECT-TYPE
    SYNTAX     Integer32 (1..2147483647)
    MAX-ACCESS not-accessible
    STATUS     current
    DESCRIPTION
        "Tunnel number.  An identifier used to distinguish
         between multiple tunnels.
        "
    ::= { unisTunnelNvgreIfEntry 1 }

unisTunnelNvgreTunnIfIndex OBJECT-TYPE
    SYNTAX     InterfaceIndex
    MAX-ACCESS read-only
    STATUS     current
    DESCRIPTION
        "A unique value, greater than zero, for each
         interface.  It is recommended that values are assigned
         contiguously starting from 1.  The value for each
         interface sub-layer must remain constant at least from
         one re-initialization of the entity's network
         management system to the next re-initialization.
        "
    ::= { unisTunnelNvgreIfEntry 2 }

unisTunnelNvgreIfAddressType OBJECT-TYPE
    SYNTAX     InetAddressType
    MAX-ACCESS read-create
    STATUS     current
    DESCRIPTION
        "The type of address in the corresponding
         unisTunnelNvgreIfLocalAddr and unisTunnelNvgreIfRemoteAddr objects.
        "
    ::= { unisTunnelNvgreIfEntry 3 }

unisTunnelNvgreIfLocalAddr OBJECT-TYPE
    SYNTAX     InetAddress
    MAX-ACCESS read-create
    STATUS     current
    DESCRIPTION
        "The address of the local endpoint of the tunnel
         (i.e., the source address used in the outer IP
         header).
        "
    ::= { unisTunnelNvgreIfEntry 4 }

unisTunnelNvgreIfRemoteAddr OBJECT-TYPE
    SYNTAX     InetAddress
    MAX-ACCESS read-create
    STATUS     current
    DESCRIPTION
        "The address of the remote endpoint of the tunnel
         (i.e., the destination address used in the outer IP
         header).
        "
    ::= { unisTunnelNvgreIfEntry 5 }

unisTunnelNvgreIfStatus OBJECT-TYPE
    SYNTAX     RowStatus
    MAX-ACCESS read-create
    STATUS     current
    DESCRIPTION
        "The status of this row, by which new entries may be
         created, or old entries deleted from this table.  The
         agent need not support setting this object to
         createAndWait or notInService since there are no other
         writable objects in this table, and writable objects
         in rows of corresponding tables such as the
         unisTunnelNvgreIfTable may be modified while this row is
         active.

         Creating a row in this table will cause an interface
         index to be assigned by the agent in an
         implementation-dependent manner, and corresponding
         rows will be instantiated in the ifTable.
         The status of this row will become
         active as soon as the agent assigns the interface
         index, regardless of whether the interface is
         operationally up.

         Deleting a row in this table will likewise delete the
         corresponding row in the ifTable.
        "
    ::= { unisTunnelNvgreIfEntry 6 }

unisTunnelDestinationTable OBJECT-TYPE
    SYNTAX     SEQUENCE OF UnisTunnelDestinationEntry
    MAX-ACCESS not-accessible
    STATUS     current
    DESCRIPTION
       "The (conceptual) table containing information on tunnels.
       "
    ::= { unisTunnelTables 12 }

unisTunnelDestinationEntry OBJECT-TYPE
    SYNTAX     UnisTunnelDestinationEntry
    MAX-ACCESS not-accessible
    STATUS     current
    DESCRIPTION
        "An entry (conceptual row) containing the information on a
         particular tunnel.
        "
    INDEX      { unisTunnelDestinationDstAddr,
               unisTunnelDestinationDstType,
         unisTunnelDestinationTunNum}
    ::= { unisTunnelDestinationTable 1 }

UnisTunnelDestinationEntry ::= SEQUENCE {
    unisTunnelDestinationDstAddr           InetAddress,
    unisTunnelDestinationDstType           InetAddressType,
    unisTunnelDestinationTunNum            Integer32,
    unisTunnelDestinationTunIfindex        InterfaceIndex
}

unisTunnelDestinationDstAddr OBJECT-TYPE
    SYNTAX     InetAddress
    MAX-ACCESS not-accessible
    STATUS     current
    DESCRIPTION
        "Destination address of a tunnel.
        "
    ::= { unisTunnelDestinationEntry 1 }

unisTunnelDestinationDstType OBJECT-TYPE
    SYNTAX     InetAddressType
    MAX-ACCESS not-accessible
    STATUS     current
    DESCRIPTION
        "Type of the destination address.
        "
    ::= { unisTunnelDestinationEntry 2 }

unisTunnelDestinationTunNum OBJECT-TYPE
    SYNTAX     Integer32 (0..65535)
    MAX-ACCESS not-accessible
    STATUS     current
    DESCRIPTION
        "Tunnel number, an identifier used to distinguish
         between multiple tunnels.
        "
    ::= { unisTunnelDestinationEntry 3 }

unisTunnelDestinationTunIfindex OBJECT-TYPE
    SYNTAX     InterfaceIndex
    MAX-ACCESS read-only
    STATUS     current
    DESCRIPTION
        "A unique value greater than zero, for each interface.
        "
    ::= { unisTunnelDestinationEntry 4 }


unisTunnelGrep2mpStatsTable OBJECT-TYPE
    SYNTAX     SEQUENCE OF UnisTunnelGrep2mpStatsEntry
    MAX-ACCESS not-accessible
    STATUS     current
    DESCRIPTION
        "The table contains GRE P2MP tunnel mapping statistics."
    ::= { unisTunnelTables 13 }

unisTunnelGrep2mpStatsEntry OBJECT-TYPE
    SYNTAX     UnisTunnelGrep2mpStatsEntry
    MAX-ACCESS not-accessible
    STATUS     current
    DESCRIPTION
           "GRE P2MP tunnel mapping statistics entry."
    INDEX { unisTunnelGrep2mpStatsTunnelNo,
            unisTunnelGrep2mpStatsVrf,
            unisTunnelGrep2mpStatsVPCID,
            unisTunnelGrep2mpStatsBraAddr,
            unisTunnelGrep2mpStatsBraMask,
            unisTunnelGrep2mpStatsAddrType,
            unisTunnelGrep2mpStatsDestAddr}
    ::= { unisTunnelGrep2mpStatsTable 1 }

UnisTunnelGrep2mpStatsEntry ::= SEQUENCE {
        unisTunnelGrep2mpStatsTunnelNo              Integer32,
        unisTunnelGrep2mpStatsVrf                   Integer32,
        unisTunnelGrep2mpStatsVPCID                 Integer32,
        unisTunnelGrep2mpStatsBraAddr               InetAddress,
        unisTunnelGrep2mpStatsBraMask               InetAddress,
        unisTunnelGrep2mpStatsAddrType              InetAddressType,
        unisTunnelGrep2mpStatsDestAddr              InetAddressIPv4,
        unisTunnelGrep2mpStatsInPkts                Counter64,
        unisTunnelGrep2mpStatsInOctets              Counter64,
        unisTunnelGrep2mpStatsInDis                 Counter64,
        unisTunnelGrep2mpStatsOutPkts               Counter64,
        unisTunnelGrep2mpStatsOutOctets             Counter64,
        unisTunnelGrep2mpStatsOutDis                Counter64

    }
unisTunnelGrep2mpStatsTunnelNo OBJECT-TYPE
    SYNTAX     Integer32
    MAX-ACCESS not-accessible
    STATUS     current
    DESCRIPTION
           "Tunnel interfacenumber."
    ::= { unisTunnelGrep2mpStatsEntry 1 }


unisTunnelGrep2mpStatsVrf OBJECT-TYPE
    SYNTAX     Integer32
    MAX-ACCESS not-accessible
    STATUS     current
    DESCRIPTION
           "VPN instance index."
    ::= { unisTunnelGrep2mpStatsEntry 2 }

unisTunnelGrep2mpStatsVPCID OBJECT-TYPE
    SYNTAX     Integer32
    MAX-ACCESS not-accessible
    STATUS     current
    DESCRIPTION
           "VPC ID."
    ::= { unisTunnelGrep2mpStatsEntry 3 }


unisTunnelGrep2mpStatsBraAddr OBJECT-TYPE
    SYNTAX     InetAddress
    MAX-ACCESS not-accessible
    STATUS     current
    DESCRIPTION
           "Branch network IP address."
    ::= { unisTunnelGrep2mpStatsEntry 4 }

unisTunnelGrep2mpStatsBraMask OBJECT-TYPE
    SYNTAX     InetAddress
    MAX-ACCESS not-accessible
    STATUS     current
    DESCRIPTION
           "Branch network mask."
    ::= { unisTunnelGrep2mpStatsEntry 5 }

unisTunnelGrep2mpStatsAddrType OBJECT-TYPE
    SYNTAX     InetAddressType
    MAX-ACCESS not-accessible
    STATUS     current
    DESCRIPTION
        "Type of address in the corresponding
        unisTunnelGrep2mpStatsBraAddr and unisTunnelGrep2mpStatsBraMask
        objects.
        "
    ::= { unisTunnelGrep2mpStatsEntry 6 }

unisTunnelGrep2mpStatsDestAddr OBJECT-TYPE
    SYNTAX     InetAddressIPv4
    MAX-ACCESS not-accessible
    STATUS     current
    DESCRIPTION
           "Tunnel destination address."
    ::= { unisTunnelGrep2mpStatsEntry 7 }



unisTunnelGrep2mpStatsInPkts OBJECT-TYPE
    SYNTAX     Counter64
    MAX-ACCESS read-only
    STATUS     current
    DESCRIPTION
           "Total number of IP datagrams received."
    ::= { unisTunnelGrep2mpStatsEntry 8 }

unisTunnelGrep2mpStatsInOctets OBJECT-TYPE
    SYNTAX     Counter64
    MAX-ACCESS read-only
    STATUS     current
    DESCRIPTION
           "Total number of octets received in IP datagrams."
    ::= { unisTunnelGrep2mpStatsEntry 9 }

unisTunnelGrep2mpStatsInDis OBJECT-TYPE
    SYNTAX     Counter64
    MAX-ACCESS read-only
    STATUS     current
    DESCRIPTION
           "The number of input IP datagrams for which no problems were
            encountered to prevent their continued processing, but
            were discarded."
    ::= { unisTunnelGrep2mpStatsEntry 10 }

unisTunnelGrep2mpStatsOutPkts OBJECT-TYPE
    SYNTAX     Counter64
    MAX-ACCESS read-only
    STATUS     current
    DESCRIPTION
           "Total number IP datagrams sent."
    ::= { unisTunnelGrep2mpStatsEntry 11 }

unisTunnelGrep2mpStatsOutOctets OBJECT-TYPE
    SYNTAX     Counter64
    MAX-ACCESS read-only
    STATUS     current
    DESCRIPTION
           "Total number of octets in IP datagrams sent."
    ::= { unisTunnelGrep2mpStatsEntry 12 }

unisTunnelGrep2mpStatsOutDis OBJECT-TYPE
    SYNTAX     Counter64
    MAX-ACCESS read-only
    STATUS     current
    DESCRIPTION
           "The number of output IP datagrams which no problem was
            encountered to prevent their transmission to their
            destination, but were discarded ."
    ::= { unisTunnelGrep2mpStatsEntry 13 }


END
