-- =========================================================================
-- Copyright (c) 2020 Unisyue Technologies Co., Ltd.  All rights reserved.
--
-- Description: This MIB file is used for management of unis Class Based
--             QoS information.
-- Reference:
-- Version: V2.4
-- History:
-- V1.0 created by tangshun.
-- V1.1 2006/01/17 modified by wangjinwang
--   add enum value 22 and 23 in MatchRuleType
--   add comment for unisCBQoSMatchRuleIntValue1
-- V1.2 2006/02/24 modified by changhuifeng
--   Add an enumeration Bittorrent(24) to object unisCBQoSMatchRuleType.
--   Add unisCBQoSMirrorCfgInfoTable for flow mirror.
--   Add unisCBQoSRedirectIpv6Interface1 and unisCBQoSRedirectIpv6Interface2
--   object for unisCBQoSRedirectCfgInfoTable.
--   Modify the value range of unisCBQoSRemarkValue from "1~4094" to "1~4095"
--   in unisIfQoSPQClassRuleTable.
-- V1.3 2006/03/29 modified by xialei
--   Modify the MAX-ACCESS clause of unisCBQoSQueueDropType.
--   Modify the description for object unisCBQoSQueueCbs.
--   Modify the enumeration name of object unisCBQoSRedirectType.
-- V1.4 2007/10/15 modified by wangjinwang
--   Add unisCBQoSGlobalApplyTable to global policy apply.
--   Add unisCBQoSPolicyClassMode and unisCBQoSPolicyClassCfgOrder to
--   unisCBQoSPolicyClassCfgInfoTable.
--   Add unisCBQoSNestCfgInfoTable to traffic behavior.
--   Add enumeration matchRuleServiceDot1p
--   to object unisCBQoSMatchRuleType.
--   Add enumeration typeTopMostVlanID to object unisCBQoSRemarkType.
-- V1.5 2007/12/12 modified by Xu Hang/ChenWei
--   Delete the default value of unisCBQoSGlobalApplyDirection
--   in unisCBQoSGlobalApplyTable
--   Add unisCBQoSApplyPolicyIndexObjects to unisCBQoSApplyPolicyStaticsObjects
--   Add unisCBQoSStaticsObjects to unisCBQoSApplyPolicyStaticsObjects
--   Modify the MAX-ACCESS clause of unisCBQoSQueueDropType.
--   Modify the MAX-ACCESS clause of unisCBQoSIfApplyPolicyIfIndex,
--   unisCBQoSIfApplyPolicyDirection, unisCBQoSVlanApplyPolicyVlanid
--   and unisCBQoSVlanApplyPolicyDirection.
--   Add unisCBQoSApplyingStatusObjects to unisCBQoSObjects.
--   Add unisCBQoSApplyingStatus to unisCBQoSApplyPolicyObjects.
--   Add unisCBQoSNotifications to unisCBQoSObjects.
--   Add unisCBQoSNotificationsPrefix to unisCBQoSNotifications.
--   Add unisCBQoSIfPolicyChanged and unisCBQoSVlanPolicyChanged
--   to unisCBQoSNotificationsPrefix.
--   Add remark-local-pre-pass and remark-drop-pre-pass to CarAction.
--   Delete the default value of unisCBQoSVlanApplyPolicyDirection and
--   unisCBQoSGlobalApplyDirection.
-- V1.6 2008/05/28 modified by ChenWei
--   Add unisCBQoSNestPolicyCfgInfoTable to unisCBQoSBehaviorObjects.
--   Add unisCBQoSNestPolicyApplyObjectTable to unisCBQoSApplyPolicyIndexObjects.
-- V1.7 2011/01/25 modified by XuGuoFang/zhaixiaoxiang
--   Modify the range of unisCBQoSQueueBandwidthValue.
--   Modify the range of unisCBQoSQueueCbs.
--   Modify the description of unisCBQoSQueueCbsRatio.
--   Modify the description of unisCBQoSBehaviorIndexNext.
-- V1.8 2012/07/02 modified by XuJunjie/XunZhi
--   Modify MatchRuleType add matchRuleMplsLabel to matchRuleForwardingLayer.
--   Modify the description for unisCBQoSClassifierIndexNext.
--   Modify the description for unisCBQosClassifierMatchRuleNextIndex.
--   Modify the description for unisCBQoSMatchRuleStringValue.
--   Modify the description for unisCBQoSMatchRuleIntValue1.
--   Modify the description for unisCBQoSMatchRuleIntValue2.
--   Add table unisCBQoSMatchCpProtoCfgTable.
--   Add table unisCBQoSMatchCpGroupCfgTable.
--   Add unisCBQoSAccountingMode in unisCBQoSAccountCfgInfoTable.
--   Add unisCBQoSRedirectIfVlanID in unisCBQoSRedirectCfgInfoTable.
--   Add table unisCBQoSMirrorIfCfgInfoTable.
--   Add table unisCBQoSColoredRemarkCfgTable.
--   Add table unisCBQoSPrimapCfgInfoTable.
--   Add table unisCBQoSColorMapDpCfgInfoTable.
--   Modify the description for unisCBQoSPolicyIndexNext
--   Modify the description for unisCBQoSPolicyClassNextIndex
--   Add table unisCBQoSCpApplyPolicyTable
--   Modify ApplyObjectType add controlPlane
--   Modify the description for unisCBQoSApplyObjectMainSite
--   Modify the description for unisCBQoSApplyObjectSubChannel
--   Add table unisCBQoSCpApplyObjectTable
--   Modify SYNTAX add partialSuccess(3) for unisCBQoSClassBehaviorStatus
--   Modify unisCBQoSQueueBandwidthUnit add a value RemainPercent.
--   Modify unisCBQoSPolicyClassMode, add modeQppb, modeIpSourceGuard, modeVoiceVlan,
--   modeDCBX to value list.
--   Add node ApplyPolicyStatus for table unisCBQoSIfApplyPolicyTable,
--   unisCBQoSVlanApplyPolicyTable, and unisCBQoSGlobalApplyTable.
-- V1.9 2013/03/13 modified by MouXuanli
--   Add typeSecondMplsExp to RemarkType.
--   Modify the description of unisCBQoSRemarkValue and unisCBQoSColoredRemarkValue.
-- V2.0 2014/02/24 modified by MouXuanli
--   Modify the range of unisCBQoSQueueLength.
-- V2.1 2014/04/17 modified by GaoYu/XunZhi
--   Add enumeration matchRuleMacAcl and matchRuleUserAcl to MatchRuleType.
--   Modify the description of unisCBQoSMatchRuleStringValue.
--   Modify the description of unisCBQoSMatchRuleIntValue1.
-- V2.2 2016/2/24 modified by WanQing
--   Add enumeration matchRuleVxlan to MatchRuleType.
--   Modify the description of unisCBQoSMatchRuleStringValue.
--   2017/03/02 modified by gaomengfei
--   Add unisCBQoSCarClassName to unisCBQoSCarRunInfoEntry.
--   2017/10/10 modified by gaomengfei
--   Add unisCBQoSAccountingPktpps to UnisCBQoSAccountingRunInfoEntry.
--   Add unisCBQoSAccountingPktbps to UnisCBQoSAccountingRunInfoEntry.
--   2018/01/4 modified by gaomengfei
--   Add unisCBQoSPolicyAccRunInfoTable.
-- V2.3 2018/10/31 modified by gaomengfei
--   Add unisCBQoSCarGreenpps to unisCBQoSCarRunInfoEntry.
--   Add unisCBQoSCarGreenbps to unisCBQoSCarRunInfoEntry.
--   Add unisCBQoSCarRedpps to unisCBQoSCarRunInfoEntry.
--   Add unisCBQoSCarRedbps to unisCBQoSCarRunInfoEntry.
--   Add unisCBQoSCarYellowpps to unisCBQoSCarRunInfoEntry.
--   Add unisCBQoSCarYellowbps to unisCBQoSCarRunInfoEntry.
-- V2.4 2019/05/29 modified by gaomengfei
--   Modify the value range of unisCBQoSQueueBandwidthValue from "1~10000000" to "1~100000000".
-- ==========================================================================
UNIS-CBQOS2-MIB DEFINITIONS ::= BEGIN

IMPORTS
    unisCommon
        FROM UNIS-OID-MIB
    Integer32, Counter64, Unsigned32, OBJECT-TYPE, MODULE-IDENTITY, NOTIFICATION-TYPE
        FROM SNMPv2-SMI
    InetAddressType, InetAddress
        FROM INET-ADDRESS-MIB           -- [RFC3291]
    TEXTUAL-CONVENTION, RowStatus, TruthValue
        FROM SNMPv2-TC;

unisCBQos2 MODULE-IDENTITY
    LAST-UPDATED "201905290000Z"        --May 29, 2019 at 00:00 GMT
    ORGANIZATION
        "Unisyue Technologies Co., Ltd."
    CONTACT-INFO
        ""
    DESCRIPTION
        "This MIB contains objects to manage configuration and
         monitor running state for Class Based QoS feature.

            *********************************
                    MIB Tables
            **********************************
         This MIB consists of the following tables:
            1 :  unisCBQoSClassifierCfgInfoTable
            2 :  unisCBQoSMatchRuleCfgInfoTable
            3 :  unisCBQoSMatchCpProtoCfgTable
            4 :  unisCBQoSMatchCpGroupCfgTable
            5 :  unisCBQoSBehaviorCfgInfoTable
            6 :  unisCBQoSCarCfgInfoTable
            7 :  unisCBQoSAggregativeCarCfgInfoTable
            8 :  unisCBQoSGtsCfgInfoTable
            9 :  unisCBQoSRemarkCfgInfoTable
            10:  unisCBQoSQueueCfgInfoTable
            11:  unisCBQoSWredCfgInfoTable
            12:  unisCBQoSWredClassCfgInfoTable
            13:  unisCBQoSPolicyRouteCfgInfoTable
            14:  unisCBQoSNatCfgInfoTable
            15:  unisCBQoSFirewallCfgInfoTable
            16:  unisCBQoSSamplingCfgInfoTable
            17:  unisCBQoSAccountCfgInfoTable
            18:  unisCBQoSRedirectCfgInfoTable
            19:  unisCBQoSPriorityMapCfgInfoTable
            20:  unisCBQoSPolicyCfgInfoTable
            21:  unisCBQoSPolicyClassCfgInfoTable
            22:  unisCBQoSIfApplyPolicyTable
            23:  unisCBQoSAtmPvcApplyPolicyTable
            24:  unisCBQoSVlanApplyPolicyTable
            25:  unisCBQoSFrClassApplyPolicyTable
            26:  unisCBQoSFrPvcApplyPolicyTable
            27:  unisCBQoSIfCbqRunInfoTable
            28:  unisCBQoSIfClassMatchRunInfoTable
            29:  unisCBQoSIfCarRunInfoTable
            30:  unisCBQoSIfGtsRunInfoTable
            31:  unisCBQoSIfRemarkRunInfoTable
            32:  unisCBQoSIfQueueRunInfoTable
            33:  unisCBQoSIfWredRunInfoTable
            34:  unisCBQoSIfAccountingRunInfoTable
            35:  unisCBQoSAtmPvcCbqRunInfoTable
            36:  unisCBQoSAtmPvcClassMatchRunInfoTable
            37:  unisCBQoSAtmPvcCarRunInfoTable
            38:  unisCBQoSAtmPvcGtsRunInfoTable
            39:  unisCBQoSAtmPvcRemarkRunInfoTable
            40:  unisCBQoSAtmPvcQueueRunInfoTable
            41:  unisCBQoSAtmPvcWredRunInfoTable
            42:  unisCBQoSAtmPvcAccountingRunInfoTable
            43:  unisCBQoSFrPvcCbqRunInfoTable
            44:  unisCBQoSFrPvcClassMatchRunInfoTable
            45:  unisCBQoSFrPvcCarRunInfoTable
            46:  unisCBQoSFrPvcGtsRunInfoTable
            47:  unisCBQoSFrPvcRemarkRunInfoTable
            48:  unisCBQoSFrPvcQueueRunInfoTable
            49:  unisCBQoSFrPvcWredRunInfoTable
            50:  unisCBQoSFrPvcAccountingRunInfoTable
            51:  unisCBQoSIfVlanClassMatchRunInfoTable
            52:  unisCBQoSIfVlanAccountingRunInfoTable
            53:  unisCBQoSMirrorCfgInfoTable
            54:  unisCBQoSGlobalApplyTable
            55:  unisCBQoSCpApplyPolicyTable
            56:  unisCBQoSNestCfgInfoTable
            57:  unisCBQoSNestPolicyCfgInfoTable
            58:  unisCBQoSMirrorIfCfgInfoTable
            59:  unisCBQoSColoredRemarkCfgTable
            60:  unisCBQoSPrimapCfgInfoTable
            61:  unisCBQoSColorMapDpCfgInfoTable
            62:  unisCBQoSApplyObjectTable
            63:  unisCBQoSIntApplyObjectTable
            64:  unisCBQoSVlanApplyObjectTable
            65:  unisCBQoSPvcApplyObjectTable
            66:  unisCBQoSNestPolicyApplyObjectTable
            67:  unisCBQoSCpApplyObjectTable
            68:  unisCBQoSCbqRunInfoTable
            69:  unisCBQoSClassMatchRunInfoTable
            70:  unisCBQoSCarRunInfoTable
            71:  unisCBQoSGtsRunInfoTable
            72:  unisCBQoSRemarkRunInfoTable
            73:  unisCBQoSQueueRunInfoTable
            74:  unisCBQoSWredRunInfoTable
            75:  unisCBQoSAccountingRunInfoTable
            76:  unisCBQoSPolicyAccRunInfoTable
            77:  unisCBQoSApplyingStatusObjects
            78:  unisCBQoSNotifications
        "
    REVISION "201905290000Z"        --May 29, 2019 at 00:00 GMT
    DESCRIPTION
        "Modify the value range of unisCBQoSQueueBandwidthValue from 1~10000000 to 1~100000000."
    REVISION "201810310000Z"        --October 31, 2018 at 00:00 GMT
    DESCRIPTION
        "Add unisCBQoSCarGreenpps to unisCBQoSCarRunInfoEntry.
         Add unisCBQoSCarGreenbps to unisCBQoSCarRunInfoEntry.
         Add unisCBQoSCarRedpps to unisCBQoSCarRunInfoEntry.
         Add unisCBQoSCarRedbps to unisCBQoSCarRunInfoEntry.
         Add unisCBQoSCarYellowpps to unisCBQoSCarRunInfoEntry.
         Add unisCBQoSCarYellowbps to unisCBQoSCarRunInfoEntry."
    REVISION "201801040000Z"        --January 4, 2018 at 00:00 GMT
    DESCRIPTION
        "Add unisCBQoSPolicyAccRunInfoTable."
    REVISION "201710100000Z"        --October 10, 2017 at 00:00 GMT
    DESCRIPTION
        "Add unisCBQoSAccountingPktpps to UnisCBQoSAccountingRunInfoEntry.
         Add unisCBQoSAccountingPktbps to UnisCBQoSAccountingRunInfoEntry."
    REVISION "201703020000Z"        --March 02, 2017 at 00:00 GMT
    DESCRIPTION
        "Add unisCBQoSCarClassName to unisCBQoSCarRunInfoEntry."
    REVISION "201602240000Z"        -- Feb 24, 2016 at 00:00 GMT
    DESCRIPTION
        "Add enumeration matchRuleVxlan to MatchRuleType.
         Modify the description of unisCBQoSMatchRuleStringValue."
    REVISION "201207020000Z"        -- July 02, 2012 at 00:00 GMT
    DESCRIPTION
        "Modified to add new tables and new nodes."
    REVISION "200507300000Z"        -- July 30, 2005 at 00:00 GMT
    DESCRIPTION
        "The initial revision of this MIB module."
    ::= { unisQos2 2 }

unisQos2 OBJECT IDENTIFIER ::= { unisCommon 65 }

--
-- type definitions in the traffic classifier
--

-- MatchRuleType
MatchRuleType ::= TEXTUAL-CONVENTION
    STATUS current
    DESCRIPTION
        "Type of Match Rule."
    SYNTAX INTEGER
    {
        matchRuleAny(1),
        matchRuleIpv4Acl(2),
        matchRuleIPv6Acl(3) ,
        matchRuleIPv4Protocol(4),
        matchRuleIPv6Protocol(5),
        matchRuleIPXProtocol(6),
        matchRuleDscp(7),
        matchRuleIpPre(8),
        matchRuleVlan8021p(9),
        matchRuleMplsExp(10),
        matchRuleAtmClp(11),
        matchRuleFrDe(12),
        matchRuleSourceMac(13),
        matchRuleDestinationMac(14),
        matchRuleQosLocalID(15),
        matchRuleClassifier(16),
        matchRuleInboundInterface(17),
        matchRuleRtpPort(18),
        matchRuleSourceIp(19),
        matchRuleVlanID(20),
        matchRuleTopMostVlanID(21),
        matchRuleLocalPrecedence(22),
        matchRuleDropPriority(23),
        matchRuleBittorrent(24),
        matchRuleServiceDot1p(25),
        matchRuleMplsLabel(26),
        matchRuleSecondMplsLabel(27),
        matchRuleSecondMplsExp(28),
        matchRulePacketLength(29),
        matchRuleArpProtocol(30),
        matchRuleForwardingLayer(31),
        matchRuleMacAcl(32),
        matchRuleUserAcl(33),
        matchRuleVxlan(34)
    }
--
-- end of type definitions in the traffic classifier
--

--
-- type definitions in the traffic behavior
--

-- CarAction
CarAction ::= TEXTUAL-CONVENTION
    STATUS current
    DESCRIPTION
        "The actions taken when packets conforming or exceeding
         the configured committed information rate(CIR)."
    SYNTAX INTEGER
    {
        invalid(0),
        pass(1),
        continue(2),
        discard(3),
        remark(4),
        remark-ip-continue(5),
        remark-ip-pass(6),
        remark-mplsexp-continue(7),
        remark-mplsexp-pass(8),
        remark-dscp-continue(9),
        remark-dscp-pass(10),
        remark-dot1p-continue(11),
        remark-dot1p-pass(12),
        remark-atm-clp-continue(13),
        remark-atm-clp-pass(14),
        remark-fr-de-continue(15),
        remark-fr-de-pass(16),
        remark-local-pre-pass(17),
        remark-drop-pre-pass(18)
    }

-- RemarkType
RemarkType ::= TEXTUAL-CONVENTION
    STATUS  current
    DESCRIPTION
        "Type of remark."
    SYNTAX INTEGER
    {
        typeIpPrecedence(1),
        typeDscp(2),
        typeMplsExp(3),
        typeVlan8021p(4),
        typeAtmClp(5),
        typeFrDe(6),
        typeVlanID(7),
        typeQosLocalID(8),
        typeDropPrecedence(9),
        typeLocalPrecedence(10),
        typeTopMostVlanID(11),
        typeSecondMplsExp(12)
    }

-- WredType
WredType ::= TEXTUAL-CONVENTION
    STATUS current
    DESCRIPTION
        "WRED type."
    SYNTAX INTEGER
    {
        typeIpPrecBased(1),
        typeDscpBased(2),
        typeDropLevelBased(3),
        typeAtmClpBased(4),
        typeVlan8021pBased(5),
        typeMplsExpBased(6)
    }

-- QueueType
QueueType ::= TEXTUAL-CONVENTION
    STATUS  current
    DESCRIPTION
        "Queueing Type:
         EF:(1)
         AF:(2)
         WFQ:(3)
        "
    SYNTAX INTEGER
    {
        ef(1),
        af(2),
        wfq(3)
    }

-- QueueBandwidthUnit
QueueBandwidthUnit ::= TEXTUAL-CONVENTION
    STATUS current
    DESCRIPTION
        "Bandwidth Unit:
         Absolute, Unit : Kbps(1)
         Percent, Unit : %(2)
         RemainPercent, Unit : %(3)
        "
    SYNTAX INTEGER
    {
        unitUnavailable(0),
        unitAbsolute(1),
        unitPercent(2),
        unitRemainPercent(3)
    }

--
-- end of type definitions in the traffic behavior
--

--
-- type definitions in the policy
--

-- Direction
DirectionType ::= TEXTUAL-CONVENTION
    STATUS  current
    DESCRIPTION
        "The direction of policy apply on at interface."
    SYNTAX  INTEGER
    {
        inbound(1),
        outbound(2)
    }

-- ApplyObjectType
ApplyObjectType ::= TEXTUAL-CONVENTION
    STATUS  current
    DESCRIPTION
        "Type of QoS apply object."
    SYNTAX  INTEGER
    {
        interface(1),
        vlan(2),
        atmPvc(3),
        frDlci(4),
        controlPlane(5)
    }

--
-- end of type definitions in policy
--

--
-- Node definitions
--
unisCBQoSObjects OBJECT IDENTIFIER ::= { unisCBQos2 1 }

-- unisCBQoSClassifierObjects

unisCBQoSClassifierObjects OBJECT IDENTIFIER ::= { unisCBQoSObjects 1 }

-- Traffic Classifier Next Index
unisCBQoSClassifierIndexNext OBJECT-TYPE
    SYNTAX Integer32
    MAX-ACCESS read-only
    STATUS current
    DESCRIPTION
        "This object contains an appropriate value to be used for
         unisCBQoSClassifierIndex when creating rows in the
         unisCBQoSClassifierCfgInfoTable.
        "
    ::= { unisCBQoSClassifierObjects 1 }

-- Traffic Classifier

unisCBQoSClassifierCfgInfoTable OBJECT-TYPE
    SYNTAX SEQUENCE OF UnisCBQoSClassifierCfgInfoEntry
    MAX-ACCESS not-accessible
    STATUS current
    DESCRIPTION
        "A table of Traffic Classifier configuration information."
    ::= { unisCBQoSClassifierObjects 2 }

unisCBQoSClassifierCfgInfoEntry OBJECT-TYPE
    SYNTAX UnisCBQoSClassifierCfgInfoEntry
    MAX-ACCESS not-accessible
    STATUS current
    DESCRIPTION
        "Traffic Classifier Configuration Information Entry."
    INDEX { unisCBQoSClassifierIndex }
    ::= { unisCBQoSClassifierCfgInfoTable 1 }

UnisCBQoSClassifierCfgInfoEntry ::=
    SEQUENCE
    {
        unisCBQoSClassifierIndex
            Integer32,
        unisCBQoSClassifierName
            OCTET STRING,
        unisCBQoSClassifierRuleCount
            Integer32,
        unisCBQoSClassifierOperator
            INTEGER,
        unisCBQoSClassifierLayer
            INTEGER,
        unisCBQoSClassifierType
            INTEGER,
        unisCBQosClassifierMatchRuleNextIndex
            Integer32,
        unisCBQoSClassifierRowStatus
            RowStatus
    }

unisCBQoSClassifierIndex OBJECT-TYPE
    SYNTAX Integer32
    MAX-ACCESS not-accessible
    STATUS current
    DESCRIPTION
        "Index of Traffic Classifier.  Begin with 0."
    ::= { unisCBQoSClassifierCfgInfoEntry 1 }

unisCBQoSClassifierName OBJECT-TYPE
    SYNTAX OCTET STRING (SIZE (1..31))
    MAX-ACCESS read-create
    STATUS current
    DESCRIPTION
        "Name of Traffic Classifier."
    ::= { unisCBQoSClassifierCfgInfoEntry 2 }

unisCBQoSClassifierRuleCount OBJECT-TYPE
    SYNTAX Integer32
    MAX-ACCESS read-only
    STATUS current
    DESCRIPTION
        "The counter of match rules of Traffic classifier."
    ::= { unisCBQoSClassifierCfgInfoEntry 3 }

unisCBQoSClassifierOperator OBJECT-TYPE
    SYNTAX INTEGER
    {
        and(1),
        or(2)
    }
    MAX-ACCESS read-create
    STATUS current
    DESCRIPTION
        "Operator of the match rules of traffic classifier.
         Software QoS supports and, or.
         Hardware QoS supports and.
        "
    DEFVAL { and }
    ::= { unisCBQoSClassifierCfgInfoEntry 4 }

unisCBQoSClassifierLayer OBJECT-TYPE
    SYNTAX INTEGER
    {
        unavailable(1),
        l2(2),
        l3(3),
        both(4)
    }
    MAX-ACCESS read-create
    STATUS current
    DESCRIPTION
        "Configuration layer of traffic classifier.
         Only hardware QoS support it.
         1(unavailable) is returned only when getting value from software QoS.
         1(unavailable) can't be set.
        "
    DEFVAL { l3 }
    ::= { unisCBQoSClassifierCfgInfoEntry 5 }

unisCBQoSClassifierType OBJECT-TYPE
    SYNTAX INTEGER
    {
        systemDefined(1),
        userDefined(2)
    }
    MAX-ACCESS read-only
    STATUS current
    DESCRIPTION
        "The type of classifier."
    ::= { unisCBQoSClassifierCfgInfoEntry 6 }

unisCBQosClassifierMatchRuleNextIndex OBJECT-TYPE
    SYNTAX Integer32
    MAX-ACCESS read-only
    STATUS current
    DESCRIPTION
        "This object contains an appropriate value to be used for
         unisCBQoSMatchRuleIndex when creating rows in the
         unisCBQoSMatchRuleCfgInfoTable.
        "
    ::= { unisCBQoSClassifierCfgInfoEntry 7 }

unisCBQoSClassifierRowStatus OBJECT-TYPE
    SYNTAX RowStatus
    MAX-ACCESS read-create
    STATUS current
    DESCRIPTION
        "RowStatus."
    ::= { unisCBQoSClassifierCfgInfoEntry 8 }

-- Match rule

unisCBQoSMatchRuleCfgInfoTable OBJECT-TYPE
    SYNTAX SEQUENCE OF UnisCBQoSMatchRuleCfgInfoEntry
    MAX-ACCESS not-accessible
    STATUS current
    DESCRIPTION
        "A table of Match Rule configuration information."
    ::= { unisCBQoSClassifierObjects 3 }

unisCBQoSMatchRuleCfgInfoEntry OBJECT-TYPE
    SYNTAX UnisCBQoSMatchRuleCfgInfoEntry
    MAX-ACCESS not-accessible
    STATUS current
    DESCRIPTION
        "Match Rule Configuration Information Entry."
    INDEX { unisCBQoSClassifierIndex, unisCBQoSMatchRuleIndex }
    ::= { unisCBQoSMatchRuleCfgInfoTable 1 }

UnisCBQoSMatchRuleCfgInfoEntry ::=
    SEQUENCE
    {
        unisCBQoSMatchRuleIndex
            Integer32,
        unisCBQoSMatchRuleIfNot
            INTEGER,
        unisCBQoSMatchRuleType
            MatchRuleType,
        unisCBQoSMatchRuleStringValue
            OCTET STRING,
        unisCBQoSMatchRuleIntValue1
            Unsigned32,
        unisCBQoSMatchRuleIntValue2
            Unsigned32,
        unisCBQoSMatchIpAddressType
            InetAddressType,
        unisCBQoSMatchIpAddress
            InetAddress,
        unisCBQoSMatchRuleRowStatus
            RowStatus
    }

unisCBQoSMatchRuleIndex OBJECT-TYPE
    SYNTAX Integer32
    MAX-ACCESS not-accessible
    STATUS current
    DESCRIPTION
        "Index of Match Rule."
    ::= { unisCBQoSMatchRuleCfgInfoEntry 1 }

unisCBQoSMatchRuleIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { unisCBQoSMatchRuleCfgInfoEntry 2 }

unisCBQoSMatchRuleType OBJECT-TYPE
    SYNTAX MatchRuleType
    MAX-ACCESS read-create
    STATUS current
    DESCRIPTION
        "Type of Match Rule."
    ::= { unisCBQoSMatchRuleCfgInfoEntry 3 }

unisCBQoSMatchRuleStringValue OBJECT-TYPE
    SYNTAX OCTET STRING (SIZE (0..255))
    MAX-ACCESS read-create
    STATUS current
    DESCRIPTION
        "Value of Match Rule.
         IPv4 ACL: SIZE (1..63) ACL name
         MAC ACL: SIZE (1..63) MAC ACL name
         User ACL: SIZE (1..63) User ACL name
         IPv6 ACL: SIZE (1..63) IPv6 ACL name
         SourceMAC: SIZE (12) HHHHHHHHHHHH
           for example: 010102020303 means the match rule is
                        'if-match source-mac 0101-0202-0303'
         DestinationMAC: SIZE (12) HHHHHHHHHHHH
           for example: 010102020303 means the match rule is
                        'if-match destination-mac 0101-0202-0303'
         Classifier: SIZE (1..31) classifier name
         InboundInterface: SIZE (1..47) interface description
         TopMostVlanID, VlanID: SIZE(1..109), up to 10 values can be input;
           for example: 1##5#11#111##114#1111 means the match rule is
                        'if-match vlanid 1 to 5 11 111 to 114 1111'
         SourceIp: SIZE (12) HHHHHHHHHHHH
           for example: 010102020303 means the match rule is
                        'if-match source-ip mac-address 0101-0202-0303'
         MplsLabel: SIZE (1..63), up to 8 values can be input;
           for example: 1#11#111#1111 means the match rule is
                        'if-match mpls-label 1 11 111 1111';
                        1##1111 means the match rule is
                        'if-match mpls-label 1 to 1111';
         SecondMplsLabel: SIZE (1..63), up to 8 values can be input;
           for example: 1#11#111#1111 means the match rule is
                        'if-match mpls-label 1 11 111 1111';
                        1##1111 means the match rule is
                        'if-match mpls-label 1 to 1111';
         VxlanID: SIZE(1..8) Vxlan ID or any
           for example: 20 means the match rule is
                        'if-match vxlan 20';
                        any means the match rule is
                        'if-match vxlan any';
         other types: Set is not permitted.  Zero-length string will
                      be returned when getting.
        "
    ::= { unisCBQoSMatchRuleCfgInfoEntry 4 }

unisCBQoSMatchRuleIntValue1 OBJECT-TYPE
    SYNTAX Unsigned32
    MAX-ACCESS read-create
    STATUS current
    DESCRIPTION
        "Value of Match Rule.
         IPv4 ACL: 2000~3999
         MAC ACL: 4000~4999
         User ACL: 5000~5999
         IPv6 ACL: 2000~3999; 10000~42767
         Software QoS: 2000~3999
         Hardware Qos: 10000~42767
         RtpPort: start-port: 2000~65535
         IpPrec: value: 0~7, up to 8 values can be input.  The bit set to
                 1 of the last 8 bits of unisCBQoSMatchRuleIntValue1 is
                 used to indicate the value 0~7.
           for example: 0x53(Binary format is 01010011)
                        means the match rule is 'if-match ip-prec 0 1 4 6'
         Dscp: value:0~63, up to 8 values can be input.
               The bit set to 1 of unisCBQoSMatchRuleIntValue1 is used
               to indicate the value 32~63.
               The bit set to 1 of unisCBQoSMatchRuleIntValue2 is used to
               indicate the value 0~31.
           for example: 0x80000003 means the match rule is 'if-match
                        dscp 32 33 63'
         Vlan8021p: value:0~7, up to 8 values can be input.  The bit set
                    to 1 of the last 8 bits of unisCBQoSMatchRuleIntValue1
                    is used to indicate the value 0~7.
           for example: 0x53(Binary format is 01010011) means the
                        match rule is 'if-match customer-dot1p 0 1 4 6'
         MplsExp: value:0~7, up to 8 values can be input.  The bit set to 1
                  of the last 8 bits of unisCBQoSMatchRuleIntValue1 is used
                  to indicate the 8 value 0~7.
           for example: 0x53(Binary format is 01010011) means the
                        match rule is 'if-match mpls 0 1 4 6'
         SourceIp: 1~4095
         QosLocalID: 1~4095
         AtmClp: 0~1
         FrDe: 0~1
         LocalPrecedence: 0~7, up to 8 values can be input.  The bit set to
                          1 of the last 8 bits of unisCBQoSMatchRuleIntValue1
                          is used to indicate the value 0~7.
           for example: 0x53(Binary format is 01010011) means the match
                        rule is 'if-match localprecedence 0 1 4 6'
         DropPriority: 0~2, up to 3 values can be input.  The bit set to 1
                       of the last 3 bits of unisCBQoSMatchRuleIntValue1 is
                       used to indicate the value 0~2.
         ServiceDot1p: 0~7, up to 8 values can be input.
                       The bit set to 1 of the last 8 bits of
                       unisCBQoSMatchRuleIntValue1 is used to indicate
                       the value 0~7.
           for example: 0x53(Binary format is 01010011) means the match
                        rule is 'if-match service-dot1p 0 1 4 6'
         SecondMplsExp: value:0~7, up to 8 values can be input.  The bit
                        set to 1 of the last 8 bits of unisCBQoSMatchRuleIntValue1
                        is used to indicate the 8 value 0~7.
           for example: 0x53(Binary format is 01010011) means the
                        match rule is 'if-match mpls 0 1 4 6'
         PacketLength: 1~2000.  unisCBQoSMatchRuleIntValue1 is used to
                       indicate the minimum value, unisCBQoSMatchRuleIntValue2
                       is used to indicate the maximum value.
         ForwardingLayer: {bridge(1), route(2)}
         other types: Set is not permitted.  0xffffffff will be returned
                      when getting.
        "
    ::= { unisCBQoSMatchRuleCfgInfoEntry 5 }

unisCBQoSMatchRuleIntValue2 OBJECT-TYPE
    SYNTAX Unsigned32
    MAX-ACCESS read-create
    STATUS current
    DESCRIPTION
        "Value of Match Rule.
         RtpPort: end-port: 2000~65535
         Dscp: value:0~63, up to 8 values can be input.
               The bit set to 1 of unisCBQoSMatchRuleIntValue1 is used to indicate the value 32~63.
               The bit set to 1 of unisCBQoSMatchRuleIntValue2 is used to indicate the value 0~31.
               for example: 0x80000003 means the match rule is 'if-match dscp 0 1 31'
         PacketLength: 1~2000.  unisCBQoSMatchRuleIntValue1 is used to
                       indicate the minimum value, unisCBQoSMatchRuleIntValue2
                       is used to indicate the maximum value.
         other types: Set is not permitted.  0xffffffff will be returned when getting.
        "
    ::= { unisCBQoSMatchRuleCfgInfoEntry 6 }

unisCBQoSMatchIpAddressType OBJECT-TYPE
    SYNTAX InetAddressType
    MAX-ACCESS read-create
    STATUS current
    DESCRIPTION
        "A value that represents a type of Internet address.
          unknown(0)  An unknown address type.  This value MUST
            be used if the value of the corresponding
            InetAddress object is a zero-length string.
            It may also be used to indicate an IP address
            which is not in one of the formats defined below.

         ipv4(1)     An IPv4 address as defined by the
                InetAddressIPv4 textual convention.

         ipv6(2)     A global IPv6 address as defined by the
                InetAddressIPv6 textual convention.

         ipv4z(3)    A non-global IPv4 address including a zone
                index as defined by the InetAddressIPv4z textual convention.

         ipv6z(4)    A non-global IPv6 address including a zone
                index as defined by the InetAddressIPv6z textual convention.

         dns(16)     A DNS domain name as defined by the
                InetAddressDNS textual convention.

         Value of match rule.
         SourceIp support this node.
         other types: Set is not permitted.  Unknown will be returned when getting.
        "
    ::= { unisCBQoSMatchRuleCfgInfoEntry 7 }

unisCBQoSMatchIpAddress OBJECT-TYPE
    SYNTAX InetAddress
    MAX-ACCESS read-create
    STATUS current
    DESCRIPTION
        "Denotes a generic Internet address.
         SourceIP support this node.
         other types: Set is not permitted.  NULL will be returned when getting.
        "
    ::= { unisCBQoSMatchRuleCfgInfoEntry 8 }

unisCBQoSMatchRuleRowStatus OBJECT-TYPE
    SYNTAX RowStatus
    MAX-ACCESS read-create
    STATUS current
    DESCRIPTION
        "RowStatus."
    ::= { unisCBQoSMatchRuleCfgInfoEntry 9 }

-- unisCBQoSMatchCpProtoCfgTable

unisCBQoSMatchCpProtoCfgTable OBJECT-TYPE
    SYNTAX SEQUENCE OF UnisCBQoSMatchCpProtoCfgEntry
    MAX-ACCESS not-accessible
    STATUS current
    DESCRIPTION
        "A table of Matching CpProtocol Rule configuration information."
    ::= { unisCBQoSClassifierObjects 4 }

unisCBQoSMatchCpProtoCfgEntry OBJECT-TYPE
    SYNTAX UnisCBQoSMatchCpProtoCfgEntry
    MAX-ACCESS not-accessible
    STATUS current
    DESCRIPTION
        "Matching CpProtocol Rule Configuration Information Entry."
    INDEX { unisCBQoSClassifierIndex, unisCBQoSMatchRuleIndex }
    ::= { unisCBQoSMatchCpProtoCfgTable 1 }

UnisCBQoSMatchCpProtoCfgEntry ::=
    SEQUENCE
    {
        unisCBQoSMatchCpProtoIfNot
            INTEGER,
        unisCBQoSMatchCpProtoValue
            OCTET STRING,
        unisCBQoSMatchCpProtoRowStatus
            RowStatus
    }

unisCBQoSMatchCpProtoIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { unisCBQoSMatchCpProtoCfgEntry 1 }

unisCBQoSMatchCpProtoValue OBJECT-TYPE
    SYNTAX OCTET STRING (SIZE (0..255))
    MAX-ACCESS read-create
    STATUS current
    DESCRIPTION
        "Value of Cp Protocol, SIZE (1..23).  Up to 8 values can be input.
           for example: 1#2#3#4#5 means the match rule is
                        'if-match control-plane protocol arp arp-snooping
                        bgp bgp4+ bpdu-tunnel';
        arp: 1
        arp-snooping: 2
        bgp: 3
        bgp4+: 4
        bpdu-tunnel: 5
        cdp: 6
        cfd: 7
        dhcp: 8
        dhcp-snooping: 9
        dhcp6: 10
        dldp: 11
        dot1x: 12
        gmrp: 13
        gvrp: 14
        http: 15
        https: 16
        icmp: 17
        icmp6: 18
        igmp: 19
        igmp-snooping: 20
        irdp: 21
        isis: 22
        lacp: 23
        ldp: 24
        ldp6: 25
        lldp: 26
        mld: 27
        msdp: 28
        ntp: 29
        oam: 30
        ospf-multicast: 31
        ospf-unicast: 32
        ospf3-multicast: 33
        ospf3-unicast: 34
        pagp: 35
        pim-multicast: 36
        pim-unicast: 37
        pim6-multicast: 38
        pim6-unicast: 39
        portal: 40
        pppoe-negotiation: 41
        pvst: 42
        radius: 43
        rip: 44
        ripng: 45
        rrpp: 46
        rsvp: 47
        smart-link: 48
        snmp: 49
        stp: 50
        tacas: 51
        udld: 52
        udp-helper: 53
        vrrp: 54
        vrrp6: 55
        vtp: 56
        ip-option: 57
        ipv6-option: 58
        ssh: 59
        telnet: 60"
    ::= { unisCBQoSMatchCpProtoCfgEntry 2 }

unisCBQoSMatchCpProtoRowStatus OBJECT-TYPE
    SYNTAX RowStatus
    MAX-ACCESS read-create
    STATUS current
    DESCRIPTION
        "RowStatus."
    ::= { unisCBQoSMatchCpProtoCfgEntry 3 }

-- unisCBQoSMatchCpGroupCfgTable

unisCBQoSMatchCpGroupCfgTable OBJECT-TYPE
    SYNTAX SEQUENCE OF UnisCBQoSMatchCpGroupCfgEntry
    MAX-ACCESS not-accessible
    STATUS current
    DESCRIPTION
        "A table of matching Cp protocol group rule configuration information."
    ::= { unisCBQoSClassifierObjects 5 }

unisCBQoSMatchCpGroupCfgEntry OBJECT-TYPE
    SYNTAX UnisCBQoSMatchCpGroupCfgEntry
    MAX-ACCESS not-accessible
    STATUS current
    DESCRIPTION
        "Matching Cp protocol group Rule Configuration Information Entry."
    INDEX { unisCBQoSClassifierIndex, unisCBQoSMatchRuleIndex }
    ::= { unisCBQoSMatchCpGroupCfgTable 1 }

UnisCBQoSMatchCpGroupCfgEntry ::=
    SEQUENCE
    {
        unisCBQoSMatchCpGroupIfNot
            INTEGER,
        unisCBQoSMatchCpGroupValue
            INTEGER,
        unisCBQoSMatchCpGroupRowStatus
            RowStatus
    }

unisCBQoSMatchCpGroupIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { unisCBQoSMatchCpGroupCfgEntry 1 }

unisCBQoSMatchCpGroupValue OBJECT-TYPE
    SYNTAX INTEGER
    {
        critical(1),
        important(2),
        management(3),
        normal(4),
        redirect(5),
        monitor(6),
        exception(7)
    }
    MAX-ACCESS read-create
    STATUS current
    DESCRIPTION
        "Type of Cp protocol group.
        "
    ::= { unisCBQoSMatchCpGroupCfgEntry 2 }

unisCBQoSMatchCpGroupRowStatus OBJECT-TYPE
    SYNTAX RowStatus
    MAX-ACCESS read-create
    STATUS current
    DESCRIPTION
        "RowStatus."
    ::= { unisCBQoSMatchCpGroupCfgEntry 3 }

-- unisCBQoSBehaviorObjects

unisCBQoSBehaviorObjects OBJECT IDENTIFIER ::= { unisCBQoSObjects 2 }

-- Traffic Behavior Next Index

unisCBQoSBehaviorIndexNext OBJECT-TYPE
    SYNTAX Integer32
    MAX-ACCESS read-only
    STATUS current
    DESCRIPTION
        "This object contains an appropriate value to be used for
         unisCBQoSBehaviorIndex when creating rows in the
         unisCBQoSBehaviorCfgInfoTable."
    ::= { unisCBQoSBehaviorObjects 1 }

-- Traffic Behavior

unisCBQoSBehaviorCfgInfoTable OBJECT-TYPE
    SYNTAX SEQUENCE OF UnisCBQoSBehaviorCfgInfoEntry
    MAX-ACCESS not-accessible
    STATUS current
    DESCRIPTION
        "A table of Traffic Behavior configuration information."
    ::= { unisCBQoSBehaviorObjects 2 }

unisCBQoSBehaviorCfgInfoEntry OBJECT-TYPE
    SYNTAX UnisCBQoSBehaviorCfgInfoEntry
    MAX-ACCESS not-accessible
    STATUS current
    DESCRIPTION
        "Traffic Behavior Configuration Information Entry."
    INDEX { unisCBQoSBehaviorIndex }
    ::= { unisCBQoSBehaviorCfgInfoTable 1 }

UnisCBQoSBehaviorCfgInfoEntry ::=
    SEQUENCE
    {
        unisCBQoSBehaviorIndex
            Integer32,
        unisCBQoSBehaviorName
            OCTET STRING,
        unisCBQoSBehaviorType
            INTEGER,
        unisCBQoSBehaviorRowStatus
            RowStatus
    }

unisCBQoSBehaviorIndex OBJECT-TYPE
    SYNTAX Integer32
    MAX-ACCESS not-accessible
    STATUS current
    DESCRIPTION
        "Index of Traffic Behavior."
    ::= { unisCBQoSBehaviorCfgInfoEntry 1 }

unisCBQoSBehaviorName OBJECT-TYPE
    SYNTAX OCTET STRING (SIZE (1..31))
    MAX-ACCESS read-create
    STATUS current
    DESCRIPTION
        "Name of Traffic Behavior."
    ::= { unisCBQoSBehaviorCfgInfoEntry 2 }

unisCBQoSBehaviorType OBJECT-TYPE
    SYNTAX INTEGER
    {
        systemDefined(1),
        userDefined(2)
    }
    MAX-ACCESS read-only
    STATUS current
    DESCRIPTION
        "Type of behavior."
    ::= { unisCBQoSBehaviorCfgInfoEntry 3 }

unisCBQoSBehaviorRowStatus OBJECT-TYPE
    SYNTAX RowStatus
    MAX-ACCESS read-create
    STATUS current
    DESCRIPTION
        "RowStatus."
    ::= { unisCBQoSBehaviorCfgInfoEntry 4 }

-- CAR

unisCBQoSCarCfgInfoTable OBJECT-TYPE
    SYNTAX SEQUENCE OF UnisCBQoSCarCfgInfoEntry
    MAX-ACCESS not-accessible
    STATUS current
    DESCRIPTION
        "A table of CAR feature configuration information."
    ::= { unisCBQoSBehaviorObjects 3 }

unisCBQoSCarCfgInfoEntry OBJECT-TYPE
    SYNTAX UnisCBQoSCarCfgInfoEntry
    MAX-ACCESS not-accessible
    STATUS current
    DESCRIPTION
        "CAR Configuration Information Entry."
    INDEX { unisCBQoSBehaviorIndex }
    ::= { unisCBQoSCarCfgInfoTable 1 }

UnisCBQoSCarCfgInfoEntry ::=
    SEQUENCE
    {
        unisCBQoSCarCir
            Unsigned32,
        unisCBQoSCarCbs
            Unsigned32,
        unisCBQoSCarEbs
            Unsigned32,
        unisCBQoSCarPir
            Unsigned32,
        unisCBQoSCarPbs
            Unsigned32,
        unisCBQoSCarGreenAction
            CarAction,
        unisCBQoSCarGreenRemarkValue
            Integer32,
        unisCBQoSCarYellowAction
            CarAction,
        unisCBQoSCarYellowRemarkValue
            Integer32,
        unisCBQoSCarRedAction
            CarAction,
        unisCBQoSCarRedRemarkValue
            Integer32,
        unisCBQoSCarPolicedPriorityMapType
            INTEGER,
        unisCBQoSCarRowStatus
            RowStatus
    }

unisCBQoSCarCir OBJECT-TYPE
    SYNTAX Unsigned32
    MAX-ACCESS read-create
    STATUS current
    DESCRIPTION
        "Committed Information Rate.  Unit: kbps."
    ::= { unisCBQoSCarCfgInfoEntry 1 }

unisCBQoSCarCbs OBJECT-TYPE
    SYNTAX Unsigned32
    MAX-ACCESS read-create
    STATUS current
    DESCRIPTION
        "Committed Burst Size.  Unit: byte."
    ::= { unisCBQoSCarCfgInfoEntry 2 }

unisCBQoSCarEbs OBJECT-TYPE
    SYNTAX Unsigned32
    MAX-ACCESS read-create
    STATUS current
    DESCRIPTION
        "Excess Burst Size.  Unit: byte.
         Only software QoS support this node.
         4294967295 is returned only when getting value from hardware QoS.
         4294967295 can't be set."
    DEFVAL {0}
    ::= { unisCBQoSCarCfgInfoEntry 3 }

unisCBQoSCarPir OBJECT-TYPE
    SYNTAX Unsigned32
    MAX-ACCESS read-create
    STATUS current
    DESCRIPTION
        "Peak Information Rate.  Unit: kbps.
         Only hardware QoS support this node.
         4294967295 is returned only when getting value from software QoS.
         4294967295 can't be set."
    ::= { unisCBQoSCarCfgInfoEntry 4 }

unisCBQoSCarPbs OBJECT-TYPE
    SYNTAX Unsigned32
    MAX-ACCESS read-create
    STATUS current
    DESCRIPTION
        "Peak Burst Size.  Unit: byte.
         Only hardware QoS support this node.
         4294967295 is returned only when getting value from software QoS.
         4294967295 can't be set."
    ::= { unisCBQoSCarCfgInfoEntry 5 }

unisCBQoSCarGreenAction OBJECT-TYPE
    SYNTAX CarAction
    MAX-ACCESS read-create
    STATUS current
    DESCRIPTION
        "Green Action
         Hardware QoS : pass, discard, remark.
         Software QoS : pass, discard, remark IP Precedence, remark DSCP, remark MPLS EXP.
        "
    DEFVAL {pass}
    ::= { unisCBQoSCarCfgInfoEntry 6 }

unisCBQoSCarGreenRemarkValue OBJECT-TYPE
    SYNTAX Integer32 (0..63|255)
    MAX-ACCESS read-create
    STATUS current
    DESCRIPTION
        "The value is to remark When green action is remarking.
         For remarking DSCP, the range is 0~63;
         For remarking IP Precedence and MPLS EXP, the range is 0~7;
         Only software QoS support this node.
         255 is returned only when getting value from hardware QoS or
         when action being pass, discard of software QoS.
         255 can't be set.
        "
    ::= { unisCBQoSCarCfgInfoEntry 7 }

unisCBQoSCarYellowAction OBJECT-TYPE
    SYNTAX CarAction
    MAX-ACCESS read-create
    STATUS current
    DESCRIPTION
        "Yellow Action:
         Only hardware QoS support this node.  Hardware QoS support pass, discard, remark.
         invalid is returned only when getting value from software QoS.
         invalid can't be set.
        "
    DEFVAL {remark}
    ::= { unisCBQoSCarCfgInfoEntry 8 }

unisCBQoSCarYellowRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { unisCBQoSCarCfgInfoEntry 9 }

unisCBQoSCarRedAction OBJECT-TYPE
    SYNTAX CarAction
    MAX-ACCESS read-create
    STATUS current
    DESCRIPTION
        "Red Action:
         Hardware QoS : pass, discard, remark.
         Software QoS : pass, discard, remark IP Precedence, remark DSCP, remark MPLS EXP.
        "
    DEFVAL {discard}
    ::= { unisCBQoSCarCfgInfoEntry 10 }

unisCBQoSCarRedRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { unisCBQoSCarCfgInfoEntry 11 }

unisCBQoSCarPolicedPriorityMapType OBJECT-TYPE
    SYNTAX INTEGER
    {
        none(0),
        policed-service-map(1),
        local-precedence-dot1p-map(2),
        drop-precedence-map(3)
    }
    MAX-ACCESS read-create
    STATUS current
    DESCRIPTION
        "Type of priority map."
    DEFVAL { none }
    ::= { unisCBQoSCarCfgInfoEntry 12 }

unisCBQoSCarRowStatus OBJECT-TYPE
    SYNTAX RowStatus
    MAX-ACCESS read-create
    STATUS current
    DESCRIPTION
        "RowStatus."
    ::= { unisCBQoSCarCfgInfoEntry 13 }

--
-- nodes of aggregative CAR applyed behavior
--
unisCBQoSAggregativeCarCfgInfoTable OBJECT-TYPE
    SYNTAX SEQUENCE OF UnisCBQoSAggregativeCarCfgInfoEntry
    MAX-ACCESS not-accessible
    STATUS current
    DESCRIPTION
        "A table of aggregative CAR applied CBQ feature configuration information.
         Aggregative CAR is managed by UNIS-IFQOS2-MIB.  So, you can use UNIS-IFQOS2-MIB
         to get some details information about aggregative CAR.
        "
    ::= { unisCBQoSBehaviorObjects 4 }

unisCBQoSAggregativeCarCfgInfoEntry OBJECT-TYPE
    SYNTAX UnisCBQoSAggregativeCarCfgInfoEntry
    MAX-ACCESS not-accessible
    STATUS current
    DESCRIPTION
        "Aggregative CAR feature applied CBQ configuration information entry."
    INDEX { unisCBQoSBehaviorIndex,
            unisCBQoSCarAggregativeCarIndex }
    ::= { unisCBQoSAggregativeCarCfgInfoTable 1 }

UnisCBQoSAggregativeCarCfgInfoEntry ::=
    SEQUENCE
    {
        unisCBQoSCarAggregativeCarIndex
            Integer32,
        unisCBQoSCarAggregativeCarName
            OCTET STRING,
        unisCBQoSAggregativeCarRowStatus
            RowStatus
    }

unisCBQoSCarAggregativeCarIndex OBJECT-TYPE
    SYNTAX Integer32
    MAX-ACCESS not-accessible
    STATUS current
    DESCRIPTION
        "Index of aggregative CAR.
         It is equal to unisIfQoSAggregativeCarIndex at UNIS-IFQOS2-MIB.
        "
    ::= { unisCBQoSAggregativeCarCfgInfoEntry 1 }

unisCBQoSCarAggregativeCarName OBJECT-TYPE
    SYNTAX OCTET STRING (SIZE(1..31))
    MAX-ACCESS read-only
    STATUS current
    DESCRIPTION
        "Name of aggregative CAR.
         It is equal to unisIfQoSAggregativeCarName at UNIS-IFQOS2-MIB.
        "
    ::= { unisCBQoSAggregativeCarCfgInfoEntry 2 }

unisCBQoSAggregativeCarRowStatus OBJECT-TYPE
    SYNTAX RowStatus
    MAX-ACCESS read-create
    STATUS current
    DESCRIPTION
        "RowStatus."
    ::= { unisCBQoSAggregativeCarCfgInfoEntry 3 }

-- GTS

unisCBQoSGtsCfgInfoTable OBJECT-TYPE
    SYNTAX SEQUENCE OF UnisCBQoSGtsCfgInfoEntry
    MAX-ACCESS not-accessible
    STATUS current
    DESCRIPTION
        "A table of GTS feature configuration information."
    ::= { unisCBQoSBehaviorObjects 5 }

unisCBQoSGtsCfgInfoEntry OBJECT-TYPE
    SYNTAX UnisCBQoSGtsCfgInfoEntry
    MAX-ACCESS not-accessible
    STATUS current
    DESCRIPTION
        "GTS Configuration Information Entry."
    INDEX { unisCBQoSBehaviorIndex }
    ::= { unisCBQoSGtsCfgInfoTable 1 }

UnisCBQoSGtsCfgInfoEntry ::=
    SEQUENCE
    {
        unisCBQoSGtsCir
            Unsigned32,
        unisCBQoSGtsCbs
            Unsigned32,
        unisCBQoSGtsEbs
            Unsigned32,
        unisCBQoSGtsQueueLength
            Integer32,
        unisCBQoSGtsRowStatus
            RowStatus,
        unisCBQoSGtsPir
            Unsigned32
    }

unisCBQoSGtsCir OBJECT-TYPE
    SYNTAX Unsigned32
    MAX-ACCESS read-create
    STATUS current
    DESCRIPTION
        "Committed Information Rate.  Unit: kbps"
    ::= { unisCBQoSGtsCfgInfoEntry 1 }

unisCBQoSGtsCbs OBJECT-TYPE
    SYNTAX Unsigned32
    MAX-ACCESS read-create
    STATUS current
    DESCRIPTION
        "Committed Burst Size.  Unit: byte
         default: max(cir*1/2,15000)"
    ::= { unisCBQoSGtsCfgInfoEntry 2 }

unisCBQoSGtsEbs OBJECT-TYPE
    SYNTAX Unsigned32
    MAX-ACCESS read-create
    STATUS current
    DESCRIPTION
        "Excess Burst Size.  Unit: byte"
    ::= { unisCBQoSGtsCfgInfoEntry 3 }

unisCBQoSGtsQueueLength OBJECT-TYPE
    SYNTAX Integer32 (1..1024)
    MAX-ACCESS read-create
    STATUS current
    DESCRIPTION
        "The length of GTS buffer."
    DEFVAL { 50 }
    ::= { unisCBQoSGtsCfgInfoEntry 4 }

unisCBQoSGtsRowStatus OBJECT-TYPE
    SYNTAX RowStatus
    MAX-ACCESS read-create
    STATUS current
    DESCRIPTION
        "RowStatus."
    ::= { unisCBQoSGtsCfgInfoEntry 5 }

unisCBQoSGtsPir OBJECT-TYPE
    SYNTAX Unsigned32
    UNITS  "kbps"
    MAX-ACCESS read-create
    STATUS current
    DESCRIPTION
        "Peak Information Rate."
    ::= { unisCBQoSGtsCfgInfoEntry 6 }

-- REMARK

unisCBQoSRemarkCfgInfoTable OBJECT-TYPE
    SYNTAX SEQUENCE OF UnisCBQoSRemarkCfgInfoEntry
    MAX-ACCESS not-accessible
    STATUS current
    DESCRIPTION
        "A table of Remarking feature configuration information."
    ::= { unisCBQoSBehaviorObjects 6 }

unisCBQoSRemarkCfgInfoEntry OBJECT-TYPE
    SYNTAX UnisCBQoSRemarkCfgInfoEntry
    MAX-ACCESS not-accessible
    STATUS current
    DESCRIPTION
        "Remarking Configuration Information Entry."
    INDEX { unisCBQoSBehaviorIndex, unisCBQoSRemarkType }
    ::= { unisCBQoSRemarkCfgInfoTable 1 }

UnisCBQoSRemarkCfgInfoEntry ::=
    SEQUENCE
    {
        unisCBQoSRemarkType
            RemarkType,
        unisCBQoSRemarkValue
            Integer32,
        unisCBQoSRemarkRowStatus
            RowStatus
    }

unisCBQoSRemarkType OBJECT-TYPE
    SYNTAX RemarkType
    MAX-ACCESS not-accessible
    STATUS current
    DESCRIPTION
        "Remark type."
    ::= { unisCBQoSRemarkCfgInfoEntry 1 }

unisCBQoSRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { unisCBQoSRemarkCfgInfoEntry 2 }

unisCBQoSRemarkRowStatus OBJECT-TYPE
    SYNTAX RowStatus
    MAX-ACCESS read-create
    STATUS current
    DESCRIPTION
        "RowStatus"
    ::= { unisCBQoSRemarkCfgInfoEntry 3 }

-- Queue

unisCBQoSQueueCfgInfoTable OBJECT-TYPE
    SYNTAX SEQUENCE OF UnisCBQoSQueueCfgInfoEntry
    MAX-ACCESS not-accessible
    STATUS current
    DESCRIPTION
        "A table of queue feature configuration information."
    ::= { unisCBQoSBehaviorObjects 7 }

unisCBQoSQueueCfgInfoEntry OBJECT-TYPE
    SYNTAX UnisCBQoSQueueCfgInfoEntry
    MAX-ACCESS not-accessible
    STATUS current
    DESCRIPTION
        "Queue Configuration Information Entry."
    INDEX { unisCBQoSBehaviorIndex }
    ::= { unisCBQoSQueueCfgInfoTable 1 }

UnisCBQoSQueueCfgInfoEntry ::=
    SEQUENCE
    {
        unisCBQoSQueueType
            QueueType,
        unisCBQoSQueueDropType
            INTEGER,
        unisCBQoSQueueLength
            Integer32,
        unisCBQoSQueueBandwidthUnit
            QueueBandwidthUnit,
        unisCBQoSQueueBandwidthValue
            Integer32,
        unisCBQoSQueueCbs
            Integer32,
        unisCBQoSQueueQueueNumber
            INTEGER,
        unisCBQoSQueueCbsRatio
            Integer32,
        unisCBQoSQueueRowStatus
            RowStatus
    }

unisCBQoSQueueType OBJECT-TYPE
    SYNTAX QueueType
    MAX-ACCESS read-create
    STATUS current
    DESCRIPTION
        "Queueing Type:
         EF:(1)
         AF:(2)
         WFQ:(3)"
    ::= { unisCBQoSQueueCfgInfoEntry 1 }

unisCBQoSQueueDropType OBJECT-TYPE
    SYNTAX INTEGER
    {
        typeUnavailable(0),
        typeTailDrop(1),
        typeWred(2)
    }
    MAX-ACCESS read-create
    STATUS current
    DESCRIPTION
        "The drop type of queue.  Only valid for AF and WFQ queue.
         typeUnavailable is returned only when getting value about EF queue.
         typeUnavailable can't be set."
    DEFVAL {typeTailDrop}
    ::= { unisCBQoSQueueCfgInfoEntry 2 }

unisCBQoSQueueLength OBJECT-TYPE
    SYNTAX Integer32 (1..2147483647)
    MAX-ACCESS read-create
    STATUS current
    DESCRIPTION
        "The length of QueueLength.  Only valid for tail-drop type
         of AF and WFQ queue.
         2147483647 is returned only when getting value about EF queue
         or WRED type of AF and WFQ queue.
         2147483647 can't be set."
    DEFVAL { 64 }
    ::= { unisCBQoSQueueCfgInfoEntry 3 }

unisCBQoSQueueBandwidthUnit OBJECT-TYPE
    SYNTAX QueueBandwidthUnit
    MAX-ACCESS read-create
    STATUS current
    DESCRIPTION
        "Bandwidth Unit:
         Absolute, Unit Kbps (1)
         Percent, Unit % (2)
         RemainPercent, Unit % of remained bandwidth (3)
         Only valid for EF and AF queue.
         0 is returned only when getting value about WFQ queue.
         0 can't be set.
        "
    ::= { unisCBQoSQueueCfgInfoEntry 4 }

unisCBQoSQueueBandwidthValue OBJECT-TYPE
    SYNTAX Integer32 (1..100000000|2147483647)
    MAX-ACCESS read-create
    STATUS current
    DESCRIPTION
        "Bandwidth value:
         Absolute value: 8~100000000.  Unit: Kbps
         Percent value: 1~100.
         Only valid for EF and AF queue.
         2147483647 is returned only when getting value about WFQ queue.
         2147483647 can't be set."
    ::= { unisCBQoSQueueCfgInfoEntry 5 }

unisCBQoSQueueCbs OBJECT-TYPE
    SYNTAX Integer32 (32..1000000000|2147483647)
    MAX-ACCESS read-create
    STATUS current
    DESCRIPTION
        "Committed Burst Size.  Unit: byte.
         Only valid for EF queue.
         Default: If the value of 'unisCBQoSQueueBandwidthValue * 25' is
                  between 1500 and 2000000, the default value of this
                  object is 'unisCBQoSQueueBandwidthValue * 25';If the value of
                  'unisCBQoSQueueBandwidthValue * 25' is larger than or equal to
                  2000000, the default value of this object is 2000000;
                  If the value of 'unisCBQoSQueueBandwidthValue * 25' is
                  less than or equal to 1500, the default value of this object is 1500.
         2147483647 is returned only when getting value about AF or WFQ queue.
         2147483647 can't be set."
    ::= { unisCBQoSQueueCfgInfoEntry 6 }

unisCBQoSQueueQueueNumber OBJECT-TYPE
    SYNTAX INTEGER
    {
        unavailable(0),
        a16(16),
        a32(32),
        a64(64),
        a128(128),
        a256(256),
        a512(512),
        a1024(1024),
        a2048(2048),
        a4096(4096)
    }
    MAX-ACCESS read-create
    STATUS current
    DESCRIPTION
        "Max number of hashed queues (a power of 2).
         Only valid for WFQ.
         'unavailable' is returned only when getting value about AF or EF queue.
         'unavailable' can't be set."
    DEFVAL {a256}
    ::= { unisCBQoSQueueCfgInfoEntry 7 }

unisCBQoSQueueCbsRatio OBJECT-TYPE
    SYNTAX Integer32(25..500|2147483647)
    MAX-ACCESS read-create
    STATUS current
    DESCRIPTION
        "Committed Burst Size Ratio.
         CBS = CBS_Ratio * Bandwidth(k bps)
         Only valid for EF queue.
         2147483647 is returned only when getting value about AF or WFQ queue.
         2147483647 can't be set.
        "
    DEFVAL { 25 }
    ::= { unisCBQoSQueueCfgInfoEntry 8 }

unisCBQoSQueueRowStatus OBJECT-TYPE
    SYNTAX RowStatus
    MAX-ACCESS read-create
    STATUS current
    DESCRIPTION
        "RowStatus."
    ::= { unisCBQoSQueueCfgInfoEntry 9 }

-- WRED

unisCBQoSWredCfgInfoTable OBJECT-TYPE
    SYNTAX SEQUENCE OF UnisCBQoSWredCfgInfoEntry
    MAX-ACCESS not-accessible
    STATUS current
    DESCRIPTION
        "A table of WRED configuration information."
    ::= { unisCBQoSBehaviorObjects 8 }

unisCBQoSWredCfgInfoEntry OBJECT-TYPE
    SYNTAX UnisCBQoSWredCfgInfoEntry
    MAX-ACCESS not-accessible
    STATUS current
    DESCRIPTION
        "WRED Configuration Information Entry."
    INDEX { unisCBQoSBehaviorIndex }
    ::= { unisCBQoSWredCfgInfoTable 1 }

UnisCBQoSWredCfgInfoEntry ::=
    SEQUENCE
    {
        unisCBQoSWredType
            WredType,
        unisCBQoSWredWeightConst
            Integer32
    }

unisCBQoSWredType OBJECT-TYPE
    SYNTAX WredType
    MAX-ACCESS read-write
    STATUS current
    DESCRIPTION
        "WRED type."
    DEFVAL { 1 }
    ::= { unisCBQoSWredCfgInfoEntry 1 }

unisCBQoSWredWeightConst OBJECT-TYPE
    SYNTAX Integer32 (1..16)
    MAX-ACCESS read-write
    STATUS current
    DESCRIPTION
        "Specify weight for calculating mean queue depth."
    DEFVAL { 9 }
    ::= { unisCBQoSWredCfgInfoEntry 2 }

-- WRED Class

unisCBQoSWredClassCfgInfoTable OBJECT-TYPE
    SYNTAX SEQUENCE OF UnisCBQoSWredClassCfgInfoEntry
    MAX-ACCESS not-accessible
    STATUS current
    DESCRIPTION
        "A table of WRED configuration information."
    ::= { unisCBQoSBehaviorObjects 9 }

unisCBQoSWredClassCfgInfoEntry OBJECT-TYPE
    SYNTAX UnisCBQoSWredClassCfgInfoEntry
    MAX-ACCESS not-accessible
    STATUS current
    DESCRIPTION
        "WRED Class Configuration Information Entry."
    INDEX { unisCBQoSBehaviorIndex, unisCBQoSWredClassValue }
    ::= { unisCBQoSWredClassCfgInfoTable 1 }

UnisCBQoSWredClassCfgInfoEntry ::=
    SEQUENCE
    {
        unisCBQoSWredClassValue
            Integer32,
        unisCBQoSWredClassLowLimit
            Integer32,
        unisCBQoSWredClassHighLimit
            Integer32,
        unisCBQoSWredClassDiscardProb
            Integer32
    }

unisCBQoSWredClassValue OBJECT-TYPE
    SYNTAX Integer32 (0..63)
    MAX-ACCESS not-accessible
    STATUS current
    DESCRIPTION
        "The class value.
         For IP precedence based WRED, the class is IP precedence,
         and range is 0~7.
         For DSCP based WRED, the class is DSCP, and range is 0~63.
        "
    ::= { unisCBQoSWredClassCfgInfoEntry 1 }

unisCBQoSWredClassLowLimit OBJECT-TYPE
    SYNTAX Integer32 (1..1024)
    MAX-ACCESS read-write
    STATUS current
    DESCRIPTION
        "The low limit of queue depth."
    DEFVAL {10}
    ::= { unisCBQoSWredClassCfgInfoEntry 2 }

unisCBQoSWredClassHighLimit OBJECT-TYPE
    SYNTAX Integer32 (1..1024)
    MAX-ACCESS read-write
    STATUS current
    DESCRIPTION
        "The high limit of queue depth."
    DEFVAL { 30 }
    ::= { unisCBQoSWredClassCfgInfoEntry 3 }

unisCBQoSWredClassDiscardProb OBJECT-TYPE
    SYNTAX Integer32 (1..255)
    MAX-ACCESS read-write
    STATUS current
    DESCRIPTION
        "The discard probability denominator."
    DEFVAL { 10 }
    ::= { unisCBQoSWredClassCfgInfoEntry 4 }

-- Policy Route

unisCBQoSPolicyRouteCfgInfoTable OBJECT-TYPE
    SYNTAX SEQUENCE OF UnisCBQoSPolicyRouteCfgInfoEntry
    MAX-ACCESS not-accessible
    STATUS current
    DESCRIPTION
        "A table of Policy Routing configuration information."
    ::= { unisCBQoSBehaviorObjects 10 }

unisCBQoSPolicyRouteCfgInfoEntry OBJECT-TYPE
    SYNTAX UnisCBQoSPolicyRouteCfgInfoEntry
    MAX-ACCESS not-accessible
    STATUS current
    DESCRIPTION
        "Policy Routeing Configuration Information Entry."
    INDEX { unisCBQoSBehaviorIndex }
    ::= { unisCBQoSPolicyRouteCfgInfoTable 1 }

UnisCBQoSPolicyRouteCfgInfoEntry ::=
    SEQUENCE
    {
        unisCBQoSPolicyRouteIpAddrType
            InetAddressType,
        unisCBQoSPolicyRouteNexthop
            InetAddress,
        unisCBQoSPolicyRouteBackup
            INTEGER,
        unisCBQoSPolicyRouteRowStatus
            RowStatus
    }

unisCBQoSPolicyRouteIpAddrType OBJECT-TYPE
    SYNTAX InetAddressType
    MAX-ACCESS read-create
    STATUS current
    DESCRIPTION
        "Type of InetAddress."
    ::= { unisCBQoSPolicyRouteCfgInfoEntry 1 }

unisCBQoSPolicyRouteNexthop OBJECT-TYPE
    SYNTAX InetAddress
    MAX-ACCESS read-create
    STATUS current
    DESCRIPTION
        "The next-hop ip address for redirection."
    ::= { unisCBQoSPolicyRouteCfgInfoEntry 2 }

unisCBQoSPolicyRouteBackup OBJECT-TYPE
    SYNTAX INTEGER
    {
        backup(1),
        notbackup(2)
    }
    MAX-ACCESS read-create
    STATUS current
    DESCRIPTION
        "Whether forward the packet according to the routing table
         When the next-hop IP address for redirection is not valid.
         Backup means forwarding.  NoBackup means not forwarding.
        "
    ::= { unisCBQoSPolicyRouteCfgInfoEntry 3 }

unisCBQoSPolicyRouteRowStatus OBJECT-TYPE
    SYNTAX RowStatus
    MAX-ACCESS read-create
    STATUS current
    DESCRIPTION
        "RowStatus."
    ::= { unisCBQoSPolicyRouteCfgInfoEntry 4 }

-- NAT

unisCBQoSNatCfgInfoTable OBJECT-TYPE
    SYNTAX SEQUENCE OF UnisCBQoSNatCfgInfoEntry
    MAX-ACCESS not-accessible
    STATUS current
    DESCRIPTION
        "A table of Nat configuration information."
    ::= { unisCBQoSBehaviorObjects 11 }

unisCBQoSNatCfgInfoEntry OBJECT-TYPE
    SYNTAX UnisCBQoSNatCfgInfoEntry
    MAX-ACCESS not-accessible
    STATUS current
    DESCRIPTION
        "Nat Configuration Information Entry."
    INDEX { unisCBQoSBehaviorIndex }
    ::= { unisCBQoSNatCfgInfoTable 1 }

UnisCBQoSNatCfgInfoEntry ::=
    SEQUENCE
    {
        unisCBQoSNatMainNumber
            Integer32,
        unisCBQoSNatBackupNumber
            Integer32,
        unisCBQoSNatServiceClass
            Integer32,
        unisCBQoSNatRowStatus
            RowStatus
    }

unisCBQoSNatMainNumber OBJECT-TYPE
    SYNTAX Integer32 (1..255)
    MAX-ACCESS read-create
    STATUS current
    DESCRIPTION
        "The main ISP number."
    ::= { unisCBQoSNatCfgInfoEntry 1 }

unisCBQoSNatBackupNumber OBJECT-TYPE
    SYNTAX Integer32 (1..255)
    MAX-ACCESS read-create
    STATUS current
    DESCRIPTION
        "The backup ISP number"
    ::= { unisCBQoSNatCfgInfoEntry 2 }

unisCBQoSNatServiceClass OBJECT-TYPE
    SYNTAX Integer32 (1..4)
    MAX-ACCESS read-create
    STATUS current
    DESCRIPTION
        "The service class."
    DEFVAL { 2 }
    ::= { unisCBQoSNatCfgInfoEntry 3 }

unisCBQoSNatRowStatus OBJECT-TYPE
    SYNTAX RowStatus
    MAX-ACCESS read-create
    STATUS current
    DESCRIPTION
        "RowStatus."
    ::= { unisCBQoSNatCfgInfoEntry 4 }

-- Firewall

unisCBQoSFirewallCfgInfoTable OBJECT-TYPE
    SYNTAX SEQUENCE OF UnisCBQoSFirewallCfgInfoEntry
    MAX-ACCESS not-accessible
    STATUS current
    DESCRIPTION
        "A table of firewall configuration information."
    ::= { unisCBQoSBehaviorObjects 12 }

unisCBQoSFirewallCfgInfoEntry OBJECT-TYPE
    SYNTAX UnisCBQoSFirewallCfgInfoEntry
    MAX-ACCESS not-accessible
    STATUS current
    DESCRIPTION
        "Firewall configuration information entry."
    INDEX { unisCBQoSBehaviorIndex }
    ::= { unisCBQoSFirewallCfgInfoTable 1 }

UnisCBQoSFirewallCfgInfoEntry ::=
    SEQUENCE
    {
        unisCBQoSFirewallAction
            INTEGER,
        unisCBQoSFirewallRowStatus
            RowStatus
    }

unisCBQoSFirewallAction OBJECT-TYPE
    SYNTAX INTEGER
    {
        permit(1),
        deny(2)
    }
    MAX-ACCESS read-create
    STATUS current
    DESCRIPTION
        "The firewall action "
    DEFVAL {permit}
    ::= { unisCBQoSFirewallCfgInfoEntry 1 }

unisCBQoSFirewallRowStatus OBJECT-TYPE
    SYNTAX RowStatus
    MAX-ACCESS read-create
    STATUS current
    DESCRIPTION
        "RowStatus."
    ::= { unisCBQoSFirewallCfgInfoEntry 2 }

-- Sampling behavior

unisCBQoSSamplingCfgInfoTable OBJECT-TYPE
    SYNTAX SEQUENCE OF UnisCBQoSSamplingCfgInfoEntry
    MAX-ACCESS not-accessible
    STATUS current
    DESCRIPTION
        "A table of sampling configuration information."
    ::= { unisCBQoSBehaviorObjects 13 }

unisCBQoSSamplingCfgInfoEntry OBJECT-TYPE
    SYNTAX UnisCBQoSSamplingCfgInfoEntry
    MAX-ACCESS not-accessible
    STATUS current
    DESCRIPTION
        "Sampling configuration information entry."
    INDEX { unisCBQoSBehaviorIndex }
    ::= { unisCBQoSSamplingCfgInfoTable 1 }

UnisCBQoSSamplingCfgInfoEntry ::=
    SEQUENCE
    {
        unisCBQoSSamplingNum
            Integer32,
        unisCBQoSSamplingRowStatus
            RowStatus
    }

unisCBQoSSamplingNum OBJECT-TYPE
    SYNTAX Integer32 (1..16)
    MAX-ACCESS read-create
    STATUS current
    DESCRIPTION
        "The sampling number."
    ::= { unisCBQoSSamplingCfgInfoEntry 1 }

unisCBQoSSamplingRowStatus OBJECT-TYPE
    SYNTAX RowStatus
    MAX-ACCESS read-create
    STATUS current
    DESCRIPTION
        "RowStatus."
    ::= { unisCBQoSSamplingCfgInfoEntry 2 }

unisCBQoSAccountCfgInfoTable OBJECT-TYPE
    SYNTAX SEQUENCE OF UnisCBQoSAccountCfgInfoEntry
    MAX-ACCESS not-accessible
    STATUS current
    DESCRIPTION
        "A table of account configuration information."
    ::= { unisCBQoSBehaviorObjects 14 }

unisCBQoSAccountCfgInfoEntry OBJECT-TYPE
    SYNTAX UnisCBQoSAccountCfgInfoEntry
    MAX-ACCESS not-accessible
    STATUS current
    DESCRIPTION
        "Account configuration information entry."
    INDEX { unisCBQoSBehaviorIndex }
    ::= { unisCBQoSAccountCfgInfoTable 1 }

UnisCBQoSAccountCfgInfoEntry ::=
    SEQUENCE
    {
        unisCBQoSAccounting
            TruthValue,
        unisCBQoSAccountRowStatus
            RowStatus,
        unisCBQoSAccountingMode
            INTEGER
    }

unisCBQoSAccounting OBJECT-TYPE
    SYNTAX TruthValue
    MAX-ACCESS read-create
    STATUS current
    DESCRIPTION
        "Account action."
    ::= { unisCBQoSAccountCfgInfoEntry 1 }

unisCBQoSAccountRowStatus OBJECT-TYPE
    SYNTAX RowStatus
    MAX-ACCESS read-create
    STATUS current
    DESCRIPTION
        "RowStatus."
    ::= { unisCBQoSAccountCfgInfoEntry 2 }

unisCBQoSAccountingMode OBJECT-TYPE
    SYNTAX INTEGER
    {
        auto(1),
        packet(2),
        byte(3),
        both(4)
    }
    MAX-ACCESS read-create
    STATUS current
    DESCRIPTION
        "Account mode."
    DEFVAL { auto }
    ::= { unisCBQoSAccountCfgInfoEntry 3 }

--
-- nodes of unisCBQoSRedirectCfgInfoTable
--
unisCBQoSRedirectCfgInfoTable OBJECT-TYPE
    SYNTAX SEQUENCE OF UnisCBQoSRedirectCfgInfoEntry
    MAX-ACCESS not-accessible
    STATUS current
    DESCRIPTION
        "A table of redirect configuration information."
    ::= { unisCBQoSBehaviorObjects 15 }

unisCBQoSRedirectCfgInfoEntry OBJECT-TYPE
    SYNTAX UnisCBQoSRedirectCfgInfoEntry
    MAX-ACCESS not-accessible
    STATUS current
    DESCRIPTION
        "Redirect configuration information entry."
    INDEX { unisCBQoSBehaviorIndex }
    ::= { unisCBQoSRedirectCfgInfoTable 1 }

UnisCBQoSRedirectCfgInfoEntry ::=
    SEQUENCE
    {
        unisCBQoSRedirectType
            INTEGER,
        unisCBQoSRedirectIfIndex
            Integer32,
        unisCBQoSRedirectIpAddressType
            InetAddressType,
        unisCBQoSRedirectIpAddress1
            InetAddress,
        unisCBQoSRedirectIpAddress2
            InetAddress,
        unisCBQoSRedirectRowStatus
            RowStatus,
        unisCBQoSRedirectIpv6Interface1
            Integer32,
        unisCBQoSRedirectIpv6Interface2
            Integer32,
        unisCBQoSRedirectIfVlanID
            Integer32
    }

unisCBQoSRedirectType OBJECT-TYPE
    SYNTAX INTEGER
    {
        cpu(1),
        interface(2),
        nextHop(3)
    }
    MAX-ACCESS read-create
    STATUS current
    DESCRIPTION
        "The type of redirect."
    ::= { unisCBQoSRedirectCfgInfoEntry 1 }

unisCBQoSRedirectIfIndex OBJECT-TYPE
    SYNTAX Integer32
    MAX-ACCESS read-create
    STATUS current
    DESCRIPTION
        "ifIndex.
         Only the value of unisCBQoSRedirectType is interface,
         can be set this node.
        "
    DEFVAL { 0 }
    ::= { unisCBQoSRedirectCfgInfoEntry 2 }

unisCBQoSRedirectIpAddressType OBJECT-TYPE
    SYNTAX InetAddressType
    MAX-ACCESS read-create
    STATUS current
    DESCRIPTION
        "A value that represents a type of Internet address.
          unknown(0)  An unknown address type.  This value MUST
             be used if the value of the corresponding
             InetAddress object is a zero-length string.
             It may also be used to indicate an IP address
             which is not in one of the formats defined
             below.

          ipv4(1)     An IPv4 address as defined by the
             InetAddressIPv4 textual convention.

          ipv6(2)     A global IPv6 address as defined by the
             InetAddressIPv6 textual convention.

          ipv4z(3)    A non-global IPv4 address including a zone
             index as defined by the InetAddressIPv4z
             textual convention.

          ipv6z(4)    A non-global IPv6 address including a zone
             index as defined by the InetAddressIPv6z
             textual convention.

          dns(16)     A DNS domain name as defined by the
             InetAddressDNS textual convention.
          Now supports ipv4 and ipv6.
          Only the value of unisCBQoSRedirectType is next-hop,
          can be set this node and unisCBQoSRedirectIpAddress1 or unisCBQoSRedirectIpAddress2.
        "
    DEFVAL { unknown }
    ::= { unisCBQoSRedirectCfgInfoEntry 3 }

unisCBQoSRedirectIpAddress1 OBJECT-TYPE
    SYNTAX InetAddress
    MAX-ACCESS read-create
    STATUS current
    DESCRIPTION
        "IP Address.
         If the value of unisCBQoSRedirectType is not next-hop,
         zero-length string will be returned when getting.
         If the value of unisCBQoSRedirectIpAddressType is ipv6,
         this node is set necessarily.
        "
    ::= { unisCBQoSRedirectCfgInfoEntry 4 }

unisCBQoSRedirectIpAddress2 OBJECT-TYPE
    SYNTAX InetAddress
    MAX-ACCESS read-create
    STATUS current
    DESCRIPTION
        "IP Address.
         If the value of unisCBQoSRedirectType is not next-hop,
         zero-length string will be returned when getting.
         If the value of unisCBQoSRedirectIpAddressType is ipv6,
         this node is set optionally.
        "
    ::= { unisCBQoSRedirectCfgInfoEntry 5 }

unisCBQoSRedirectRowStatus OBJECT-TYPE
    SYNTAX RowStatus
    MAX-ACCESS read-create
    STATUS current
    DESCRIPTION
        "RowStatus."
    ::= { unisCBQoSRedirectCfgInfoEntry 6 }

unisCBQoSRedirectIpv6Interface1 OBJECT-TYPE
    SYNTAX Integer32
    MAX-ACCESS read-create
    STATUS current
    DESCRIPTION
        "IfIndex for ipv6 next hop .
         If and only if the value of unisCBQoSRedirectIpAddressType is ipv6
         and unisCBQoSRedirectIpAddress1 is set,
         this node can be set.
        "
    DEFVAL { 0 }
    ::= { unisCBQoSRedirectCfgInfoEntry 7 }

unisCBQoSRedirectIpv6Interface2 OBJECT-TYPE
    SYNTAX Integer32
    MAX-ACCESS read-create
    STATUS current
    DESCRIPTION
        "IfIndex for ipv6 next hop .
         If and only if the value of unisCBQoSRedirectIpAddressType is ipv6
         and unisCBQoSRedirectIpAddress2 is set,
         this node can be set.
        "
    DEFVAL { 0 }
    ::= { unisCBQoSRedirectCfgInfoEntry 8 }

unisCBQoSRedirectIfVlanID OBJECT-TYPE
    SYNTAX Integer32 (0..4094 |65535)
    MAX-ACCESS read-create
    STATUS current
    DESCRIPTION
        "VLAN-ID to tag.
         If and only if the value of unisCBQoSRedirectType is interface,
         this node can be set.
        "
    DEFVAL { 65535 }
    ::= { unisCBQoSRedirectCfgInfoEntry 9 }

--
-- nodes of unisCBQoSPriorityMapCfgInfoTable
--
unisCBQoSPriorityMapCfgInfoTable OBJECT-TYPE
    SYNTAX SEQUENCE OF UnisCBQoSPriorityMapCfgInfoEntry
    MAX-ACCESS not-accessible
    STATUS current
    DESCRIPTION
        "A table of priority map configuration information."
    ::= { unisCBQoSBehaviorObjects 16 }

unisCBQoSPriorityMapCfgInfoEntry OBJECT-TYPE
    SYNTAX UnisCBQoSPriorityMapCfgInfoEntry
    MAX-ACCESS not-accessible
    STATUS current
    DESCRIPTION
        "priority map configuration information entry."
    INDEX { unisCBQoSBehaviorIndex }
    ::= { unisCBQoSPriorityMapCfgInfoTable 1 }

UnisCBQoSPriorityMapCfgInfoEntry ::=
    SEQUENCE
    {
        unisCBQoSPriorityMapImportType
            INTEGER,
        unisCBQoSPriorityMapExportType
            INTEGER,
        unisCBQoSPriorityMapGroupIndex
            Integer32,
        unisCBQoSPriorityMapGroupName
            OCTET STRING,
        unisCBQoSPriorityMapAuto
            INTEGER,
        unisCBQoSPriorityMapRowStatus
            RowStatus
    }

unisCBQoSPriorityMapImportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Import type of map."
    DEFVAL { invalid }
    ::= { unisCBQoSPriorityMapCfgInfoEntry 1 }

unisCBQoSPriorityMapExportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Export type of map."
    DEFVAL { invalid }
    ::= { unisCBQoSPriorityMapCfgInfoEntry 2 }

unisCBQoSPriorityMapGroupIndex OBJECT-TYPE
    SYNTAX Integer32
    MAX-ACCESS read-create
    STATUS current
    DESCRIPTION
        "Index of map group.
         Map group is managed by UNIS-IFQOS2-MIB.
        "
    ::= { unisCBQoSPriorityMapCfgInfoEntry 3 }

unisCBQoSPriorityMapGroupName OBJECT-TYPE
    SYNTAX OCTET STRING (SIZE(0..31))
    MAX-ACCESS read-only
    STATUS current
    DESCRIPTION
        "Name of map group.
         Map group is managed by UNIS-IFQOS2-MIB.
        "
    ::= { unisCBQoSPriorityMapCfgInfoEntry 4 }

unisCBQoSPriorityMapAuto OBJECT-TYPE
    SYNTAX INTEGER
    {
        invalid(1),
        autoDscp(2),
        autoDot1p(3),
        autoMplsExp(4),
        autoIp(5)
    }
    MAX-ACCESS read-create
    STATUS current
    DESCRIPTION
        "Type of priority MAP."
    DEFVAL { invalid }
    ::= { unisCBQoSPriorityMapCfgInfoEntry 5 }

unisCBQoSPriorityMapRowStatus OBJECT-TYPE
    SYNTAX RowStatus
    MAX-ACCESS read-create
    STATUS current
    DESCRIPTION
        "RowStatus."
    ::= { unisCBQoSPriorityMapCfgInfoEntry 6 }

--
-- nodes of unisCBQoSMirrorCfgInfoTable
--
unisCBQoSMirrorCfgInfoTable OBJECT-TYPE
    SYNTAX SEQUENCE OF UnisCBQoSMirrorCfgInfoEntry
    MAX-ACCESS not-accessible
    STATUS current
    DESCRIPTION
        "A table of flow mirror configuration information."
    ::= { unisCBQoSBehaviorObjects 17 }

unisCBQoSMirrorCfgInfoEntry OBJECT-TYPE
    SYNTAX UnisCBQoSMirrorCfgInfoEntry
    MAX-ACCESS not-accessible
    STATUS current
    DESCRIPTION
        "Flow mirror configuration information entry."
    INDEX { unisCBQoSBehaviorIndex }
    ::= { unisCBQoSMirrorCfgInfoTable 1 }

UnisCBQoSMirrorCfgInfoEntry ::=
    SEQUENCE
    {
        unisCBQoSMirrorType
            INTEGER,
        unisCBQoSMirrorIfIndex
            OCTET STRING,
        unisCBQoSMirrorVlanID
            Integer32,
        unisCBQoSMirrorRowStatus
            RowStatus
    }

unisCBQoSMirrorType OBJECT-TYPE
    SYNTAX INTEGER
    {
        interface(1),
        cpu(2),
        vlan(3)
    }
    MAX-ACCESS read-create
    STATUS current
    DESCRIPTION
        "Type of flow mirror."
    ::= { unisCBQoSMirrorCfgInfoEntry 1 }

unisCBQoSMirrorIfIndex OBJECT-TYPE
    SYNTAX OCTET STRING (SIZE (0..255))
    MAX-ACCESS read-create
    STATUS current
    DESCRIPTION
        "IfIndex of destination interface.
         Only the value of unisCBQoSMirrorType is interface,
         can be set this node.
         For example: 1#11#111#1111 means the flow mirror
         destination ifindex is 1,11,111 and 1111.
         '#' is list separator for all IfIndex value.
        "
    ::= { unisCBQoSMirrorCfgInfoEntry 2 }

unisCBQoSMirrorVlanID OBJECT-TYPE
    SYNTAX Integer32 (0..4094)
    MAX-ACCESS read-create
    STATUS current
    DESCRIPTION
        "Destination vlan of flow mirror,
         Only the value of unisCBQoSMirrorType is vlan,
         can be set this node.
        "
    ::= { unisCBQoSMirrorCfgInfoEntry 3 }

unisCBQoSMirrorRowStatus OBJECT-TYPE
    SYNTAX RowStatus
    MAX-ACCESS read-create
    STATUS current
    DESCRIPTION
        "RowStatus."
    ::= { unisCBQoSMirrorCfgInfoEntry 4 }

--
-- nodes of unisCBQoSNestCfgInfoTable
--
unisCBQoSNestCfgInfoTable OBJECT-TYPE
    SYNTAX SEQUENCE OF UnisCBQoSNestCfgInfoEntry
    MAX-ACCESS not-accessible
    STATUS current
    DESCRIPTION
        "Insert a service VLAN tag or customer VLAN tag into a packet.
        A VLAN tag contains the VLAN ID field and the 802.1p priority
        field.  Both the service VLAN ID and the customer VLAN ID can
        not be set at the same time.  One of them must be set.  The
        802.1p priority of the service VLAN tag and that of the
        customer VLAN tag can be set optionally.  However, both of
        them can not be set at the same time.  The new setting
        overwrites the previous one."
    ::= { unisCBQoSBehaviorObjects 18 }

unisCBQoSNestCfgInfoEntry OBJECT-TYPE
    SYNTAX UnisCBQoSNestCfgInfoEntry
    MAX-ACCESS not-accessible
    STATUS current
    DESCRIPTION
        "VLAN nesting table entry."
    INDEX { unisCBQoSBehaviorIndex }
    ::= { unisCBQoSNestCfgInfoTable 1 }

UnisCBQoSNestCfgInfoEntry ::=
    SEQUENCE
    {
        unisCBQoSNestServiceVlanID
            Integer32,
        unisCBQoSNestServiceDot1pValue
            Integer32,
        unisCBQoSNestCustomerVlanID
            Integer32,
        unisCBQoSNestCustomerDot1pValue
            Integer32,
        unisCBQoSNestRowStatus
            RowStatus
    }

unisCBQoSNestServiceVlanID OBJECT-TYPE
    SYNTAX Integer32 (1..4094|65535)
    MAX-ACCESS read-create
    STATUS current
    DESCRIPTION
        "VLAN ID of the service VLAN tag to be inserted.  If the
        customer VLAN tag has been configured, 65535 is returned
        for the service VLAN ID.  The service VLAN ID can not be
        set to 65535."
    ::= { unisCBQoSNestCfgInfoEntry 1 }

unisCBQoSNestServiceDot1pValue OBJECT-TYPE
    SYNTAX Integer32 (0..7|65535)
    MAX-ACCESS read-create
    STATUS current
    DESCRIPTION
        "802.1p priority value in the service VLAN tag to be inserted.
        If the 802.1p priority is not set, 65535 is returned.  The
        802.1p priority value can not be set to 65535."
    ::= { unisCBQoSNestCfgInfoEntry 2 }

unisCBQoSNestCustomerVlanID OBJECT-TYPE
    SYNTAX Integer32 (1..4094|65535)
    MAX-ACCESS read-create
    STATUS current
    DESCRIPTION
        "VLAN ID of the customer VLAN tag to be inserted.  If the
        service VLAN tag has been configured, 65535 is returned for
        the customer VLAN ID.  The customer VLAN ID can not be set
        to 65535."
    ::= { unisCBQoSNestCfgInfoEntry 3 }

unisCBQoSNestCustomerDot1pValue OBJECT-TYPE
    SYNTAX Integer32 (0..7|65535)
    MAX-ACCESS read-create
    STATUS current
    DESCRIPTION
        "802.1p priority value in the customer VLAN tag to be inserted.
        If the 802.1p priority is not set, 65535 is returned.  The
        802.1p priority value can not be set to 65535."
    ::= { unisCBQoSNestCfgInfoEntry 4 }

unisCBQoSNestRowStatus OBJECT-TYPE
    SYNTAX RowStatus
    MAX-ACCESS read-create
    STATUS current
    DESCRIPTION
        "RowStatus"
    ::= { unisCBQoSNestCfgInfoEntry 5 }

-- Nest Policy

unisCBQoSNestPolicyCfgInfoTable OBJECT-TYPE
    SYNTAX SEQUENCE OF UnisCBQoSNestPolicyCfgInfoEntry
    MAX-ACCESS not-accessible
    STATUS current
    DESCRIPTION
        "This table is used for configuring nest policy."
    ::= { unisCBQoSBehaviorObjects 19 }

unisCBQoSNestPolicyCfgInfoEntry OBJECT-TYPE
    SYNTAX UnisCBQoSNestPolicyCfgInfoEntry
    MAX-ACCESS not-accessible
    STATUS current
    DESCRIPTION
        "Nest policy configuration entry."
    INDEX { unisCBQoSBehaviorIndex }
    ::= { unisCBQoSNestPolicyCfgInfoTable 1 }

UnisCBQoSNestPolicyCfgInfoEntry ::=
    SEQUENCE
    {
        unisCBQoSNestPolicyName
            OCTET STRING,
        unisCBQoSNestPolicyRowStatus
            RowStatus
    }

unisCBQoSNestPolicyName OBJECT-TYPE
    SYNTAX OCTET STRING (SIZE(1..31))
    MAX-ACCESS read-create
    STATUS current
    DESCRIPTION
        "Name of the nested policy."
    ::= { unisCBQoSNestPolicyCfgInfoEntry 1 }

unisCBQoSNestPolicyRowStatus OBJECT-TYPE
    SYNTAX RowStatus
    MAX-ACCESS read-create
    STATUS current
    DESCRIPTION
        "RowStatus"
    ::= { unisCBQoSNestPolicyCfgInfoEntry 2 }

--
-- nodes of unisCBQoSMirrorIfCfgInfoTable
--
unisCBQoSMirrorIfCfgInfoTable OBJECT-TYPE
    SYNTAX SEQUENCE OF UnisCBQoSMirrorIfCfgInfoEntry
    MAX-ACCESS not-accessible
    STATUS current
    DESCRIPTION
        "A table of flow mirroring to interface configuration information."
    ::= { unisCBQoSBehaviorObjects 20 }

unisCBQoSMirrorIfCfgInfoEntry OBJECT-TYPE
    SYNTAX UnisCBQoSMirrorIfCfgInfoEntry
    MAX-ACCESS not-accessible
    STATUS current
    DESCRIPTION
        "Flow mirroring to interface configuration information entry."
    INDEX { unisCBQoSBehaviorIndex, unisCBQoSMirrorIfMainIfIndex }
    ::= { unisCBQoSMirrorIfCfgInfoTable 1 }

UnisCBQoSMirrorIfCfgInfoEntry ::=
    SEQUENCE
    {
        unisCBQoSMirrorIfMainIfIndex
            Integer32,
        unisCBQoSMirrorIfMainIfStatus
            INTEGER,
        unisCBQoSMirrorIfBackupIfIndex
            Integer32,
        unisCBQoSMirrorIfBackupIfStatus
            INTEGER,
        unisCBQoSMirrorIfRowStatus
            RowStatus
    }

unisCBQoSMirrorIfMainIfIndex OBJECT-TYPE
    SYNTAX Integer32
    MAX-ACCESS not-accessible
    STATUS current
    DESCRIPTION
        "IfIndex of mirror interface."
    ::= { unisCBQoSMirrorIfCfgInfoEntry 1 }

unisCBQoSMirrorIfMainIfStatus OBJECT-TYPE
    SYNTAX INTEGER
    {
        inactive(1),
        active(2)
    }
    MAX-ACCESS read-only
    STATUS current
    DESCRIPTION
        "Status of main interface."
    DEFVAL {active}
    ::= { unisCBQoSMirrorIfCfgInfoEntry 2 }

unisCBQoSMirrorIfBackupIfIndex OBJECT-TYPE
    SYNTAX Integer32
    MAX-ACCESS read-create
    STATUS current
    DESCRIPTION
        "IfIndex of backup mirror interface."
    ::= { unisCBQoSMirrorIfCfgInfoEntry 3 }

unisCBQoSMirrorIfBackupIfStatus OBJECT-TYPE
    SYNTAX INTEGER
    {
        inactive(1),
        active(2)
    }
    MAX-ACCESS read-only
    STATUS current
    DESCRIPTION
        "Status of backup interface."
    DEFVAL {active}
    ::= { unisCBQoSMirrorIfCfgInfoEntry 4 }

unisCBQoSMirrorIfRowStatus OBJECT-TYPE
    SYNTAX RowStatus
    MAX-ACCESS read-create
    STATUS current
    DESCRIPTION
        "RowStatus."
    ::= { unisCBQoSMirrorIfCfgInfoEntry 5 }

--
-- nodes of unisCBQoSColoredRemarkCfgTable
--
unisCBQoSColoredRemarkCfgTable OBJECT-TYPE
    SYNTAX SEQUENCE OF UnisCBQoSColoredRemarkCfgEntry
    MAX-ACCESS not-accessible
    STATUS current
    DESCRIPTION
        "A table of colored remarking feature configuration information."
    ::= { unisCBQoSBehaviorObjects 21 }

unisCBQoSColoredRemarkCfgEntry OBJECT-TYPE
    SYNTAX UnisCBQoSColoredRemarkCfgEntry
    MAX-ACCESS not-accessible
    STATUS current
    DESCRIPTION
        "Colored remarking configuration information entry."
    INDEX { unisCBQoSBehaviorIndex, unisCBQoSColoredRemarkType, unisCBQoSColoredRemarkColor }
    ::= { unisCBQoSColoredRemarkCfgTable 1 }

UnisCBQoSColoredRemarkCfgEntry ::=
    SEQUENCE
    {
        unisCBQoSColoredRemarkType
            RemarkType,
        unisCBQoSColoredRemarkColor
            INTEGER,
        unisCBQoSColoredRemarkValue
            Integer32,
        unisCBQoSColoredRemarkRowStatus
            RowStatus
    }

unisCBQoSColoredRemarkType OBJECT-TYPE
    SYNTAX RemarkType
    MAX-ACCESS not-accessible
    STATUS current
    DESCRIPTION
        "Remark type."
    ::= { unisCBQoSColoredRemarkCfgEntry 1 }

unisCBQoSColoredRemarkColor OBJECT-TYPE
    SYNTAX INTEGER
    {
        green(1),
        yellow(2),
        red(3)
    }
    MAX-ACCESS not-accessible
    STATUS current
    DESCRIPTION
        "Remark color."
    ::= { unisCBQoSColoredRemarkCfgEntry 2 }

unisCBQoSColoredRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { unisCBQoSColoredRemarkCfgEntry 3 }

unisCBQoSColoredRemarkRowStatus OBJECT-TYPE
    SYNTAX RowStatus
    MAX-ACCESS read-create
    STATUS current
    DESCRIPTION
        "RowStatus"
    ::= { unisCBQoSColoredRemarkCfgEntry 4 }

--
-- nodes of unisCBQoSPrimapCfgInfoTable
--
unisCBQoSPrimapCfgInfoTable OBJECT-TYPE
    SYNTAX SEQUENCE OF UnisCBQoSPrimapCfgInfoEntry
    MAX-ACCESS not-accessible
    STATUS current
    DESCRIPTION
        "A table of referencing priority map configuration information."
    ::= { unisCBQoSBehaviorObjects 22 }

unisCBQoSPrimapCfgInfoEntry OBJECT-TYPE
    SYNTAX UnisCBQoSPrimapCfgInfoEntry
    MAX-ACCESS not-accessible
    STATUS current
    DESCRIPTION
        "Referencing priority map configuration information entry."
    INDEX { unisCBQoSBehaviorIndex, unisCBQoSPrimapColorType, unisCBQoSPrePriMapTableType }
    ::= { unisCBQoSPrimapCfgInfoTable 1 }

UnisCBQoSPrimapCfgInfoEntry ::=
    SEQUENCE
    {
        unisCBQoSPrimapColorType
            INTEGER,
        unisCBQoSPrePriMapTableType
            INTEGER,
        unisCBQoSPrimapRowStatus
            RowStatus
    }

unisCBQoSPrimapColorType OBJECT-TYPE
    SYNTAX INTEGER
    {
        noColorMap(1),
        colorMap(2)
    }
    MAX-ACCESS not-accessible
    STATUS current
    DESCRIPTION
        "Color type of priority map."
    ::= { unisCBQoSPrimapCfgInfoEntry 1 }

unisCBQoSPrePriMapTableType OBJECT-TYPE
    SYNTAX INTEGER
    {
        dot1pToLp(1),
        dot1pToDp(2),
        expToLp(3),
        dscpToLp(4),
        expToDp(5),
        dscpToDp(6),
        dscpToDot1p(7),
        dot1pToDscp(8),
        dscpToDscp(9),
        dscpToExp(10),
        expToDscp(11),
        expToDot1p(12),
        expToExp(13),
        lpToDot1p(14),
        dot1pToRpr(15),
        dscpToRpr(16),
        expToRpr(17),
        ippreToRpr(18),
        upToDot1p(19),
        upToDscp(20),
        upToExp(21),
        upToDp(22),
        upToLp(23),
        upToRpr(24),
        upToFc(25),
        lpTodscp(26),
        dot11eToLp(27),
        lpToDot11e(28),
        lpToLp(29),
        dot1pToExp(30),
        lpToExp(31),
        lpToDp(32),
        upToUp(33),
        dot1pToDot1p(34)
    }
    MAX-ACCESS not-accessible
    STATUS current
    DESCRIPTION
        "The type of pre-defined priority mapping table."
    ::= { unisCBQoSPrimapCfgInfoEntry 2 }

unisCBQoSPrimapRowStatus OBJECT-TYPE
    SYNTAX RowStatus
    MAX-ACCESS read-create
    STATUS current
    DESCRIPTION
        "RowStatus"
    ::= { unisCBQoSPrimapCfgInfoEntry 3 }

--
-- nodes of unisCBQoSColorMapDpCfgInfoTable
--
unisCBQoSColorMapDpCfgInfoTable OBJECT-TYPE
    SYNTAX SEQUENCE OF UnisCBQoSColorMapDpCfgInfoEntry
    MAX-ACCESS not-accessible
    STATUS current
    DESCRIPTION
        "A table of referencing color-map-DP action configuration information."
    ::= { unisCBQoSBehaviorObjects 23 }

unisCBQoSColorMapDpCfgInfoEntry OBJECT-TYPE
    SYNTAX UnisCBQoSColorMapDpCfgInfoEntry
    MAX-ACCESS not-accessible
    STATUS current
    DESCRIPTION
        "Referencing color-map-DP action configuration information entry."
    INDEX { unisCBQoSBehaviorIndex }
    ::= { unisCBQoSColorMapDpCfgInfoTable 1 }

UnisCBQoSColorMapDpCfgInfoEntry ::=
    SEQUENCE
    {
        unisCBQoSColorMapDpEnable
            TruthValue,
        unisCBQoSColorMapDpRowStatus
            RowStatus
    }

unisCBQoSColorMapDpEnable OBJECT-TYPE
    SYNTAX TruthValue
    MAX-ACCESS read-create
    STATUS current
    DESCRIPTION
        "Color-map-DP enable status."
    ::= { unisCBQoSColorMapDpCfgInfoEntry 1 }

unisCBQoSColorMapDpRowStatus OBJECT-TYPE
    SYNTAX RowStatus
    MAX-ACCESS read-create
    STATUS current
    DESCRIPTION
        "RowStatus"
    ::= { unisCBQoSColorMapDpCfgInfoEntry 2 }

-- unisCBQoSPolicyObjects

unisCBQoSPolicyObjects OBJECT IDENTIFIER ::= { unisCBQoSObjects 3 }

-- Traffic Policy Next Index

unisCBQoSPolicyIndexNext OBJECT-TYPE
    SYNTAX Integer32
    MAX-ACCESS read-only
    STATUS current
    DESCRIPTION
        "This object contains an appropriate value to be used for
         unisCBQoSPolicyIndex when creating rows in the
         unisCBQoSPolicyCfgInfoTable."
    ::= { unisCBQoSPolicyObjects 1 }

-- Traffic Policy

unisCBQoSPolicyCfgInfoTable OBJECT-TYPE
    SYNTAX SEQUENCE OF UnisCBQoSPolicyCfgInfoEntry
    MAX-ACCESS not-accessible
    STATUS current
    DESCRIPTION
        "A table of QoS policy configuration information."
    ::= { unisCBQoSPolicyObjects 2 }

unisCBQoSPolicyCfgInfoEntry OBJECT-TYPE
    SYNTAX UnisCBQoSPolicyCfgInfoEntry
    MAX-ACCESS not-accessible
    STATUS current
    DESCRIPTION
        "Traffic policy configuration information entry."
    INDEX { unisCBQoSPolicyIndex }
    ::= { unisCBQoSPolicyCfgInfoTable 1 }

UnisCBQoSPolicyCfgInfoEntry ::=
    SEQUENCE
    {
        unisCBQoSPolicyIndex
            Integer32,
        unisCBQoSPolicyName
            OCTET STRING,
        unisCBQoSPolicyClassCount
            Integer32,
        unisCBQoSPolicyConfigMode
            INTEGER,
        unisCBQoSPolicyType
            INTEGER,
        unisCBQoSPolicyClassNextIndex
            Integer32,
        unisCBQoSPolicyRowStatus
            RowStatus
    }

unisCBQoSPolicyIndex OBJECT-TYPE
    SYNTAX Integer32
    MAX-ACCESS not-accessible
    STATUS current
    DESCRIPTION
        "Index of Traffic Policy."
    ::= { unisCBQoSPolicyCfgInfoEntry 1 }

unisCBQoSPolicyName OBJECT-TYPE
    SYNTAX OCTET STRING (SIZE (1..31))
    MAX-ACCESS read-create
    STATUS current
    DESCRIPTION
        "Name of Traffic Policy."
    ::= { unisCBQoSPolicyCfgInfoEntry 2 }

unisCBQoSPolicyClassCount OBJECT-TYPE
    SYNTAX Integer32
    MAX-ACCESS read-only
    STATUS current
    DESCRIPTION
        "The counter of policy classes of policy."
    ::= { unisCBQoSPolicyCfgInfoEntry 3 }

unisCBQoSPolicyConfigMode OBJECT-TYPE
    SYNTAX INTEGER
    {
        unavailable(0),
        config(1),
        auto(2)
    }
    MAX-ACCESS read-create
    STATUS current
    DESCRIPTION
        "Configuration mode of Traffic Policy.
         Only hardware QoS support this node.
         'unavailable' is returned only when getting value from software QoS.
         'unavailable' can't be set."
    DEFVAL {config}
    ::= { unisCBQoSPolicyCfgInfoEntry 4 }

unisCBQoSPolicyType OBJECT-TYPE
    SYNTAX INTEGER
    {
        systemDefined(1),
        userDefined(2)
    }
    MAX-ACCESS read-only
    STATUS current
    DESCRIPTION
        "Type of policy."
    ::= { unisCBQoSPolicyCfgInfoEntry 5 }

unisCBQoSPolicyClassNextIndex OBJECT-TYPE
    SYNTAX Integer32
    MAX-ACCESS read-only
    STATUS current
    DESCRIPTION
        "This object contains an appropriate value to be used for
         unisCBQoSPolicyClassIndex when creating rows in the
         unisCBQoSPolicyClassCfgInfoTable.
        "
    ::= { unisCBQoSPolicyCfgInfoEntry 6 }

unisCBQoSPolicyRowStatus OBJECT-TYPE
    SYNTAX RowStatus
    MAX-ACCESS read-create
    STATUS current
    DESCRIPTION
        "RowStatus."
    ::= { unisCBQoSPolicyCfgInfoEntry 7 }

-- Classifier-Behavior in QoS policy

unisCBQoSPolicyClassCfgInfoTable OBJECT-TYPE
    SYNTAX SEQUENCE OF UnisCBQoSPolicyClassCfgInfoEntry
    MAX-ACCESS not-accessible
    STATUS current
    DESCRIPTION
        "A table of QoS Policy classifier-behavior configuration information."
    ::= { unisCBQoSPolicyObjects 3 }

unisCBQoSPolicyClassCfgInfoEntry OBJECT-TYPE
    SYNTAX UnisCBQoSPolicyClassCfgInfoEntry
    MAX-ACCESS not-accessible
    STATUS current
    DESCRIPTION
        "Traffic policy classifier-behavior configuration information entry."
    INDEX { unisCBQoSPolicyIndex, unisCBQoSPolicyClassIndex }
    ::= { unisCBQoSPolicyClassCfgInfoTable 1 }

UnisCBQoSPolicyClassCfgInfoEntry ::=
    SEQUENCE
    {
        unisCBQoSPolicyClassIndex
            Integer32,
        unisCBQoSPolicyClassClassifierIndex
            Integer32,
        unisCBQoSPolicyClassClassifierName
            OCTET STRING,
        unisCBQoSPolicyClassBehaviorIndex
            Integer32,
        unisCBQoSPolicyClassBehaviorName
            OCTET STRING,
        unisCBQoSPolicyClassPrecedence
            Integer32,
        unisCBQoSPolicyClassRowStatus
            RowStatus,
        unisCBQoSPolicyClassMode
            INTEGER,
        unisCBQoSPolicyClassCfgOrder
            Integer32
    }

unisCBQoSPolicyClassIndex OBJECT-TYPE
    SYNTAX Integer32
    MAX-ACCESS not-accessible
    STATUS current
    DESCRIPTION
        "PolicyClass Index in a QoS policy."
    ::= { unisCBQoSPolicyClassCfgInfoEntry 1 }

unisCBQoSPolicyClassClassifierIndex OBJECT-TYPE
    SYNTAX Integer32
    MAX-ACCESS read-create
    STATUS current
    DESCRIPTION
        "Index of classifier applied by a policy.
         It should exist in unisCBQoSClassifierCfgInfoTable."
    ::= { unisCBQoSPolicyClassCfgInfoEntry 2 }

unisCBQoSPolicyClassClassifierName OBJECT-TYPE
    SYNTAX OCTET STRING (SIZE (1..31))
    MAX-ACCESS read-only
    STATUS current
    DESCRIPTION
        "Name of classifier applied by a policy.
         It is corresponding to unisCBQoSPolicyClassClassifierIndex."
    ::= { unisCBQoSPolicyClassCfgInfoEntry 3 }

unisCBQoSPolicyClassBehaviorIndex OBJECT-TYPE
    SYNTAX Integer32
    MAX-ACCESS read-create
    STATUS current
    DESCRIPTION
        "Index of Behavior applied by a policy.
         It should exist in unisCBQoSBehaviorCfgInfoTable."
    ::= { unisCBQoSPolicyClassCfgInfoEntry 4 }

unisCBQoSPolicyClassBehaviorName OBJECT-TYPE
    SYNTAX OCTET STRING (SIZE (1..31))
    MAX-ACCESS read-only
    STATUS current
    DESCRIPTION
        "Name of Behavior applied by a policy.
         It is corresponding to unisCBQoSPolicyClassBehaviorIndex."
    ::= { unisCBQoSPolicyClassCfgInfoEntry 5 }

unisCBQoSPolicyClassPrecedence OBJECT-TYPE
    SYNTAX Integer32 (0..16383|2147483647)
    MAX-ACCESS read-create
    STATUS current
    DESCRIPTION
        "The Precedence of the class in the policy.
         Only hardware QoS support this node.
         2147483647 is returned only when getting value from software QoS.
         2147483647 can't be set."
    ::= { unisCBQoSPolicyClassCfgInfoEntry 6 }

unisCBQoSPolicyClassRowStatus OBJECT-TYPE
    SYNTAX RowStatus
    MAX-ACCESS read-create
    STATUS current
    DESCRIPTION
        "RowStatus."
    ::= { unisCBQoSPolicyClassCfgInfoEntry 7 }

unisCBQoSPolicyClassMode OBJECT-TYPE
    SYNTAX INTEGER
    {
        modeNo(1),
        modeDot1q(2),
        modeQppb(3),
        modeIpSourceGuard(4),
        modeVoiceVlan(5),
        modeDCBX(6)
    }
    MAX-ACCESS read-create
    STATUS current
    DESCRIPTION
        "Set the mode of the classifier-behavior association.  The
        default mode modeNo is a normal mode.
        modeDot1q indicates that the association is used for VLAN mapping.
        modeQppb indicates that the association is used for BGP routing policy.
        modeIpSourceGuard indicates that the association is used for packets
        undergo IP source guard.
        modeVoiceVlan indicates that the association is used for voice data
        packets.
        modeDCBX indicates that the association is used for DCBX.
        "
    DEFVAL {modeNo}
    ::= { unisCBQoSPolicyClassCfgInfoEntry 8 }

unisCBQoSPolicyClassCfgOrder OBJECT-TYPE
    SYNTAX Integer32
    MAX-ACCESS read-only
    STATUS current
    DESCRIPTION
        "A QoS policy contains multiple classifier-behavior
        associations.  A node indicates the configuration order of
        the corresponding classifier-behavior association."
    ::= { unisCBQoSPolicyClassCfgInfoEntry 9 }

-- unisCBQoSApplyPolicyObjects

unisCBQoSApplyPolicyObjects OBJECT IDENTIFIER ::= { unisCBQoSObjects 4 }

-- Policy Instance on interface Table

unisCBQoSIfApplyPolicyTable OBJECT-TYPE
    SYNTAX SEQUENCE OF UnisCBQoSIfApplyPolicyEntry
    MAX-ACCESS not-accessible
    STATUS current
    DESCRIPTION
        "A table of QoS policy instance."
    ::= { unisCBQoSApplyPolicyObjects 1 }

unisCBQoSIfApplyPolicyEntry OBJECT-TYPE
    SYNTAX UnisCBQoSIfApplyPolicyEntry
    MAX-ACCESS not-accessible
    STATUS current
    DESCRIPTION
        "Policy applied on interface Configuration Information Entry."
    INDEX { unisCBQoSIfApplyPolicyIfIndex, unisCBQoSIfApplyPolicyDirection }
    ::= { unisCBQoSIfApplyPolicyTable 1 }

UnisCBQoSIfApplyPolicyEntry ::=
    SEQUENCE
    {
        unisCBQoSIfApplyPolicyIfIndex
            Integer32,
        unisCBQoSIfApplyPolicyDirection
            DirectionType,
        unisCBQoSIfApplyPolicyName
            OCTET STRING,
        unisCBQoSIfApplyPolicyEnableDynamic
            INTEGER,
        unisCBQoSIfApplyPolicyRowStatus
            RowStatus,
        unisCBQoSIfApplyPolicyStatus
            INTEGER
    }

unisCBQoSIfApplyPolicyIfIndex OBJECT-TYPE
    SYNTAX Integer32
    MAX-ACCESS accessible-for-notify
    STATUS current
    DESCRIPTION
        "Interface Index, equal to ifIndex."
    ::= { unisCBQoSIfApplyPolicyEntry 1 }

unisCBQoSIfApplyPolicyDirection OBJECT-TYPE
    SYNTAX DirectionType
    MAX-ACCESS accessible-for-notify
    STATUS current
    DESCRIPTION
        "Policy direction:
         inbound (1)
         outbound (2)
        "
    ::= { unisCBQoSIfApplyPolicyEntry 2 }

unisCBQoSIfApplyPolicyName OBJECT-TYPE
    SYNTAX OCTET STRING (SIZE (1..31))
    MAX-ACCESS read-create
    STATUS current
    DESCRIPTION
        "Name of Traffic Policy."
    ::= { unisCBQoSIfApplyPolicyEntry 3 }

unisCBQoSIfApplyPolicyEnableDynamic OBJECT-TYPE
    SYNTAX INTEGER
    {
        unavailable(1),
        true(2),
        false(3)
    }
    MAX-ACCESS read-create
    STATUS current
    DESCRIPTION
        "If the value of it is specified 'true',Enable dynamic qos policy.
         'unavailable' is returned if device don't support dynamic QoS.
         'unavailable' can't be set.
        "
    ::= { unisCBQoSIfApplyPolicyEntry 4 }

unisCBQoSIfApplyPolicyRowStatus OBJECT-TYPE
    SYNTAX RowStatus
    MAX-ACCESS read-create
    STATUS current
    DESCRIPTION
        "RowStatus."
    ::= { unisCBQoSIfApplyPolicyEntry 5 }

unisCBQoSIfApplyPolicyStatus OBJECT-TYPE
    SYNTAX INTEGER
    {
        proccessing(1),
        success(2),
        partialItemFailed(3)
    }
    MAX-ACCESS read-only
    STATUS current
    DESCRIPTION
        "Status of policy applied on interface."
    ::= { unisCBQoSIfApplyPolicyEntry 6 }

-- Policy Instance on ATM PVC Table

unisCBQoSAtmPvcApplyPolicyTable OBJECT-TYPE
    SYNTAX SEQUENCE OF UnisCBQoSAtmPvcApplyPolicyEntry
    MAX-ACCESS not-accessible
    STATUS current
    DESCRIPTION
        "A table of QoS policy instance."
    ::= { unisCBQoSApplyPolicyObjects 2 }

unisCBQoSAtmPvcApplyPolicyEntry OBJECT-TYPE
    SYNTAX UnisCBQoSAtmPvcApplyPolicyEntry
    MAX-ACCESS not-accessible
    STATUS current
    DESCRIPTION
        "Policy applied on ATM PVC Configuration Information Entry."
    INDEX { unisCBQoSAtmPvcApplyPolicyIfIndex,
            unisCBQoSAtmPvcApplyPolicyVPI,
            unisCBQoSAtmPvcApplyPolicyVCI,
            unisCBQoSAtmPvcApplyPolicyDirection }
    ::= { unisCBQoSAtmPvcApplyPolicyTable 1 }

UnisCBQoSAtmPvcApplyPolicyEntry ::=
    SEQUENCE
    {
        unisCBQoSAtmPvcApplyPolicyIfIndex
            Integer32,
        unisCBQoSAtmPvcApplyPolicyVPI
            Integer32,
        unisCBQoSAtmPvcApplyPolicyVCI
            Integer32,
        unisCBQoSAtmPvcApplyPolicyDirection
            DirectionType,
        unisCBQoSAtmPvcApplyPolicyName
            OCTET STRING,
        unisCBQoSAtmPvcApplyPolicyRowStatus
            RowStatus
    }

unisCBQoSAtmPvcApplyPolicyIfIndex OBJECT-TYPE
    SYNTAX Integer32
    MAX-ACCESS not-accessible
    STATUS current
    DESCRIPTION
        "ATM Interface Index, equal to ifIndex."
    ::= { unisCBQoSAtmPvcApplyPolicyEntry 1 }

unisCBQoSAtmPvcApplyPolicyVPI OBJECT-TYPE
    SYNTAX Integer32
    MAX-ACCESS not-accessible
    STATUS current
    DESCRIPTION
        "VPI value of ATM Interface."
    ::= { unisCBQoSAtmPvcApplyPolicyEntry 2 }

unisCBQoSAtmPvcApplyPolicyVCI OBJECT-TYPE
    SYNTAX Integer32
    MAX-ACCESS not-accessible
    STATUS current
    DESCRIPTION
        "VCI value of ATM Interface."
    ::= { unisCBQoSAtmPvcApplyPolicyEntry 3 }

unisCBQoSAtmPvcApplyPolicyDirection OBJECT-TYPE
    SYNTAX DirectionType
    MAX-ACCESS not-accessible
    STATUS current
    DESCRIPTION
        "Policy direction:
         inbound (1)
         outbound (2)"
    ::= { unisCBQoSAtmPvcApplyPolicyEntry 4 }

unisCBQoSAtmPvcApplyPolicyName OBJECT-TYPE
    SYNTAX OCTET STRING (SIZE (1..31))
    MAX-ACCESS read-create
    STATUS current
    DESCRIPTION
        "Name of Traffic Policy."
    ::= { unisCBQoSAtmPvcApplyPolicyEntry 5 }

unisCBQoSAtmPvcApplyPolicyRowStatus OBJECT-TYPE
    SYNTAX RowStatus
    MAX-ACCESS read-create
    STATUS current
    DESCRIPTION
        "RowStatus"
    ::= { unisCBQoSAtmPvcApplyPolicyEntry 6 }

-- Policy Instance on VLAN Table

unisCBQoSVlanApplyPolicyTable OBJECT-TYPE
    SYNTAX SEQUENCE OF UnisCBQoSVlanApplyPolicyEntry
    MAX-ACCESS not-accessible
    STATUS current
    DESCRIPTION
        "A table of QoS policy instance."
    ::= { unisCBQoSApplyPolicyObjects 3 }

unisCBQoSVlanApplyPolicyEntry OBJECT-TYPE
    SYNTAX UnisCBQoSVlanApplyPolicyEntry
    MAX-ACCESS not-accessible
    STATUS current
    DESCRIPTION
        "Policy applied on Ethernet VLAN Configuration Information Entry."
    INDEX { unisCBQoSVlanApplyPolicyVlanid,
            unisCBQoSVlanApplyPolicyDirection }
    ::= { unisCBQoSVlanApplyPolicyTable 1 }

UnisCBQoSVlanApplyPolicyEntry ::=
    SEQUENCE
    {
        unisCBQoSVlanApplyPolicyVlanid
            Integer32,
        unisCBQoSVlanApplyPolicyDirection
            DirectionType,
        unisCBQoSVlanApplyPolicyName
            OCTET STRING,
        unisCBQoSVlanApplyPriority
            Integer32,
        unisCBQoSVlanApplyPolicyRowStatus
            RowStatus,
        unisCBQoSVlanApplyPolicyStatus
            INTEGER
    }

unisCBQoSVlanApplyPolicyVlanid OBJECT-TYPE
    SYNTAX Integer32
    MAX-ACCESS accessible-for-notify
    STATUS current
    DESCRIPTION
        "Vlan of Ethernet Interface."
    ::= { unisCBQoSVlanApplyPolicyEntry 1 }

unisCBQoSVlanApplyPolicyDirection OBJECT-TYPE
    SYNTAX DirectionType
    MAX-ACCESS accessible-for-notify
    STATUS current
    DESCRIPTION
        "Policy direction:
         inbound (1)
         outbound (2)"
    ::= { unisCBQoSVlanApplyPolicyEntry 2 }

unisCBQoSVlanApplyPolicyName OBJECT-TYPE
    SYNTAX OCTET STRING (SIZE (0..31))
    MAX-ACCESS read-create
    STATUS current
    DESCRIPTION
        "Name of Traffic Policy."
    ::= { unisCBQoSVlanApplyPolicyEntry 3 }

unisCBQoSVlanApplyPriority OBJECT-TYPE
    SYNTAX Integer32 (0..4095)
    MAX-ACCESS read-create
    STATUS current
    DESCRIPTION
        "The priority of policy."
    ::= { unisCBQoSVlanApplyPolicyEntry 4 }

unisCBQoSVlanApplyPolicyRowStatus OBJECT-TYPE
    SYNTAX RowStatus
    MAX-ACCESS read-create
    STATUS current
    DESCRIPTION
        "RowStatus."
    ::= { unisCBQoSVlanApplyPolicyEntry 5 }

unisCBQoSVlanApplyPolicyStatus OBJECT-TYPE
    SYNTAX INTEGER
    {
        proccessing(1),
        success(2),
        partialItemFailed(3)
    }
    MAX-ACCESS read-only
    STATUS current
    DESCRIPTION
        "Status of policy applied on VLAN."
    ::= { unisCBQoSVlanApplyPolicyEntry 6 }

-- Policy Instance on FR class Table

unisCBQoSFrClassApplyPolicyTable OBJECT-TYPE
    SYNTAX SEQUENCE OF UnisCBQoSFrClassApplyPolicyEntry
    MAX-ACCESS not-accessible
    STATUS current
    DESCRIPTION
        "A table of QoS policy instance."
    ::= { unisCBQoSApplyPolicyObjects 4 }

unisCBQoSFrClassApplyPolicyEntry OBJECT-TYPE
    SYNTAX UnisCBQoSFrClassApplyPolicyEntry
    MAX-ACCESS not-accessible
    STATUS current
    DESCRIPTION
        "Policy applied on FR class Configuration Information Entry."
    INDEX { unisCBQoSFrClassApplyPolicyFrClassName,
            unisCBQoSFrClassApplyPolicyDirection }
    ::= { unisCBQoSFrClassApplyPolicyTable 1 }

UnisCBQoSFrClassApplyPolicyEntry ::=
    SEQUENCE
    {
        unisCBQoSFrClassApplyPolicyFrClassName
            OCTET STRING,
        unisCBQoSFrClassApplyPolicyDirection
            DirectionType,
        unisCBQoSFrClassApplyPolicyName
            OCTET STRING,
        unisCBQoSFrClassApplyPolicyRowStatus
            RowStatus
    }

unisCBQoSFrClassApplyPolicyFrClassName OBJECT-TYPE
    SYNTAX OCTET STRING (SIZE (1..31))
    MAX-ACCESS not-accessible
    STATUS current
    DESCRIPTION
        "The name of FR class."
    ::= { unisCBQoSFrClassApplyPolicyEntry 1 }

unisCBQoSFrClassApplyPolicyDirection OBJECT-TYPE
    SYNTAX DirectionType
    MAX-ACCESS not-accessible
    STATUS current
    DESCRIPTION
        "Policy direction:
         inbound (1)
         outbound (2)"
    ::= { unisCBQoSFrClassApplyPolicyEntry 2 }

unisCBQoSFrClassApplyPolicyName OBJECT-TYPE
    SYNTAX OCTET STRING (SIZE (1..31))
    MAX-ACCESS read-create
    STATUS current
    DESCRIPTION
        "Name of Traffic Policy."
    ::= { unisCBQoSFrClassApplyPolicyEntry 3 }

unisCBQoSFrClassApplyPolicyRowStatus OBJECT-TYPE
    SYNTAX RowStatus
    MAX-ACCESS read-create
    STATUS current
    DESCRIPTION
        "RowStatus."
    ::= { unisCBQoSFrClassApplyPolicyEntry 4 }

-- Policy Instance on FR PVC Table

unisCBQoSFrPvcApplyPolicyTable OBJECT-TYPE
    SYNTAX SEQUENCE OF UnisCBQoSFrPvcApplyPolicyEntry
    MAX-ACCESS not-accessible
    STATUS current
    DESCRIPTION
        "A table of QoS policy instance."
    ::= { unisCBQoSApplyPolicyObjects 5 }

unisCBQoSFrPvcApplyPolicyEntry OBJECT-TYPE
    SYNTAX UnisCBQoSFrPvcApplyPolicyEntry
    MAX-ACCESS not-accessible
    STATUS current
    DESCRIPTION
        "Policy applied on FR PVC Configuration Information Entry."
    INDEX { unisCBQoSFrPvcApplyPolicyIfIndex,
            unisCBQoSFrPvcApplyPolicyDlciNum,
            unisCBQoSFrPvcApplyPolicyDirection }
    ::= { unisCBQoSFrPvcApplyPolicyTable 1 }

UnisCBQoSFrPvcApplyPolicyEntry ::=
    SEQUENCE
    {
        unisCBQoSFrPvcApplyPolicyIfIndex
            Integer32,
        unisCBQoSFrPvcApplyPolicyDlciNum
            Integer32,
        unisCBQoSFrPvcApplyPolicyDirection
            DirectionType,
        unisCBQoSFrPvcApplyPolicyName
            OCTET STRING,
        unisCBQoSFrPvcApplyPolicyRowStatus
            RowStatus
    }

unisCBQoSFrPvcApplyPolicyIfIndex OBJECT-TYPE
    SYNTAX Integer32
    MAX-ACCESS not-accessible
    STATUS current
    DESCRIPTION
        "Fr Interface Index, equal to ifIndex."
    ::= { unisCBQoSFrPvcApplyPolicyEntry 1 }

unisCBQoSFrPvcApplyPolicyDlciNum OBJECT-TYPE
    SYNTAX Integer32 (16..1007)
    MAX-ACCESS not-accessible
    STATUS current
    DESCRIPTION
        "Fr DLCI number."
    ::= { unisCBQoSFrPvcApplyPolicyEntry 2 }

unisCBQoSFrPvcApplyPolicyDirection OBJECT-TYPE
    SYNTAX DirectionType
    MAX-ACCESS not-accessible
    STATUS current
    DESCRIPTION
        "Policy direction:
         inbound (1)
         outbound (2)"
    ::= { unisCBQoSFrPvcApplyPolicyEntry 3 }

unisCBQoSFrPvcApplyPolicyName OBJECT-TYPE
    SYNTAX OCTET STRING (SIZE (1..31))
    MAX-ACCESS read-only
    STATUS current
    DESCRIPTION
        "Name of Traffic Policy."
    ::= { unisCBQoSFrPvcApplyPolicyEntry 4 }

unisCBQoSFrPvcApplyPolicyRowStatus OBJECT-TYPE
    SYNTAX RowStatus
    MAX-ACCESS read-only
    STATUS current
    DESCRIPTION
        "RowStatus."
    ::= { unisCBQoSFrPvcApplyPolicyEntry 5 }

-- Policy Instance on Global

unisCBQoSGlobalApplyTable OBJECT-TYPE
    SYNTAX SEQUENCE OF UnisCBQoSGlobalApplyEntry
    MAX-ACCESS not-accessible
    STATUS current
    DESCRIPTION
        "A table of QoS policies applied globally.  A QoS policy
        applied globally takes effect on all ports of the device."
    ::= { unisCBQoSApplyPolicyObjects 6 }

unisCBQoSGlobalApplyEntry OBJECT-TYPE
    SYNTAX UnisCBQoSGlobalApplyEntry
    MAX-ACCESS not-accessible
    STATUS current
    DESCRIPTION
        "A global policy entry."
    INDEX { unisCBQoSGlobalApplyDirection }
    ::= { unisCBQoSGlobalApplyTable 1 }

UnisCBQoSGlobalApplyEntry ::=
    SEQUENCE
    {
        unisCBQoSGlobalApplyDirection
            DirectionType,
        unisCBQoSGlobalApplyName
            OCTET STRING,
        unisCBQoSGlobalApplyRowStatus
            RowStatus,
        unisCBQoSGlobalApplyStatus
            INTEGER
    }

unisCBQoSGlobalApplyDirection OBJECT-TYPE
    SYNTAX DirectionType
    MAX-ACCESS not-accessible
    STATUS current
    DESCRIPTION
        "Policy direction:
         inbound (1)
         outbound (2)"
    ::= { unisCBQoSGlobalApplyEntry 1 }

unisCBQoSGlobalApplyName OBJECT-TYPE
    SYNTAX OCTET STRING (SIZE (1..31))
    MAX-ACCESS read-create
    STATUS current
    DESCRIPTION
        "Name of a global policy."
    ::= { unisCBQoSGlobalApplyEntry 2 }

unisCBQoSGlobalApplyRowStatus OBJECT-TYPE
    SYNTAX RowStatus
    MAX-ACCESS read-create
    STATUS current
    DESCRIPTION
        "RowStatus."
    ::= { unisCBQoSGlobalApplyEntry 3 }

unisCBQoSGlobalApplyStatus OBJECT-TYPE
    SYNTAX INTEGER
    {
        proccessing(1),
        success(2),
        partialItemFailed(3)
    }
    MAX-ACCESS read-only
    STATUS current
    DESCRIPTION
        "Status of policy applied globally."
    ::= { unisCBQoSGlobalApplyEntry 4 }

-- Policy Instance on controlPlane

unisCBQoSCpApplyPolicyTable OBJECT-TYPE
    SYNTAX SEQUENCE OF UnisCBQoSCpApplyPolicyEntry
    MAX-ACCESS not-accessible
    STATUS current
    DESCRIPTION
        "A table of QoS policies applied on control plane."
    ::= { unisCBQoSApplyPolicyObjects 7 }

unisCBQoSCpApplyPolicyEntry OBJECT-TYPE
    SYNTAX UnisCBQoSCpApplyPolicyEntry
    MAX-ACCESS not-accessible
    STATUS current
    DESCRIPTION
        "Policy applied on control plane configuration information entry."
    INDEX { unisCBQoSCpApplyPolicyChassis,
            unisCBQoSCpApplyPolicySlot,
            unisCBQoSCpApplyPolicyDirection }
    ::= { unisCBQoSCpApplyPolicyTable 1 }

UnisCBQoSCpApplyPolicyEntry ::=
    SEQUENCE
    {
        unisCBQoSCpApplyPolicyChassis
            Unsigned32,
        unisCBQoSCpApplyPolicySlot
            Unsigned32,
        unisCBQoSCpApplyPolicyDirection
            DirectionType,
        unisCBQoSCpApplyPolicyName
            OCTET STRING,
        unisCBQoSCpApplyPolicyStatus
            INTEGER,
        unisCBQoSCpApplyRowStatus
            RowStatus
    }

unisCBQoSCpApplyPolicyChassis OBJECT-TYPE
    SYNTAX Unsigned32
    MAX-ACCESS not-accessible
    STATUS current
    DESCRIPTION
        "Chassis number."
    ::= { unisCBQoSCpApplyPolicyEntry 1 }

unisCBQoSCpApplyPolicySlot OBJECT-TYPE
    SYNTAX Unsigned32
    MAX-ACCESS not-accessible
    STATUS current
    DESCRIPTION
        "Slot number."
    ::= { unisCBQoSCpApplyPolicyEntry 2 }

unisCBQoSCpApplyPolicyDirection OBJECT-TYPE
    SYNTAX DirectionType
    MAX-ACCESS not-accessible
    STATUS current
    DESCRIPTION
        "Policy direction:
         inbound (1)
         outbound (2)"
    ::= { unisCBQoSCpApplyPolicyEntry 3 }

unisCBQoSCpApplyPolicyName OBJECT-TYPE
    SYNTAX OCTET STRING (SIZE (1..31))
    MAX-ACCESS read-create
    STATUS current
    DESCRIPTION
        "Name of traffic policy."
    ::= { unisCBQoSCpApplyPolicyEntry 4 }

unisCBQoSCpApplyPolicyStatus OBJECT-TYPE
    SYNTAX INTEGER
    {
        proccessing(1),
        success(2),
        partialItemFailed(3)
    }
    MAX-ACCESS read-only
    STATUS current
    DESCRIPTION
        "Status of policy applied on control plane."
    ::= { unisCBQoSCpApplyPolicyEntry 5 }

unisCBQoSCpApplyRowStatus OBJECT-TYPE
    SYNTAX RowStatus
    MAX-ACCESS read-create
    STATUS current
    DESCRIPTION
        "RowStatus."
    ::= { unisCBQoSCpApplyPolicyEntry 6 }

-- Running statistics information

unisCBQoSApplyPolicyStaticsObjects OBJECT IDENTIFIER ::= { unisCBQoSObjects 5 }

-- Interface: policy Running statistics information

unisCBQoSIfStaticsObjects OBJECT IDENTIFIER ::= { unisCBQoSApplyPolicyStaticsObjects 1 }

-- Interface CBQ statistics

unisCBQoSIfCbqRunInfoTable OBJECT-TYPE
    SYNTAX SEQUENCE OF UnisCBQoSIfCbqRunInfoEntry
    MAX-ACCESS not-accessible
    STATUS current
    DESCRIPTION
        "A table of interface CBQ Running statistics.
         When policy using queue behavior is applied on
         interface the interface will using Class Based Queuing."
    ::= { unisCBQoSIfStaticsObjects 1 }

unisCBQoSIfCbqRunInfoEntry OBJECT-TYPE
    SYNTAX UnisCBQoSIfCbqRunInfoEntry
    MAX-ACCESS not-accessible
    STATUS current
    DESCRIPTION
        "Interface CBQ statistics entry."
    INDEX { unisCBQoSIfApplyPolicyIfIndex }
    ::= { unisCBQoSIfCbqRunInfoTable 1 }

UnisCBQoSIfCbqRunInfoEntry ::=
    SEQUENCE
    {
        unisCBQoSIfCbqQueueSize
            Integer32,
        unisCBQoSIfCbqDiscard
            Counter64,
        unisCBQoSIfCbqEfQueueSize
            Integer32,
        unisCBQoSIfCbqAfQueueSize
            Integer32,
        unisCBQoSIfCbqBeQueueSize
            Integer32,
        unisCBQoSIfCbqBeActiveQueueNum
            Integer32,
        unisCBQoSIfCbqBeMaxActiveQueueNum
            Integer32,
        unisCBQoSIfCbqBeTotalQueueNum
            Integer32,
        unisCBQoSIfCbqAfAllocatedQueueNum
            Integer32
    }

unisCBQoSIfCbqQueueSize OBJECT-TYPE
    SYNTAX Integer32
    MAX-ACCESS read-only
    STATUS current
    DESCRIPTION
        "Packet number of CBQ queue"
    ::= { unisCBQoSIfCbqRunInfoEntry 1 }

unisCBQoSIfCbqDiscard OBJECT-TYPE
    SYNTAX Counter64
    MAX-ACCESS read-only
    STATUS current
    DESCRIPTION
        "The number of discarded packets which couldn't be enqueued."
    ::= { unisCBQoSIfCbqRunInfoEntry 2 }

unisCBQoSIfCbqEfQueueSize OBJECT-TYPE
    SYNTAX Integer32
    MAX-ACCESS read-only
    STATUS current
    DESCRIPTION
        "Packet number of EF queue."
    ::= { unisCBQoSIfCbqRunInfoEntry 3 }

unisCBQoSIfCbqAfQueueSize OBJECT-TYPE
    SYNTAX Integer32
    MAX-ACCESS read-only
    STATUS current
    DESCRIPTION
        "Packet number of AF queue."
    ::= { unisCBQoSIfCbqRunInfoEntry 4 }

unisCBQoSIfCbqBeQueueSize OBJECT-TYPE
    SYNTAX Integer32
    MAX-ACCESS read-only
    STATUS current
    DESCRIPTION
        "Packet number of BE queue."
    ::= { unisCBQoSIfCbqRunInfoEntry 5 }

unisCBQoSIfCbqBeActiveQueueNum OBJECT-TYPE
    SYNTAX Integer32
    MAX-ACCESS read-only
    STATUS current
    DESCRIPTION
        "The Packet number of Active BE Queue."
    ::= { unisCBQoSIfCbqRunInfoEntry 6 }

unisCBQoSIfCbqBeMaxActiveQueueNum OBJECT-TYPE
    SYNTAX Integer32
    MAX-ACCESS read-only
    STATUS current
    DESCRIPTION
        "The max Packet number of Active BE Queue."
    ::= { unisCBQoSIfCbqRunInfoEntry 7 }

unisCBQoSIfCbqBeTotalQueueNum OBJECT-TYPE
    SYNTAX Integer32
    MAX-ACCESS read-only
    STATUS current
    DESCRIPTION
        "The total Packet number of BE Queue."
    ::= { unisCBQoSIfCbqRunInfoEntry 8 }

unisCBQoSIfCbqAfAllocatedQueueNum OBJECT-TYPE
    SYNTAX Integer32
    MAX-ACCESS read-only
    STATUS current
    DESCRIPTION
        "The Allocated Packet number of AF Queue."
    ::= { unisCBQoSIfCbqRunInfoEntry 9 }

-- Class match statistics

unisCBQoSIfClassMatchRunInfoTable OBJECT-TYPE
    SYNTAX SEQUENCE OF UnisCBQoSIfClassMatchRunInfoEntry
    MAX-ACCESS not-accessible
    STATUS current
    DESCRIPTION
        "A table of Running statistics for matching a classifier
         in a QoS policy applied on the interface."
    ::= { unisCBQoSIfStaticsObjects 2 }

unisCBQoSIfClassMatchRunInfoEntry OBJECT-TYPE
    SYNTAX UnisCBQoSIfClassMatchRunInfoEntry
    MAX-ACCESS not-accessible
    STATUS current
    DESCRIPTION
        "Classifier's matching statistics information entry."
    INDEX { unisCBQoSIfApplyPolicyIfIndex,
            unisCBQoSIfApplyPolicyDirection,
            unisCBQoSPolicyClassIndex }
    ::= { unisCBQoSIfClassMatchRunInfoTable 1 }

UnisCBQoSIfClassMatchRunInfoEntry ::=
    SEQUENCE
    {
        unisCBQoSIfClassMatchedPackets
            Counter64,
        unisCBQoSIfClassMatchedBytes
            Counter64,
        unisCBQoSIfClassAverageRate
            Counter64
    }

unisCBQoSIfClassMatchedPackets OBJECT-TYPE
    SYNTAX Counter64
    MAX-ACCESS read-only
    STATUS current
    DESCRIPTION
        "Number of packets matching a class in a QoS policy."
    ::= { unisCBQoSIfClassMatchRunInfoEntry 1 }

unisCBQoSIfClassMatchedBytes OBJECT-TYPE
    SYNTAX Counter64
    MAX-ACCESS read-only
    STATUS current
    DESCRIPTION
        "Number of bytes matching a class in a QoS policy.
         Only software QoS support this node."
    ::= { unisCBQoSIfClassMatchRunInfoEntry 2 }

unisCBQoSIfClassAverageRate OBJECT-TYPE
    SYNTAX Counter64
    MAX-ACCESS read-only
    STATUS current
    DESCRIPTION
        "Average rate matching a class of the last 5 minutes."
    ::= { unisCBQoSIfClassMatchRunInfoEntry 3 }

-- CAR statistics

unisCBQoSIfCarRunInfoTable OBJECT-TYPE
    SYNTAX SEQUENCE OF UnisCBQoSIfCarRunInfoEntry
    MAX-ACCESS not-accessible
    STATUS current
    DESCRIPTION
        "A table of Running statistics for CAR
         in a QoS policy applied on the interface."
    ::= { unisCBQoSIfStaticsObjects 3 }

unisCBQoSIfCarRunInfoEntry OBJECT-TYPE
    SYNTAX UnisCBQoSIfCarRunInfoEntry
    MAX-ACCESS not-accessible
    STATUS current
    DESCRIPTION
        "CAR statistics information entry."
    INDEX { unisCBQoSIfApplyPolicyIfIndex,
            unisCBQoSIfApplyPolicyDirection,
            unisCBQoSPolicyClassIndex }
    ::= { unisCBQoSIfCarRunInfoTable 1 }

UnisCBQoSIfCarRunInfoEntry ::=
    SEQUENCE
    {
        unisCBQoSIfCarGreenPackets
            Counter64,
        unisCBQoSIfCarGreenBytes
            Counter64,
        unisCBQoSIfCarRedPackets
            Counter64,
        unisCBQoSIfCarRedBytes
            Counter64,
        unisCBQoSIfCarYellowPackets
            Counter64,
        unisCBQoSIfCarYellowBytes
            Counter64
    }

unisCBQoSIfCarGreenPackets OBJECT-TYPE
    SYNTAX Counter64
    MAX-ACCESS read-only
    STATUS current
    DESCRIPTION
        "Number of green packets."
    ::= { unisCBQoSIfCarRunInfoEntry 1 }

unisCBQoSIfCarGreenBytes OBJECT-TYPE
    SYNTAX Counter64
    MAX-ACCESS read-only
    STATUS current
    DESCRIPTION
        "Number of green bytes."
    ::= { unisCBQoSIfCarRunInfoEntry 2 }

unisCBQoSIfCarRedPackets OBJECT-TYPE
    SYNTAX Counter64
    MAX-ACCESS read-only
    STATUS current
    DESCRIPTION
        "Number of red packets."
    ::= { unisCBQoSIfCarRunInfoEntry 3 }

unisCBQoSIfCarRedBytes OBJECT-TYPE
    SYNTAX Counter64
    MAX-ACCESS read-only
    STATUS current
    DESCRIPTION
        "Number of red bytes."
    ::= { unisCBQoSIfCarRunInfoEntry 4 }

unisCBQoSIfCarYellowPackets OBJECT-TYPE
    SYNTAX Counter64
    MAX-ACCESS read-only
    STATUS current
    DESCRIPTION
        "Number of yellow packets."
    ::= { unisCBQoSIfCarRunInfoEntry 5 }

unisCBQoSIfCarYellowBytes OBJECT-TYPE
    SYNTAX Counter64
    MAX-ACCESS read-only
    STATUS current
    DESCRIPTION
        "Number of yellow bytes."
    ::= { unisCBQoSIfCarRunInfoEntry 6 }

-- GTS statistics

unisCBQoSIfGtsRunInfoTable OBJECT-TYPE
    SYNTAX SEQUENCE OF UnisCBQoSIfGtsRunInfoEntry
    MAX-ACCESS not-accessible
    STATUS current
    DESCRIPTION
        "A table of Running statistics for GTS
         in a QoS policy applied on the interface."
    ::= { unisCBQoSIfStaticsObjects 4 }

unisCBQoSIfGtsRunInfoEntry OBJECT-TYPE
    SYNTAX UnisCBQoSIfGtsRunInfoEntry
    MAX-ACCESS not-accessible
    STATUS current
    DESCRIPTION
        "GTS statistics entry."
    INDEX { unisCBQoSIfApplyPolicyIfIndex,
            unisCBQoSIfApplyPolicyDirection,
            unisCBQoSPolicyClassIndex }
    ::= { unisCBQoSIfGtsRunInfoTable 1 }

UnisCBQoSIfGtsRunInfoEntry ::=
    SEQUENCE
    {
        unisCBQoSIfGtsPassedPackets
            Counter64,
        unisCBQoSIfGtsPassedBytes
            Counter64,
        unisCBQoSIfGtsDiscardedPackets
            Counter64,
        unisCBQoSIfGtsDiscardedBytes
            Counter64,
        unisCBQoSIfGtsDelayedPackets
            Counter64,
        unisCBQoSIfGtsDelayedBytes
            Counter64,
        unisCBQoSIfGtsQueueSize
            Integer32
    }

unisCBQoSIfGtsPassedPackets OBJECT-TYPE
    SYNTAX Counter64
    MAX-ACCESS read-only
    STATUS current
    DESCRIPTION
        "Number of packets passed by GTS."
    ::= { unisCBQoSIfGtsRunInfoEntry 1 }

unisCBQoSIfGtsPassedBytes OBJECT-TYPE
    SYNTAX Counter64
    MAX-ACCESS read-only
    STATUS current
    DESCRIPTION
        "Number of bytes passed by GTS."
    ::= { unisCBQoSIfGtsRunInfoEntry 2 }

unisCBQoSIfGtsDiscardedPackets OBJECT-TYPE
    SYNTAX Counter64
    MAX-ACCESS read-only
    STATUS current
    DESCRIPTION
        "Number of packets discarded by GTS."
    ::= { unisCBQoSIfGtsRunInfoEntry 3 }

unisCBQoSIfGtsDiscardedBytes OBJECT-TYPE
    SYNTAX Counter64
    MAX-ACCESS read-only
    STATUS current
    DESCRIPTION
        "Number of bytes discarded by GTS."
    ::= { unisCBQoSIfGtsRunInfoEntry 4 }

unisCBQoSIfGtsDelayedPackets OBJECT-TYPE
    SYNTAX Counter64
    MAX-ACCESS read-only
    STATUS current
    DESCRIPTION
        "Number of packets delayed by GTS."
    ::= { unisCBQoSIfGtsRunInfoEntry 5 }

unisCBQoSIfGtsDelayedBytes OBJECT-TYPE
    SYNTAX Counter64
    MAX-ACCESS read-only
    STATUS current
    DESCRIPTION
        "Number of bytes delayed by GTS."
    ::= { unisCBQoSIfGtsRunInfoEntry 6 }

unisCBQoSIfGtsQueueSize OBJECT-TYPE
    SYNTAX Integer32
    MAX-ACCESS read-only
    STATUS current
    DESCRIPTION
        "Packet number of GTS queue."
    ::= { unisCBQoSIfGtsRunInfoEntry 7 }

-- Remark statistics

unisCBQoSIfRemarkRunInfoTable OBJECT-TYPE
    SYNTAX SEQUENCE OF UnisCBQoSIfRemarkRunInfoEntry
    MAX-ACCESS not-accessible
    STATUS current
    DESCRIPTION
        "A table of Running statistics for remarking
         in a QoS policy applied on the interface."
    ::= { unisCBQoSIfStaticsObjects 5 }

unisCBQoSIfRemarkRunInfoEntry OBJECT-TYPE
    SYNTAX UnisCBQoSIfRemarkRunInfoEntry
    MAX-ACCESS not-accessible
    STATUS current
    DESCRIPTION
        "Remarking statistics entry."
    INDEX { unisCBQoSIfApplyPolicyIfIndex,
            unisCBQoSIfApplyPolicyDirection,
            unisCBQoSPolicyClassIndex }
    ::= { unisCBQoSIfRemarkRunInfoTable 1 }

UnisCBQoSIfRemarkRunInfoEntry ::=
    SEQUENCE
    {
        unisCBQoSIfRemarkedPackets
            Counter64
    }

unisCBQoSIfRemarkedPackets OBJECT-TYPE
    SYNTAX Counter64
    MAX-ACCESS read-only
    STATUS current
    DESCRIPTION
        "Number of packets remarked."
    ::= { unisCBQoSIfRemarkRunInfoEntry 1 }

-- Queue statistics

unisCBQoSIfQueueRunInfoTable OBJECT-TYPE
    SYNTAX SEQUENCE OF UnisCBQoSIfQueueRunInfoEntry
    MAX-ACCESS not-accessible
    STATUS current
    DESCRIPTION
        "A table of Running statistics for queue
         in a QoS policy applied on the interface."
    ::= { unisCBQoSIfStaticsObjects 6 }

unisCBQoSIfQueueRunInfoEntry OBJECT-TYPE
    SYNTAX UnisCBQoSIfQueueRunInfoEntry
    MAX-ACCESS not-accessible
    STATUS current
    DESCRIPTION
        "Queue statistics entry."
    INDEX { unisCBQoSIfApplyPolicyIfIndex,
            unisCBQoSIfApplyPolicyDirection,
            unisCBQoSPolicyClassIndex }
    ::= { unisCBQoSIfQueueRunInfoTable 1 }

UnisCBQoSIfQueueRunInfoEntry ::=
    SEQUENCE
    {
        unisCBQoSIfQueueMatchedPackets
            Counter64,
        unisCBQoSIfQueueMatchedBytes
            Counter64,
        unisCBQoSIfQueueEnqueuedPackets
            Counter64,
        unisCBQoSIfQueueEnqueuedBytes
            Counter64,
        unisCBQoSIfQueueDiscardedPackets
            Counter64,
        unisCBQoSIfQueueDiscardedBytes
            Counter64
    }

unisCBQoSIfQueueMatchedPackets OBJECT-TYPE
    SYNTAX Counter64
    MAX-ACCESS read-only
    STATUS current
    DESCRIPTION
        "Number of packets matched to enqueue."
    ::= { unisCBQoSIfQueueRunInfoEntry 1 }

unisCBQoSIfQueueMatchedBytes OBJECT-TYPE
    SYNTAX Counter64
    MAX-ACCESS read-only
    STATUS current
    DESCRIPTION
        "Number of bytes matched to enqueue."
    ::= { unisCBQoSIfQueueRunInfoEntry 2 }

unisCBQoSIfQueueEnqueuedPackets OBJECT-TYPE
    SYNTAX Counter64
    MAX-ACCESS read-only
    STATUS current
    DESCRIPTION
        "Number of packets enqueued."
    ::= { unisCBQoSIfQueueRunInfoEntry 3 }

unisCBQoSIfQueueEnqueuedBytes OBJECT-TYPE
    SYNTAX Counter64
    MAX-ACCESS read-only
    STATUS current
    DESCRIPTION
        "Number of bytes enqueued."
    ::= { unisCBQoSIfQueueRunInfoEntry 4 }

unisCBQoSIfQueueDiscardedPackets OBJECT-TYPE
    SYNTAX Counter64
    MAX-ACCESS read-only
    STATUS current
    DESCRIPTION
        "Number of packets discarded when enqueued by discard method."
    ::= { unisCBQoSIfQueueRunInfoEntry 5 }

unisCBQoSIfQueueDiscardedBytes OBJECT-TYPE
    SYNTAX Counter64
    MAX-ACCESS read-only
    STATUS current
    DESCRIPTION
        "Number of bytes discarded when enqueued by discard method."
    ::= { unisCBQoSIfQueueRunInfoEntry 6 }

-- WRED statistics

unisCBQoSIfWredRunInfoTable OBJECT-TYPE
    SYNTAX SEQUENCE OF UnisCBQoSIfWredRunInfoEntry
    MAX-ACCESS not-accessible
    STATUS current
    DESCRIPTION
        "A table of Running statistics for WRED
         in a QoS policy applied on the interface."
    ::= { unisCBQoSIfStaticsObjects 7 }

unisCBQoSIfWredRunInfoEntry OBJECT-TYPE
    SYNTAX UnisCBQoSIfWredRunInfoEntry
    MAX-ACCESS not-accessible
    STATUS current
    DESCRIPTION
        "WRED statistics entry."
    INDEX { unisCBQoSIfApplyPolicyIfIndex,
            unisCBQoSIfApplyPolicyDirection,
            unisCBQoSPolicyClassIndex,
            unisCBQoSWredClassValue }
    ::= { unisCBQoSIfWredRunInfoTable 1 }

UnisCBQoSIfWredRunInfoEntry ::=
    SEQUENCE
    {
        unisCBQoSIfWredRandomDiscardedPackets
            Counter64,
        unisCBQoSIfWredTailDiscardedPackets
            Counter64
    }

unisCBQoSIfWredRandomDiscardedPackets OBJECT-TYPE
    SYNTAX Counter64
    MAX-ACCESS read-only
    STATUS current
    DESCRIPTION
        "Number of packets that random-discarded by WRED."
    ::= { unisCBQoSIfWredRunInfoEntry 1 }

unisCBQoSIfWredTailDiscardedPackets OBJECT-TYPE
    SYNTAX Counter64
    MAX-ACCESS read-only
    STATUS current
    DESCRIPTION
        "Number of packets that tail-discarded by WRED."
    ::= { unisCBQoSIfWredRunInfoEntry 2 }

--
-- nodes of unisCBQoSIfAccountingRunInfoTable
--
unisCBQoSIfAccountingRunInfoTable OBJECT-TYPE
    SYNTAX SEQUENCE OF UnisCBQoSIfAccountingRunInfoEntry
    MAX-ACCESS not-accessible
    STATUS current
    DESCRIPTION
        "A table of Running statistics for account
         in a QoS policy applied on the interface."
    ::= { unisCBQoSIfStaticsObjects 8 }

unisCBQoSIfAccountingRunInfoEntry OBJECT-TYPE
    SYNTAX UnisCBQoSIfAccountingRunInfoEntry
    MAX-ACCESS not-accessible
    STATUS current
    DESCRIPTION
        "Account statistics entry."
    INDEX { unisCBQoSIfApplyPolicyIfIndex,
            unisCBQoSIfApplyPolicyDirection,
            unisCBQoSPolicyClassIndex
          }
    ::= { unisCBQoSIfAccountingRunInfoTable 1 }

UnisCBQoSIfAccountingRunInfoEntry ::=
    SEQUENCE
    {
        unisCBQoSIfAccountingPackets
            Counter64,
        unisCBQoSIfAccountingBytes
            Counter64
    }

unisCBQoSIfAccountingPackets OBJECT-TYPE
    SYNTAX Counter64
    MAX-ACCESS read-only
    STATUS current
    DESCRIPTION
        "Number of packets."
    ::= { unisCBQoSIfAccountingRunInfoEntry 1 }

unisCBQoSIfAccountingBytes OBJECT-TYPE
    SYNTAX Counter64
    MAX-ACCESS read-only
    STATUS current
    DESCRIPTION
        "Number of bytes."
    ::= { unisCBQoSIfAccountingRunInfoEntry 2 }

-- ATM Interface PVC: policy Running statistics information

unisCBQoSAtmPvcStaticsObjects OBJECT IDENTIFIER ::= { unisCBQoSApplyPolicyStaticsObjects 2 }

-- ATM PVC CBQ statistics

unisCBQoSAtmPvcCbqRunInfoTable OBJECT-TYPE
    SYNTAX SEQUENCE OF UnisCBQoSAtmPvcCbqRunInfoEntry
    MAX-ACCESS not-accessible
    STATUS current
    DESCRIPTION
        "A table of ATM PVC CBQ Running statistics.
         When policy using queue behavior is applied on
         ATM PVC.  ATM PVC will using Class Based Queuing."
    ::= { unisCBQoSAtmPvcStaticsObjects 1 }

unisCBQoSAtmPvcCbqRunInfoEntry OBJECT-TYPE
    SYNTAX UnisCBQoSAtmPvcCbqRunInfoEntry
    MAX-ACCESS not-accessible
    STATUS current
    DESCRIPTION
        "FR PVC CBQ statistics entry."
    INDEX { unisCBQoSAtmPvcApplyPolicyIfIndex,
            unisCBQoSAtmPvcApplyPolicyVPI,
            unisCBQoSAtmPvcApplyPolicyVCI }
    ::= { unisCBQoSAtmPvcCbqRunInfoTable 1 }

UnisCBQoSAtmPvcCbqRunInfoEntry ::=
    SEQUENCE
    {
        unisCBQoSAtmPvcCbqQueueSize
            Integer32,
        unisCBQoSAtmPvcCbqDiscard
            Counter64,
        unisCBQoSAtmPvcCbqEfQueueSize
            Integer32,
        unisCBQoSAtmPvcCbqAfQueueSize
            Integer32,
        unisCBQoSAtmPvcCbqBeQueueSize
            Integer32,
        unisCBQoSAtmPvcCbqBeActiveQueueNum
            Integer32,
        unisCBQoSAtmPvcCbqBeMaxActiveQueueNum
            Integer32,
        unisCBQoSAtmPvcCbqBeTotalQueueNum
            Integer32,
        unisCBQoSAtmPvcCbqAfAllocatedQueueNum
            Integer32
    }

unisCBQoSAtmPvcCbqQueueSize OBJECT-TYPE
    SYNTAX Integer32
    MAX-ACCESS read-only
    STATUS current
    DESCRIPTION
        "Packet number of CBQ queue."
    ::= { unisCBQoSAtmPvcCbqRunInfoEntry 1 }

unisCBQoSAtmPvcCbqDiscard OBJECT-TYPE
    SYNTAX Counter64
    MAX-ACCESS read-only
    STATUS current
    DESCRIPTION
        "The number of discarded packets which couldn't be enqueued."
    ::= { unisCBQoSAtmPvcCbqRunInfoEntry 2 }

unisCBQoSAtmPvcCbqEfQueueSize OBJECT-TYPE
    SYNTAX Integer32
    MAX-ACCESS read-only
    STATUS current
    DESCRIPTION
        "Packet number of EF queue."
    ::= { unisCBQoSAtmPvcCbqRunInfoEntry 3 }

unisCBQoSAtmPvcCbqAfQueueSize OBJECT-TYPE
    SYNTAX Integer32
    MAX-ACCESS read-only
    STATUS current
    DESCRIPTION
        "Packet number of AF queue."
    ::= { unisCBQoSAtmPvcCbqRunInfoEntry 4 }

unisCBQoSAtmPvcCbqBeQueueSize OBJECT-TYPE
    SYNTAX Integer32
    MAX-ACCESS read-only
    STATUS current
    DESCRIPTION
        "Packet number of BE queue."
    ::= { unisCBQoSAtmPvcCbqRunInfoEntry 5 }

unisCBQoSAtmPvcCbqBeActiveQueueNum OBJECT-TYPE
    SYNTAX Integer32
    MAX-ACCESS read-only
    STATUS current
    DESCRIPTION
        "The packet number of Active Be Queue."
    ::= { unisCBQoSAtmPvcCbqRunInfoEntry 6 }

unisCBQoSAtmPvcCbqBeMaxActiveQueueNum OBJECT-TYPE
    SYNTAX Integer32
    MAX-ACCESS read-only
    STATUS current
    DESCRIPTION
        "The max packet number of Active Be Queue."
    ::= { unisCBQoSAtmPvcCbqRunInfoEntry 7 }

unisCBQoSAtmPvcCbqBeTotalQueueNum OBJECT-TYPE
    SYNTAX Integer32
    MAX-ACCESS read-only
    STATUS current
    DESCRIPTION
        "The total packet number of Be Queue."
    ::= { unisCBQoSAtmPvcCbqRunInfoEntry 8 }

unisCBQoSAtmPvcCbqAfAllocatedQueueNum OBJECT-TYPE
    SYNTAX Integer32
    MAX-ACCESS read-only
    STATUS current
    DESCRIPTION
        "The Allocated packet number of AF Queue."
    ::= { unisCBQoSAtmPvcCbqRunInfoEntry 9 }

-- Class match statistics

unisCBQoSAtmPvcClassMatchRunInfoTable OBJECT-TYPE
    SYNTAX SEQUENCE OF UnisCBQoSAtmPvcClassMatchRunInfoEntry
    MAX-ACCESS not-accessible
    STATUS current
    DESCRIPTION
        "A table of Running statistics for matching a classifier
         in a QoS policy applied on ATM PVC."
    ::= { unisCBQoSAtmPvcStaticsObjects 2 }

unisCBQoSAtmPvcClassMatchRunInfoEntry OBJECT-TYPE
    SYNTAX UnisCBQoSAtmPvcClassMatchRunInfoEntry
    MAX-ACCESS not-accessible
    STATUS current
    DESCRIPTION
        "Classifier matching statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex }
    ::= { unisCBQoSAtmPvcClassMatchRunInfoTable 1 }

UnisCBQoSAtmPvcClassMatchRunInfoEntry ::=
    SEQUENCE
    {
        unisCBQoSAtmPvcClassMatchPackets
            Counter64,
        unisCBQoSAtmPvcClassMatchBytes
            Counter64,
        unisCBQoSAtmPvcClassAverageRate
            Integer32
    }

unisCBQoSAtmPvcClassMatchPackets OBJECT-TYPE
    SYNTAX Counter64
    MAX-ACCESS read-only
    STATUS current
    DESCRIPTION
        "Number of packets matching a class in a QoS policy."
    ::= { unisCBQoSAtmPvcClassMatchRunInfoEntry 1 }

unisCBQoSAtmPvcClassMatchBytes OBJECT-TYPE
    SYNTAX Counter64
    MAX-ACCESS read-only
    STATUS current
    DESCRIPTION
        "Number of bytes matching a class in a QoS policy."
    ::= { unisCBQoSAtmPvcClassMatchRunInfoEntry 2 }

unisCBQoSAtmPvcClassAverageRate OBJECT-TYPE
    SYNTAX Integer32
    MAX-ACCESS read-only
    STATUS current
    DESCRIPTION
        "Average rate matching a class in the last 5 minutes."
    ::= { unisCBQoSAtmPvcClassMatchRunInfoEntry 3 }

-- CAR statistics

unisCBQoSAtmPvcCarRunInfoTable OBJECT-TYPE
    SYNTAX SEQUENCE OF UnisCBQoSAtmPvcCarRunInfoEntry
    MAX-ACCESS not-accessible
    STATUS current
    DESCRIPTION
        "A table of Running statistics for CAR
         in a QoS policy applied on ATM PVC."
    ::= { unisCBQoSAtmPvcStaticsObjects 3 }

unisCBQoSAtmPvcCarRunInfoEntry OBJECT-TYPE
    SYNTAX UnisCBQoSAtmPvcCarRunInfoEntry
    MAX-ACCESS not-accessible
    STATUS current
    DESCRIPTION
        "CAR statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex }
    ::= { unisCBQoSAtmPvcCarRunInfoTable 1 }

UnisCBQoSAtmPvcCarRunInfoEntry ::=
    SEQUENCE
    {
        unisCBQoSAtmPvcCarConformPackets
            Counter64,
        unisCBQoSAtmPvcCarConformBytes
            Counter64,
        unisCBQoSAtmPvcCarExceedPackets
            Counter64,
        unisCBQoSAtmPvcCarExceedBytes
            Counter64
    }

unisCBQoSAtmPvcCarConformPackets OBJECT-TYPE
    SYNTAX Counter64
    MAX-ACCESS read-only
    STATUS current
    DESCRIPTION
        "Number of packets that conforming specified CIR."
    ::= { unisCBQoSAtmPvcCarRunInfoEntry 1 }

unisCBQoSAtmPvcCarConformBytes OBJECT-TYPE
    SYNTAX Counter64
    MAX-ACCESS read-only
    STATUS current
    DESCRIPTION
        "Number of bytes that conforming specified CIR."
    ::= { unisCBQoSAtmPvcCarRunInfoEntry 2 }

unisCBQoSAtmPvcCarExceedPackets OBJECT-TYPE
    SYNTAX Counter64
    MAX-ACCESS read-only
    STATUS current
    DESCRIPTION
        "Number of packets exceeded CIR."
    ::= { unisCBQoSAtmPvcCarRunInfoEntry 3 }

unisCBQoSAtmPvcCarExceedBytes OBJECT-TYPE
    SYNTAX Counter64
    MAX-ACCESS read-only
    STATUS current
    DESCRIPTION
        "Number of bytes exceeded CIR."
    ::= { unisCBQoSAtmPvcCarRunInfoEntry 4 }

-- GTS statistics

unisCBQoSAtmPvcGtsRunInfoTable OBJECT-TYPE
    SYNTAX SEQUENCE OF UnisCBQoSAtmPvcGtsRunInfoEntry
    MAX-ACCESS not-accessible
    STATUS current
    DESCRIPTION
        "A table of Running statistics for GTS
         in a QoS policy applied on ATM PVC."
    ::= { unisCBQoSAtmPvcStaticsObjects 4 }

unisCBQoSAtmPvcGtsRunInfoEntry OBJECT-TYPE
    SYNTAX UnisCBQoSAtmPvcGtsRunInfoEntry
    MAX-ACCESS not-accessible
    STATUS current
    DESCRIPTION
        "GTS statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex }
    ::= { unisCBQoSAtmPvcGtsRunInfoTable 1 }

UnisCBQoSAtmPvcGtsRunInfoEntry ::=
    SEQUENCE
    {
        unisCBQoSAtmPvcGtsPassedPackets
            Counter64,
        unisCBQoSAtmPvcGtsPassedBytes
            Counter64,
        unisCBQoSAtmPvcGtsDiscardedPackets
            Counter64,
        unisCBQoSAtmPvcGtsDiscardedBytes
            Counter64,
        unisCBQoSAtmPvcGtsDelayedPackets
            Counter64,
        unisCBQoSAtmPvcGtsDelayedBytes
            Counter64,
        unisCBQoSAtmPvcGtsQueueSize
            Integer32
    }

unisCBQoSAtmPvcGtsPassedPackets OBJECT-TYPE
    SYNTAX Counter64
    MAX-ACCESS read-only
    STATUS current
    DESCRIPTION
        "Number of packets passed by GTS."
    ::= { unisCBQoSAtmPvcGtsRunInfoEntry 1 }

unisCBQoSAtmPvcGtsPassedBytes OBJECT-TYPE
    SYNTAX Counter64
    MAX-ACCESS read-only
    STATUS current
    DESCRIPTION
        "Number of bytes passed by GTS."
    ::= { unisCBQoSAtmPvcGtsRunInfoEntry 2 }

unisCBQoSAtmPvcGtsDiscardedPackets OBJECT-TYPE
    SYNTAX Counter64
    MAX-ACCESS read-only
    STATUS current
    DESCRIPTION
        "Number of packets discarded by GTS."
    ::= { unisCBQoSAtmPvcGtsRunInfoEntry 3 }

unisCBQoSAtmPvcGtsDiscardedBytes OBJECT-TYPE
    SYNTAX Counter64
    MAX-ACCESS read-only
    STATUS current
    DESCRIPTION
        "Number of bytes discarded by GTS."
    ::= { unisCBQoSAtmPvcGtsRunInfoEntry 4 }

unisCBQoSAtmPvcGtsDelayedPackets OBJECT-TYPE
    SYNTAX Counter64
    MAX-ACCESS read-only
    STATUS current
    DESCRIPTION
        "Number of packets delayed by GTS."
    ::= { unisCBQoSAtmPvcGtsRunInfoEntry 5 }

unisCBQoSAtmPvcGtsDelayedBytes OBJECT-TYPE
    SYNTAX Counter64
    MAX-ACCESS read-only
    STATUS current
    DESCRIPTION
        "Number of bytes delayed by GTS."
    ::= { unisCBQoSAtmPvcGtsRunInfoEntry 6 }

unisCBQoSAtmPvcGtsQueueSize OBJECT-TYPE
    SYNTAX Integer32
    MAX-ACCESS read-only
    STATUS current
    DESCRIPTION
        "packet number of GTS queue."
    ::= { unisCBQoSAtmPvcGtsRunInfoEntry 7 }

-- Remark statistics

unisCBQoSAtmPvcRemarkRunInfoTable OBJECT-TYPE
    SYNTAX SEQUENCE OF UnisCBQoSAtmPvcRemarkRunInfoEntry
    MAX-ACCESS not-accessible
    STATUS current
    DESCRIPTION
        "A table of Running statistics for remarking
         in a QoS policy applied on ATM PVC."
    ::= { unisCBQoSAtmPvcStaticsObjects 5 }

unisCBQoSAtmPvcRemarkRunInfoEntry OBJECT-TYPE
    SYNTAX UnisCBQoSAtmPvcRemarkRunInfoEntry
    MAX-ACCESS not-accessible
    STATUS current
    DESCRIPTION
        "Remarking statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex }
    ::= { unisCBQoSAtmPvcRemarkRunInfoTable 1 }

UnisCBQoSAtmPvcRemarkRunInfoEntry ::=
    SEQUENCE
    {
        unisCBQoSAtmPvcRemarkedPackets
            Counter64
    }

unisCBQoSAtmPvcRemarkedPackets OBJECT-TYPE
    SYNTAX Counter64
    MAX-ACCESS read-only
    STATUS current
    DESCRIPTION
        "Number of packets remarked."
    ::= { unisCBQoSAtmPvcRemarkRunInfoEntry 1 }

-- Queue statistics

unisCBQoSAtmPvcQueueRunInfoTable OBJECT-TYPE
    SYNTAX SEQUENCE OF UnisCBQoSAtmPvcQueueRunInfoEntry
    MAX-ACCESS not-accessible
    STATUS current
    DESCRIPTION
        "A table of Running statistics for queue
         in a QoS policy applied on ATM PVC."
    ::= { unisCBQoSAtmPvcStaticsObjects 6 }

unisCBQoSAtmPvcQueueRunInfoEntry OBJECT-TYPE
    SYNTAX UnisCBQoSAtmPvcQueueRunInfoEntry
    MAX-ACCESS not-accessible
    STATUS current
    DESCRIPTION
        "Queue statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex }
    ::= { unisCBQoSAtmPvcQueueRunInfoTable 1}

UnisCBQoSAtmPvcQueueRunInfoEntry ::=
    SEQUENCE
    {
        unisCBQoSAtmPvcQueueMatchedPackets
            Counter64,
        unisCBQoSAtmPvcQueueMatchedBytes
            Counter64,
        unisCBQoSAtmPvcQueueEnqueuedPackets
            Counter64,
        unisCBQoSAtmPvcQueueEnqueuedBytes
            Counter64,
        unisCBQoSAtmPvcQueueDiscardedPackets
            Counter64,
        unisCBQoSAtmPvcQueueDiscardedBytes
            Counter64
    }

unisCBQoSAtmPvcQueueMatchedPackets OBJECT-TYPE
    SYNTAX Counter64
    MAX-ACCESS read-only
    STATUS current
    DESCRIPTION
        "Number of packets matched to enqueue."
    ::= { unisCBQoSAtmPvcQueueRunInfoEntry 1 }

unisCBQoSAtmPvcQueueMatchedBytes OBJECT-TYPE
    SYNTAX Counter64
    MAX-ACCESS read-only
    STATUS current
    DESCRIPTION
        "Number of bytes matched to enqueue."
    ::= { unisCBQoSAtmPvcQueueRunInfoEntry 2 }

unisCBQoSAtmPvcQueueEnqueuedPackets OBJECT-TYPE
    SYNTAX Counter64
    MAX-ACCESS read-only
    STATUS current
    DESCRIPTION
        "Number of packets enqueued."
    ::= { unisCBQoSAtmPvcQueueRunInfoEntry 3 }

unisCBQoSAtmPvcQueueEnqueuedBytes OBJECT-TYPE
    SYNTAX Counter64
    MAX-ACCESS read-only
    STATUS current
    DESCRIPTION
        "Number of bytes enqueued."
    ::= { unisCBQoSAtmPvcQueueRunInfoEntry 4 }

unisCBQoSAtmPvcQueueDiscardedPackets OBJECT-TYPE
    SYNTAX Counter64
    MAX-ACCESS read-only
    STATUS current
    DESCRIPTION
        "Number of packets discard when enqueued by discard method."
    ::= { unisCBQoSAtmPvcQueueRunInfoEntry 5 }

unisCBQoSAtmPvcQueueDiscardedBytes OBJECT-TYPE
    SYNTAX Counter64
    MAX-ACCESS read-only
    STATUS current
    DESCRIPTION
        "Number of bytes discard when enqueued by discard method."
    ::= { unisCBQoSAtmPvcQueueRunInfoEntry 6 }

-- WRED statistics

unisCBQoSAtmPvcWredRunInfoTable OBJECT-TYPE
    SYNTAX SEQUENCE OF UnisCBQoSAtmPvcWredRunInfoEntry
    MAX-ACCESS not-accessible
    STATUS current
    DESCRIPTION
        "A table of Running statistics for WRED
         in a QoS policy applied on ATM PVC."
    ::= { unisCBQoSAtmPvcStaticsObjects 7 }

unisCBQoSAtmPvcWredRunInfoEntry OBJECT-TYPE
    SYNTAX UnisCBQoSAtmPvcWredRunInfoEntry
    MAX-ACCESS not-accessible
    STATUS current
    DESCRIPTION
        "WRED statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex,
            unisCBQoSWredClassValue }
    ::= { unisCBQoSAtmPvcWredRunInfoTable 1 }

UnisCBQoSAtmPvcWredRunInfoEntry ::=
    SEQUENCE
    {
        unisCBQoSAtmPvcWredRandomDiscardedPackets
            Counter64,
        unisCBQoSAtmPvcWredTailDiscardedPackets
            Counter64
    }

unisCBQoSAtmPvcWredRandomDiscardedPackets OBJECT-TYPE
    SYNTAX Counter64
    MAX-ACCESS read-only
    STATUS current
    DESCRIPTION
        "Number of packets randomly discarded by WRED."
    ::= { unisCBQoSAtmPvcWredRunInfoEntry 1 }

unisCBQoSAtmPvcWredTailDiscardedPackets OBJECT-TYPE
    SYNTAX Counter64
    MAX-ACCESS read-only
    STATUS current
    DESCRIPTION
        "Number of packets tail-discarded by WRED."
    ::= { unisCBQoSAtmPvcWredRunInfoEntry 2 }

--
-- nodes of unisCBQoSAtmPvcAccountingRunInfoTable
--
unisCBQoSAtmPvcAccountingRunInfoTable OBJECT-TYPE
    SYNTAX SEQUENCE OF UnisCBQoSAtmPvcAccountingRunInfoEntry
    MAX-ACCESS not-accessible
    STATUS current
    DESCRIPTION
        "A table of Running statistics for account
         in a QoS policy applied on the ATM PVC."
    ::= { unisCBQoSAtmPvcStaticsObjects 8 }

unisCBQoSAtmPvcAccountingRunInfoEntry OBJECT-TYPE
    SYNTAX UnisCBQoSAtmPvcAccountingRunInfoEntry
    MAX-ACCESS not-accessible
    STATUS current
    DESCRIPTION
        "Account statistics entry."
    INDEX { unisCBQoSAtmPvcApplyPolicyIfIndex,
            unisCBQoSAtmPvcApplyPolicyVPI,
            unisCBQoSAtmPvcApplyPolicyVCI,
            unisCBQoSAtmPvcApplyPolicyDirection,
            unisCBQoSPolicyClassIndex,
            unisCBQoSWredClassValue
          }
    ::= { unisCBQoSAtmPvcAccountingRunInfoTable 1 }

UnisCBQoSAtmPvcAccountingRunInfoEntry ::=
    SEQUENCE
    {
        unisCBQoSAtmPvcAccountingPackets
            Counter64,
        unisCBQoSAtmPvcAccountingBytes
            Counter64
    }

unisCBQoSAtmPvcAccountingPackets OBJECT-TYPE
    SYNTAX Counter64
    MAX-ACCESS read-only
    STATUS current
    DESCRIPTION
        "Number of packets."
    ::= { unisCBQoSAtmPvcAccountingRunInfoEntry 1 }

unisCBQoSAtmPvcAccountingBytes OBJECT-TYPE
    SYNTAX Counter64
    MAX-ACCESS read-only
    STATUS current
    DESCRIPTION
        "Number of bytes."
    ::= { unisCBQoSAtmPvcAccountingRunInfoEntry 2 }

-- FR Interface PVC: policy Running statistics information

unisCBQoSFrPvcStaticsObjects OBJECT IDENTIFIER ::= { unisCBQoSApplyPolicyStaticsObjects 3 }

-- FR PVC CBQ statistics

unisCBQoSFrPvcCbqRunInfoTable OBJECT-TYPE
    SYNTAX SEQUENCE OF UnisCBQoSFrPvcCbqRunInfoEntry
    MAX-ACCESS not-accessible
    STATUS current
    DESCRIPTION
        "A table of FR PVC CBQ Running statistics.
         When policy using queue behavior is applied on FR PVC
         will using Class Based Queuing."
    ::= { unisCBQoSFrPvcStaticsObjects 1 }

unisCBQoSFrPvcCbqRunInfoEntry OBJECT-TYPE
    SYNTAX UnisCBQoSFrPvcCbqRunInfoEntry
    MAX-ACCESS not-accessible
    STATUS current
    DESCRIPTION
        "FR PVC CBQ statistics entry."
    INDEX { unisCBQoSFrPvcApplyPolicyIfIndex, unisCBQoSFrPvcApplyPolicyDlciNum }
    ::= { unisCBQoSFrPvcCbqRunInfoTable 1 }

UnisCBQoSFrPvcCbqRunInfoEntry ::=
    SEQUENCE
    {
        unisCBQoSFrPvcCbqQueueSize
            Integer32,
        unisCBQoSFrPvcCbqDiscard
            Counter64,
        unisCBQoSFrPvcCbqEfQueueSize
            Integer32,
        unisCBQoSFrPvcCbqAfQueueSize
            Integer32,
        unisCBQoSFrPvcCbqBeQueueSize
            Integer32,
        unisCBQoSFrPvcCbqBeActiveQueueNum
            Integer32,
        unisCBQoSFrPvcCbqBeMaxActiveQueueNum
            Integer32,
        unisCBQoSFrPvcCbqBeTotalQueueNum
            Integer32,
        unisCBQoSFrPvcCbqAfAllocatedQueueNum
            Integer32
    }

unisCBQoSFrPvcCbqQueueSize OBJECT-TYPE
    SYNTAX Integer32
    MAX-ACCESS read-only
    STATUS current
    DESCRIPTION
        "Packet number of CBQ queue."
    ::= { unisCBQoSFrPvcCbqRunInfoEntry 1 }

unisCBQoSFrPvcCbqDiscard OBJECT-TYPE
    SYNTAX Counter64
    MAX-ACCESS read-only
    STATUS current
    DESCRIPTION
        "The number of discarded packets which could not be enqueued."
    ::= { unisCBQoSFrPvcCbqRunInfoEntry 2 }

unisCBQoSFrPvcCbqEfQueueSize OBJECT-TYPE
    SYNTAX Integer32
    MAX-ACCESS read-only
    STATUS current
    DESCRIPTION
        "Packet number of EF queue."
    ::= { unisCBQoSFrPvcCbqRunInfoEntry 3 }

unisCBQoSFrPvcCbqAfQueueSize OBJECT-TYPE
    SYNTAX Integer32
    MAX-ACCESS read-only
    STATUS current
    DESCRIPTION
        "Packet number of AF queue."
    ::= { unisCBQoSFrPvcCbqRunInfoEntry 4 }

unisCBQoSFrPvcCbqBeQueueSize OBJECT-TYPE
    SYNTAX Integer32
    MAX-ACCESS read-only
    STATUS current
    DESCRIPTION
        "Packet number of BE queue."
    ::= { unisCBQoSFrPvcCbqRunInfoEntry 5 }

unisCBQoSFrPvcCbqBeActiveQueueNum OBJECT-TYPE
    SYNTAX Integer32
    MAX-ACCESS read-only
    STATUS current
    DESCRIPTION
        "The packet number of Active Be Queue."
    ::= { unisCBQoSFrPvcCbqRunInfoEntry 6 }

unisCBQoSFrPvcCbqBeMaxActiveQueueNum OBJECT-TYPE
    SYNTAX Integer32
    MAX-ACCESS read-only
    STATUS current
    DESCRIPTION
        "The max packet number of Active Be Queue."
    ::= { unisCBQoSFrPvcCbqRunInfoEntry 7 }

unisCBQoSFrPvcCbqBeTotalQueueNum OBJECT-TYPE
    SYNTAX Integer32
    MAX-ACCESS read-only
    STATUS current
    DESCRIPTION
        "The total packet number of Be Queue."
    ::= { unisCBQoSFrPvcCbqRunInfoEntry 8 }

unisCBQoSFrPvcCbqAfAllocatedQueueNum OBJECT-TYPE
    SYNTAX Integer32
    MAX-ACCESS read-only
    STATUS current
    DESCRIPTION
        "The Allocated packet number of AF Queue."
    ::= { unisCBQoSFrPvcCbqRunInfoEntry 9 }

-- Class match statistics

unisCBQoSFrPvcClassMatchRunInfoTable OBJECT-TYPE
    SYNTAX SEQUENCE OF UnisCBQoSFrPvcClassMatchRunInfoEntry
    MAX-ACCESS not-accessible
    STATUS current
    DESCRIPTION
        "A table of Running statistics for matching a classifier
         in a QoS policy applied on FR PVC."
    ::= { unisCBQoSFrPvcStaticsObjects 2 }

unisCBQoSFrPvcClassMatchRunInfoEntry OBJECT-TYPE
    SYNTAX UnisCBQoSFrPvcClassMatchRunInfoEntry
    MAX-ACCESS not-accessible
    STATUS current
    DESCRIPTION
        "Classifier matching statistics entry."
    INDEX { unisCBQoSFrPvcApplyPolicyIfIndex,
            unisCBQoSFrPvcApplyPolicyDlciNum,
            unisCBQoSFrPvcApplyPolicyDirection,
            unisCBQoSPolicyClassIndex }
    ::= { unisCBQoSFrPvcClassMatchRunInfoTable 1 }

UnisCBQoSFrPvcClassMatchRunInfoEntry ::=
    SEQUENCE
    {
        unisCBQoSFrPvcClassMatchedPackets
            Counter64,
        unisCBQoSFrPvcClassMatchedBytes
            Counter64,
        unisCBQoSFrPvcClassAverageRate
            Counter64
    }

unisCBQoSFrPvcClassMatchedPackets OBJECT-TYPE
    SYNTAX Counter64
    MAX-ACCESS read-only
    STATUS current
    DESCRIPTION
        "Number of packets matching a class in a QoS policy."
    ::= { unisCBQoSFrPvcClassMatchRunInfoEntry 1 }

unisCBQoSFrPvcClassMatchedBytes OBJECT-TYPE
    SYNTAX Counter64
    MAX-ACCESS read-only
    STATUS current
    DESCRIPTION
        "Number of bytes matching a class in a QoS policy."
    ::= { unisCBQoSFrPvcClassMatchRunInfoEntry 2 }

unisCBQoSFrPvcClassAverageRate OBJECT-TYPE
    SYNTAX Counter64
    MAX-ACCESS read-only
    STATUS current
    DESCRIPTION
        "Average rate matching a class of the last 5 minutes."
    ::= { unisCBQoSFrPvcClassMatchRunInfoEntry 3 }

-- CAR statistics

unisCBQoSFrPvcCarRunInfoTable OBJECT-TYPE
    SYNTAX SEQUENCE OF UnisCBQoSFrPvcCarRunInfoEntry
    MAX-ACCESS not-accessible
    STATUS current
    DESCRIPTION
        "A table of Running statistics for CAR
         in a QoS policy applied on FR PVC."
    ::= { unisCBQoSFrPvcStaticsObjects 3 }

unisCBQoSFrPvcCarRunInfoEntry OBJECT-TYPE
    SYNTAX UnisCBQoSFrPvcCarRunInfoEntry
    MAX-ACCESS not-accessible
    STATUS current
    DESCRIPTION
        "CAR statistics entry."
    INDEX { unisCBQoSFrPvcApplyPolicyIfIndex,
            unisCBQoSFrPvcApplyPolicyDlciNum,
            unisCBQoSFrPvcApplyPolicyDirection,
            unisCBQoSPolicyClassIndex }
    ::= { unisCBQoSFrPvcCarRunInfoTable 1 }

UnisCBQoSFrPvcCarRunInfoEntry ::=
    SEQUENCE
    {
        unisCBQoSFrPvcCarConformPackets
            Counter64,
        unisCBQoSFrPvcCarConformBytes
            Counter64,
        unisCBQoSFrPvcCarExceedPackets
            Counter64,
        unisCBQoSFrPvcCarExceedBytes
            Counter64
    }

unisCBQoSFrPvcCarConformPackets OBJECT-TYPE
    SYNTAX Counter64
    MAX-ACCESS read-only
    STATUS current
    DESCRIPTION
        "Number of packets conform CIR."
    ::= { unisCBQoSFrPvcCarRunInfoEntry 1 }

unisCBQoSFrPvcCarConformBytes OBJECT-TYPE
    SYNTAX Counter64
    MAX-ACCESS read-only
    STATUS current
    DESCRIPTION
        "Number of bytes conform CIR."
    ::= { unisCBQoSFrPvcCarRunInfoEntry 2 }

unisCBQoSFrPvcCarExceedPackets OBJECT-TYPE
    SYNTAX Counter64
    MAX-ACCESS read-only
    STATUS current
    DESCRIPTION
        "Number of packets exceed CIR."
    ::= { unisCBQoSFrPvcCarRunInfoEntry 3 }

unisCBQoSFrPvcCarExceedBytes OBJECT-TYPE
    SYNTAX Counter64
    MAX-ACCESS read-only
    STATUS current
    DESCRIPTION
        "Number of bytes exceed CIR."
    ::= { unisCBQoSFrPvcCarRunInfoEntry 4 }

-- GTS statistics

unisCBQoSFrPvcGtsRunInfoTable OBJECT-TYPE
    SYNTAX SEQUENCE OF UnisCBQoSFrPvcGtsRunInfoEntry
    MAX-ACCESS not-accessible
    STATUS current
    DESCRIPTION
        "A table of Running statistics for GTS
         in a QoS policy applied on FR PVC."
    ::= { unisCBQoSFrPvcStaticsObjects 4 }

unisCBQoSFrPvcGtsRunInfoEntry OBJECT-TYPE
    SYNTAX UnisCBQoSFrPvcGtsRunInfoEntry
    MAX-ACCESS not-accessible
    STATUS current
    DESCRIPTION
        "GTS statistics entry."
    INDEX { unisCBQoSFrPvcApplyPolicyIfIndex,
            unisCBQoSFrPvcApplyPolicyDlciNum,
            unisCBQoSFrPvcApplyPolicyDirection,
            unisCBQoSPolicyClassIndex }
    ::= { unisCBQoSFrPvcGtsRunInfoTable 1 }

UnisCBQoSFrPvcGtsRunInfoEntry ::=
    SEQUENCE
    {
        unisCBQoSFrPvcGtsPassedPackets
            Counter64,
        unisCBQoSFrPvcGtsPassedBytes
            Counter64,
        unisCBQoSFrPvcGtsDiscardedPackets
            Counter64,
        unisCBQoSFrPvcGtsDiscardedBytes
            Counter64,
        unisCBQoSFrPvcGtsDelayedPackets
            Counter64,
        unisCBQoSFrPvcGtsDelayedBytes
            Counter64,
        unisCBQoSFrPvcGtsQueueSize
            Integer32
    }

unisCBQoSFrPvcGtsPassedPackets OBJECT-TYPE
    SYNTAX Counter64
    MAX-ACCESS read-only
    STATUS current
    DESCRIPTION
        "Number of packets passed by GTS."
    ::= { unisCBQoSFrPvcGtsRunInfoEntry 1 }

unisCBQoSFrPvcGtsPassedBytes OBJECT-TYPE
    SYNTAX Counter64
    MAX-ACCESS read-only
    STATUS current
    DESCRIPTION
        "Number of bytes passed by GTS."
    ::= { unisCBQoSFrPvcGtsRunInfoEntry 2 }

unisCBQoSFrPvcGtsDiscardedPackets OBJECT-TYPE
    SYNTAX Counter64
    MAX-ACCESS read-only
    STATUS current
    DESCRIPTION
        "Number of packets discarded by GTS."
    ::= { unisCBQoSFrPvcGtsRunInfoEntry 3 }

unisCBQoSFrPvcGtsDiscardedBytes OBJECT-TYPE
    SYNTAX Counter64
    MAX-ACCESS read-only
    STATUS current
    DESCRIPTION
        "Number of bytes discarded by GTS."
    ::= { unisCBQoSFrPvcGtsRunInfoEntry 4 }

unisCBQoSFrPvcGtsDelayedPackets OBJECT-TYPE
    SYNTAX Counter64
    MAX-ACCESS read-only
    STATUS current
    DESCRIPTION
        "Number of packets delayed by GTS."
    ::= { unisCBQoSFrPvcGtsRunInfoEntry 5 }

unisCBQoSFrPvcGtsDelayedBytes OBJECT-TYPE
    SYNTAX Counter64
    MAX-ACCESS read-only
    STATUS current
    DESCRIPTION
        "Number of bytes delayed by GTS."
    ::= { unisCBQoSFrPvcGtsRunInfoEntry 6 }

unisCBQoSFrPvcGtsQueueSize OBJECT-TYPE
    SYNTAX Integer32
    MAX-ACCESS read-only
    STATUS current
    DESCRIPTION
        "Packet number of GTS queue."
    ::= { unisCBQoSFrPvcGtsRunInfoEntry 7 }

-- Remark statistics

unisCBQoSFrPvcRemarkRunInfoTable OBJECT-TYPE
    SYNTAX SEQUENCE OF UnisCBQoSFrPvcRemarkRunInfoEntry
    MAX-ACCESS not-accessible
    STATUS current
    DESCRIPTION
        "A table of Running statistics for remarking
         in a QoS policy applied on FR PVC."
    ::= { unisCBQoSFrPvcStaticsObjects 5 }

unisCBQoSFrPvcRemarkRunInfoEntry OBJECT-TYPE
    SYNTAX UnisCBQoSFrPvcRemarkRunInfoEntry
    MAX-ACCESS not-accessible
    STATUS current
    DESCRIPTION
        "Remarking statistics entry."
    INDEX { unisCBQoSFrPvcApplyPolicyIfIndex,
            unisCBQoSFrPvcApplyPolicyDlciNum,
            unisCBQoSFrPvcApplyPolicyDirection,
            unisCBQoSPolicyClassIndex }
    ::= { unisCBQoSFrPvcRemarkRunInfoTable 1 }

UnisCBQoSFrPvcRemarkRunInfoEntry ::=
    SEQUENCE
    {
        unisCBQoSFrPvcRemarkedPackets
            Counter64
    }

unisCBQoSFrPvcRemarkedPackets OBJECT-TYPE
    SYNTAX Counter64
    MAX-ACCESS read-only
    STATUS current
    DESCRIPTION
        "Number of packets remarked."
    ::= { unisCBQoSFrPvcRemarkRunInfoEntry 1 }

-- Queue statistics

unisCBQoSFrPvcQueueRunInfoTable OBJECT-TYPE
    SYNTAX SEQUENCE OF UnisCBQoSFrPvcQueueRunInfoEntry
    MAX-ACCESS not-accessible
    STATUS current
    DESCRIPTION
        "A table of Running statistics for queue
        in a QoS policy applied on FR PVC."
    ::= { unisCBQoSFrPvcStaticsObjects 6 }

unisCBQoSFrPvcQueueRunInfoEntry OBJECT-TYPE
    SYNTAX UnisCBQoSFrPvcQueueRunInfoEntry
    MAX-ACCESS not-accessible
    STATUS current
    DESCRIPTION
        "Queue statistics entry."
    INDEX { unisCBQoSFrPvcApplyPolicyIfIndex,
            unisCBQoSFrPvcApplyPolicyDlciNum,
            unisCBQoSFrPvcApplyPolicyDirection,
            unisCBQoSPolicyClassIndex }
    ::= { unisCBQoSFrPvcQueueRunInfoTable 1 }

UnisCBQoSFrPvcQueueRunInfoEntry ::=
    SEQUENCE
    {
        unisCBQoSFrPvcQueueMatchedPackets
            Counter64,
        unisCBQoSFrPvcQueueMatchedBytes
            Counter64,
        unisCBQoSFrPvcQueueEnqueuedPackets
            Counter64,
        unisCBQoSFrPvcQueueEnqueuedBytes
            Counter64,
        unisCBQoSFrPvcQueueDiscardedPackets
            Counter64,
        unisCBQoSFrPvcQueueDiscardedBytes
            Counter64
    }

unisCBQoSFrPvcQueueMatchedPackets OBJECT-TYPE
    SYNTAX Counter64
    MAX-ACCESS read-only
    STATUS current
    DESCRIPTION
        "Number of packets matched to enqueue."
    ::= { unisCBQoSFrPvcQueueRunInfoEntry 1 }

unisCBQoSFrPvcQueueMatchedBytes OBJECT-TYPE
    SYNTAX Counter64
    MAX-ACCESS read-only
    STATUS current
    DESCRIPTION
        "Number of bytes matched to en-queue."
    ::= { unisCBQoSFrPvcQueueRunInfoEntry 2 }

unisCBQoSFrPvcQueueEnqueuedPackets OBJECT-TYPE
    SYNTAX Counter64
    MAX-ACCESS read-only
    STATUS current
    DESCRIPTION
        "Number of packets en-queued."
    ::= { unisCBQoSFrPvcQueueRunInfoEntry 3 }

unisCBQoSFrPvcQueueEnqueuedBytes OBJECT-TYPE
    SYNTAX Counter64
    MAX-ACCESS read-only
    STATUS current
    DESCRIPTION
        "Number of bytes enqueued."
    ::= { unisCBQoSFrPvcQueueRunInfoEntry 4 }

unisCBQoSFrPvcQueueDiscardedPackets OBJECT-TYPE
    SYNTAX Counter64
    MAX-ACCESS read-only
    STATUS current
    DESCRIPTION
        "Number of packets discarded when enqueued by discard method."
    ::= { unisCBQoSFrPvcQueueRunInfoEntry 5 }

unisCBQoSFrPvcQueueDiscardedBytes OBJECT-TYPE
    SYNTAX Counter64
    MAX-ACCESS read-only
    STATUS current
    DESCRIPTION
        "Number of bytes discarded when enqueued by discard method."
    ::= { unisCBQoSFrPvcQueueRunInfoEntry 6 }

-- WRED statistics

unisCBQoSFrPvcWredRunInfoTable OBJECT-TYPE
    SYNTAX SEQUENCE OF UnisCBQoSFrPvcWredRunInfoEntry
    MAX-ACCESS not-accessible
    STATUS current
    DESCRIPTION
        "A table of Running statistics for WRED
         in a QoS policy applied on FR PVC.
        "
    ::= { unisCBQoSFrPvcStaticsObjects 7 }

unisCBQoSFrPvcWredRunInfoEntry OBJECT-TYPE
    SYNTAX UnisCBQoSFrPvcWredRunInfoEntry
    MAX-ACCESS not-accessible
    STATUS current
    DESCRIPTION
        "WRED statistics entry."
    INDEX { unisCBQoSFrPvcApplyPolicyIfIndex,
            unisCBQoSFrPvcApplyPolicyDlciNum,
            unisCBQoSFrPvcApplyPolicyDirection,
            unisCBQoSPolicyClassIndex,
            unisCBQoSWredClassValue }
    ::= { unisCBQoSFrPvcWredRunInfoTable 1 }

UnisCBQoSFrPvcWredRunInfoEntry ::=
    SEQUENCE
    {
        unisCBQoSFrPvcWredRandomDiscardedPackets
            Counter64,
        unisCBQoSFrPvcWredTailDiscardedPackets
            Counter64
    }

unisCBQoSFrPvcWredRandomDiscardedPackets OBJECT-TYPE
    SYNTAX Counter64
    MAX-ACCESS read-only
    STATUS current
    DESCRIPTION
        "Number of packets randomly discarded by WRED."
    ::= { unisCBQoSFrPvcWredRunInfoEntry 1 }

unisCBQoSFrPvcWredTailDiscardedPackets OBJECT-TYPE
    SYNTAX Counter64
    MAX-ACCESS read-only
    STATUS current
    DESCRIPTION
        "Number of packets tail-discarded by WRED."
    ::= { unisCBQoSFrPvcWredRunInfoEntry 2 }

--
-- nodes of unisCBQoSFrPvcAccountingRunInfoTable
--
unisCBQoSFrPvcAccountingRunInfoTable OBJECT-TYPE
    SYNTAX SEQUENCE OF UnisCBQoSFrPvcAccountingRunInfoEntry
    MAX-ACCESS not-accessible
    STATUS current
    DESCRIPTION
        "A table of Running statistics for account
         in a QoS policy applied on the interface."
    ::= { unisCBQoSFrPvcStaticsObjects 8 }

unisCBQoSFrPvcAccountingRunInfoEntry OBJECT-TYPE
    SYNTAX UnisCBQoSFrPvcAccountingRunInfoEntry
    MAX-ACCESS not-accessible
    STATUS current
    DESCRIPTION
        "Account statistics entry."
    INDEX { unisCBQoSFrPvcApplyPolicyIfIndex,
            unisCBQoSFrPvcApplyPolicyDlciNum,
            unisCBQoSFrPvcApplyPolicyDirection,
            unisCBQoSPolicyClassIndex,
            unisCBQoSWredClassValue
          }
    ::= { unisCBQoSFrPvcAccountingRunInfoTable 1 }

UnisCBQoSFrPvcAccountingRunInfoEntry ::=
    SEQUENCE
    {
        unisCBQoSFrPvcAccountingPackets
            Counter64,
        unisCBQoSFrPvcAccountingBytes
            Counter64
    }

unisCBQoSFrPvcAccountingPackets OBJECT-TYPE
    SYNTAX Counter64
    MAX-ACCESS read-only
    STATUS current
    DESCRIPTION
        "Number of packets."
    ::= { unisCBQoSFrPvcAccountingRunInfoEntry 1 }

unisCBQoSFrPvcAccountingBytes OBJECT-TYPE
    SYNTAX Counter64
    MAX-ACCESS read-only
    STATUS current
    DESCRIPTION
        "Number of bytes."
    ::= { unisCBQoSFrPvcAccountingRunInfoEntry 2 }

-- Ethernet Interface VLAN: policy Running statistics information

unisCBQoSVlanStaticsObjects OBJECT IDENTIFIER ::= { unisCBQoSApplyPolicyStaticsObjects 4 }

-- Class match statistics

unisCBQoSVlanClassMatchRunInfoTable OBJECT-TYPE
    SYNTAX SEQUENCE OF UnisCBQoSVlanClassMatchRunInfoEntry
    MAX-ACCESS not-accessible
    STATUS current
    DESCRIPTION
        "A table of Running statistics for matching a classifier
         in a QoS policy applied on Ethernet VLAN.
        "
    ::= { unisCBQoSVlanStaticsObjects 1 }

unisCBQoSVlanClassMatchRunInfoEntry OBJECT-TYPE
    SYNTAX UnisCBQoSVlanClassMatchRunInfoEntry
    MAX-ACCESS not-accessible
    STATUS current
    DESCRIPTION
        "Classifier matching statistics entry."
    INDEX { unisCBQoSVlanApplyPolicyVlanid,
            unisCBQoSVlanApplyPolicyDirection,
            unisCBQoSPolicyClassIndex }
    ::= { unisCBQoSVlanClassMatchRunInfoTable 1 }

UnisCBQoSVlanClassMatchRunInfoEntry ::=
    SEQUENCE
    {
        unisCBQoSVlanClassMatchedPackets
            Counter64
    }

unisCBQoSVlanClassMatchedPackets OBJECT-TYPE
    SYNTAX Counter64
    MAX-ACCESS read-only
    STATUS current
    DESCRIPTION
        "Number of packets matching a class in a QoS policy."
    ::= { unisCBQoSVlanClassMatchRunInfoEntry 1 }

--
-- nodes of unisCBQoSIfVlanAccountingRunInfoTable
--
unisCBQoSVlanAccountingRunInfoTable OBJECT-TYPE
    SYNTAX SEQUENCE OF UnisCBQoSVlanAccountingRunInfoEntry
    MAX-ACCESS not-accessible
    STATUS current
    DESCRIPTION
        "A table of Running statistics for account
         in a QoS policy applied on the interface."
    ::= { unisCBQoSVlanStaticsObjects 2 }

unisCBQoSVlanAccountingRunInfoEntry OBJECT-TYPE
    SYNTAX UnisCBQoSVlanAccountingRunInfoEntry
    MAX-ACCESS not-accessible
    STATUS current
    DESCRIPTION
        "Account statistics entry."
    INDEX { unisCBQoSVlanApplyPolicyVlanid,
            unisCBQoSVlanApplyPolicyDirection,
            unisCBQoSPolicyClassIndex }
    ::= { unisCBQoSVlanAccountingRunInfoTable 1 }

UnisCBQoSVlanAccountingRunInfoEntry ::=
    SEQUENCE
    {
        unisCBQoSVlanAccountingPackets
            Counter64,
        unisCBQoSVlanAccountingBytes
            Counter64
    }

unisCBQoSVlanAccountingPackets OBJECT-TYPE
    SYNTAX Counter64
    MAX-ACCESS read-only
    STATUS current
    DESCRIPTION
        "Number of packets."
    ::= { unisCBQoSVlanAccountingRunInfoEntry 1 }

unisCBQoSVlanAccountingBytes OBJECT-TYPE
    SYNTAX Counter64
    MAX-ACCESS read-only
    STATUS current
    DESCRIPTION
        "Number of bytes."
    ::= { unisCBQoSVlanAccountingRunInfoEntry 2 }

-- Index Object
unisCBQoSApplyPolicyIndexObjects OBJECT IDENTIFIER
    ::= { unisCBQoSApplyPolicyStaticsObjects 5 }

--
-- ApplyObjectTable
--
unisCBQoSApplyObjectTable OBJECT-TYPE
    SYNTAX SEQUENCE OF UnisCBQoSApplyObjectEntry
    MAX-ACCESS not-accessible
    STATUS current
    DESCRIPTION
        "A table of QoS apply object index.  It provides the function
         of querying the information of QoS apply object, which
         consists of interface type, interface index, ATM PVC, FR DLCI
         and nesting policy index, using QoS apply object index."
    ::= { unisCBQoSApplyPolicyIndexObjects 1 }

unisCBQoSApplyObjectEntry OBJECT-TYPE
    SYNTAX UnisCBQoSApplyObjectEntry
    MAX-ACCESS not-accessible
    STATUS current
    DESCRIPTION
        "QoS apply object index entry."
    INDEX { unisCBQoSApplyObjectIndex }
    ::= { unisCBQoSApplyObjectTable 1 }

UnisCBQoSApplyObjectEntry ::=
    SEQUENCE
    {
        unisCBQoSApplyObjectIndex
            Unsigned32,
        unisCBQoSApplyObjectType
            ApplyObjectType,
        unisCBQoSApplyObjectDirection
            DirectionType,
        unisCBQoSApplyObjectMainSite
            Unsigned32,
        unisCBQoSApplyObjectSubChannel
            Unsigned32,
        unisCBQoSApplyObjectSubClass
            Unsigned32,
        unisCBQoSApplyObjectSubClassSec
            Unsigned32
    }

unisCBQoSApplyObjectIndex OBJECT-TYPE
    SYNTAX Unsigned32
    MAX-ACCESS not-accessible
    STATUS current
    DESCRIPTION
        "QoS apply object index.  It represents the unique identifier
         of QoS policy applied position.  It generates when QoS policy
         is applied considering ifIndex, VLAN ID, ATM PVC, FR DLCI and
         policy nesting."
    ::= { unisCBQoSApplyObjectEntry 1 }

unisCBQoSApplyObjectType OBJECT-TYPE
    SYNTAX ApplyObjectType
    MAX-ACCESS read-only
    STATUS current
    DESCRIPTION
        "Apply object type."
    ::= { unisCBQoSApplyObjectEntry 2 }

unisCBQoSApplyObjectDirection OBJECT-TYPE
    SYNTAX DirectionType
    MAX-ACCESS read-only
    STATUS current
    DESCRIPTION
        "The direction of QoS apply object."
    ::= { unisCBQoSApplyObjectEntry 3 }

unisCBQoSApplyObjectMainSite OBJECT-TYPE
    SYNTAX Unsigned32
    MAX-ACCESS read-only
    STATUS current
    DESCRIPTION
        "Its value depends on unisCBQoSApplyObjectType.
         It represents VLAN ID when unisCBQoSApplyObjectType
         is vlan, and represents chassis ID when unisCBQoSApplyObjectType
         is controlPlane, otherwise it represents ifIndex."
    ::= { unisCBQoSApplyObjectEntry 4 }

unisCBQoSApplyObjectSubChannel OBJECT-TYPE
    SYNTAX Unsigned32
    MAX-ACCESS read-only
    STATUS current
    DESCRIPTION
        "Its value depends on unisCBQoSApplyObjectType.
         It represents the value of VPI/VCI, of which high 16-bits
         is VPI and low 16-bits is VCI, when unisCBQoSApplyObjectType
         is atmPvc.
         It represents the value of data link connection identifier
         in FR network, when unisCBQoSApplyObjectType is frDlci.
         It represents slot ID, when unisCBQoSApplyObjectType is controlPlane.
         Otherwise the value is '0xFFFFFFFF'."
    ::= { unisCBQoSApplyObjectEntry 5 }

unisCBQoSApplyObjectSubClass OBJECT-TYPE
    SYNTAX Unsigned32
    MAX-ACCESS read-only
    STATUS current
    DESCRIPTION
        "The value represents level-1 sub class index when the QoS
         apply object is level-2 or level-3 nesting policy.  Otherwise
         the value is '0xFFFFFFFF'."
    ::= { unisCBQoSApplyObjectEntry 6 }

unisCBQoSApplyObjectSubClassSec OBJECT-TYPE
    SYNTAX Unsigned32
    MAX-ACCESS read-only
    STATUS current
    DESCRIPTION
        "The value represents level-2 sub class index when the QoS
         apply object is level-3 nesting policy.  Otherwise
         the value is '0xFFFFFFFF'."
    ::= { unisCBQoSApplyObjectEntry 7 }

--
-- IntApplyObjectTable
--
unisCBQoSIntApplyObjectTable OBJECT-TYPE
    SYNTAX SEQUENCE OF UnisCBQoSIntApplyObjectEntry
    MAX-ACCESS not-accessible
    STATUS current
    DESCRIPTION
        "A table used for querying the QoS apply object indexes by
         interface index.  It is suitable for querying QoS apply
         object indexes for policies applied on Ethernet ports, ATM
         ports and FR ports."
    ::= { unisCBQoSApplyPolicyIndexObjects 2 }

unisCBQoSIntApplyObjectEntry OBJECT-TYPE
    SYNTAX UnisCBQoSIntApplyObjectEntry
    MAX-ACCESS not-accessible
    STATUS current
    DESCRIPTION
        "QoS apply object on interface index querying entry."
    INDEX { unisCBQoSIntApplyObjectIfIndex,
            unisCBQoSApplyObjectDirection }
    ::= { unisCBQoSIntApplyObjectTable 1 }

UnisCBQoSIntApplyObjectEntry ::=
    SEQUENCE
    {
        unisCBQoSIntApplyObjectIfIndex
            Unsigned32,
        unisCBQoSIntApplyObjectIndex
            Unsigned32
    }

unisCBQoSIntApplyObjectIfIndex OBJECT-TYPE
    SYNTAX Unsigned32
    MAX-ACCESS not-accessible
    STATUS current
    DESCRIPTION
        "Interface index."
    ::= { unisCBQoSIntApplyObjectEntry 1 }

unisCBQoSIntApplyObjectIndex OBJECT-TYPE
    SYNTAX Unsigned32
    MAX-ACCESS read-only
    STATUS current
    DESCRIPTION
        "QoS apply object index."
    ::= { unisCBQoSIntApplyObjectEntry 2 }

--
-- VlanApplyObjectTable
--
unisCBQoSVlanApplyObjectTable OBJECT-TYPE
    SYNTAX SEQUENCE OF UnisCBQoSVlanApplyObjectEntry
    MAX-ACCESS not-accessible
    STATUS current
    DESCRIPTION
        "A table used for querying the QoS apply object indexes by VLAN
         ID and policy direction.  It is suitable for querying QoS
         apply object indexes for policies applied on VLANs.  If the
         value of unisCBQoSVlanApplyObjectVlanID is 0, it means querying
         Qos apply object index for policy applied on global."
    ::= { unisCBQoSApplyPolicyIndexObjects 3 }

unisCBQoSVlanApplyObjectEntry OBJECT-TYPE
    SYNTAX UnisCBQoSVlanApplyObjectEntry
    MAX-ACCESS not-accessible
    STATUS current
    DESCRIPTION
        "VLAN apply object entry."
    INDEX { unisCBQoSVlanApplyObjectVlanID,
            unisCBQoSApplyObjectDirection }
    ::= { unisCBQoSVlanApplyObjectTable 1 }

UnisCBQoSVlanApplyObjectEntry ::=
    SEQUENCE
    {
        unisCBQoSVlanApplyObjectVlanID
            Unsigned32,
        unisCBQoSVlanApplyObjectIndex
            Unsigned32
    }

unisCBQoSVlanApplyObjectVlanID OBJECT-TYPE
    SYNTAX Unsigned32 (0..4094)
    MAX-ACCESS not-accessible
    STATUS current
    DESCRIPTION
        "VLAN ID."
    ::= { unisCBQoSVlanApplyObjectEntry 1 }

unisCBQoSVlanApplyObjectIndex OBJECT-TYPE
    SYNTAX Unsigned32
    MAX-ACCESS read-only
    STATUS current
    DESCRIPTION
        "QoS apply object index."
    ::= { unisCBQoSVlanApplyObjectEntry 2 }

--
-- PvcApplyObjectTable
--
unisCBQoSPvcApplyObjectTable OBJECT-TYPE
    SYNTAX SEQUENCE OF UnisCBQoSPvcApplyObjectEntry
    MAX-ACCESS not-accessible
    STATUS current
    DESCRIPTION
        "A table used for querying the QoS apply object indexes by ATM
         PVC or FR DLCI, ifIndex and policy direction.  It is suitable
         for querying QoS apply object indexes for policies applied on
         ATM PVCs or FR DLCIs."
    ::= { unisCBQoSApplyPolicyIndexObjects 4 }

unisCBQoSPvcApplyObjectEntry OBJECT-TYPE
    SYNTAX UnisCBQoSPvcApplyObjectEntry
    MAX-ACCESS not-accessible
    STATUS current
    DESCRIPTION
        "QoS apply object querying entry for ATM PVC or FR
         DLCI."
    INDEX { unisCBQoSPvcApplyObjectIfIndex,
            unisCBQoSPvcApplyObjectPvcID,
            unisCBQoSApplyObjectDirection }
    ::= { unisCBQoSPvcApplyObjectTable 1 }

UnisCBQoSPvcApplyObjectEntry ::=
    SEQUENCE
    {
        unisCBQoSPvcApplyObjectIfIndex
            Unsigned32,
        unisCBQoSPvcApplyObjectPvcID
            Unsigned32,
        unisCBQoSPvcApplyObjectIndex
            Unsigned32
    }

unisCBQoSPvcApplyObjectIfIndex OBJECT-TYPE
    SYNTAX Unsigned32
    MAX-ACCESS not-accessible
    STATUS current
    DESCRIPTION
        "Interface index."
    ::= { unisCBQoSPvcApplyObjectEntry 1 }

unisCBQoSPvcApplyObjectPvcID OBJECT-TYPE
    SYNTAX Unsigned32
    MAX-ACCESS not-accessible
    STATUS current
    DESCRIPTION
        "If the QoS apply object queried is a ATM PVC, its input value
         represents a VPI/VCI.  If the QoS apply object queried is a FR
         DLCI, its input value represents a value of FR DLCI."
    ::= { unisCBQoSPvcApplyObjectEntry 2 }

unisCBQoSPvcApplyObjectIndex OBJECT-TYPE
    SYNTAX Unsigned32
    MAX-ACCESS read-only
    STATUS current
    DESCRIPTION
        "QoS apply object index."
    ::= { unisCBQoSPvcApplyObjectEntry 3 }

--
-- unisCBQoSNestPolicyApplyObjectTable
--
unisCBQoSNestPolicyApplyObjectTable OBJECT-TYPE
    SYNTAX SEQUENCE OF UnisCBQoSNestPolicyApplyObjectEntry
    MAX-ACCESS not-accessible
    STATUS current
    DESCRIPTION
        "A table used for querying the nested QoS policy apply object indexes.
         It is suitable for querying nested QoS apply object indexes for policies
         applied on ifIndex, VLAN ID, ATM PVC or FR DLCI."
    ::= { unisCBQoSApplyPolicyIndexObjects 5 }

unisCBQoSNestPolicyApplyObjectEntry OBJECT-TYPE
    SYNTAX UnisCBQoSNestPolicyApplyObjectEntry
    MAX-ACCESS not-accessible
    STATUS current
    DESCRIPTION
        "QoS apply object on policy querying entry."
    INDEX { unisCBQoSApplyObjectIndex,
            unisCBQoSNestPolicyClassIndex}
    ::= { unisCBQoSNestPolicyApplyObjectTable 1 }

UnisCBQoSNestPolicyApplyObjectEntry ::=
    SEQUENCE
    {
        unisCBQoSNestPolicyClassIndex
            Unsigned32,
        unisCBQoSNestPolicyApplyObjectIndex
            Unsigned32
    }

unisCBQoSNestPolicyClassIndex OBJECT-TYPE
    SYNTAX Unsigned32
    MAX-ACCESS not-accessible
    STATUS current
    DESCRIPTION
        "Policyclass index in father policy."
    ::= { unisCBQoSNestPolicyApplyObjectEntry 1 }

unisCBQoSNestPolicyApplyObjectIndex OBJECT-TYPE
    SYNTAX Unsigned32
    MAX-ACCESS read-only
    STATUS current
    DESCRIPTION
        "QoS apply object index of the son policy."
    ::= { unisCBQoSNestPolicyApplyObjectEntry 2 }

--
-- unisCBQoSCpApplyObjectTable
--
unisCBQoSCpApplyObjectTable OBJECT-TYPE
    SYNTAX SEQUENCE OF UnisCBQoSCpApplyObjectEntry
    MAX-ACCESS not-accessible
    STATUS current
    DESCRIPTION
        "A table used for querying the QoS policy apply object indexes
         by chassis ID and slot ID.  It is suitable for querying QoS apply
         object indexes for policies applied on control plane."
    ::= { unisCBQoSApplyPolicyIndexObjects 6 }

unisCBQoSCpApplyObjectEntry OBJECT-TYPE
    SYNTAX UnisCBQoSCpApplyObjectEntry
    MAX-ACCESS not-accessible
    STATUS current
    DESCRIPTION
        "QoS policy apply object on control plane querying entry."
    INDEX { unisCBQoSCpApplyObjectChassis,
            unisCBQoSCpApplyObjectSlot,
            unisCBQoSApplyObjectDirection}
    ::= { unisCBQoSCpApplyObjectTable 1 }

UnisCBQoSCpApplyObjectEntry ::=
    SEQUENCE
    {
        unisCBQoSCpApplyObjectChassis
            Unsigned32,
        unisCBQoSCpApplyObjectSlot
            Unsigned32,
        unisCBQoSCpApplyObjectIndex
            Unsigned32
    }

unisCBQoSCpApplyObjectChassis OBJECT-TYPE
    SYNTAX Unsigned32
    MAX-ACCESS not-accessible
    STATUS current
    DESCRIPTION
        "Chassis ID."
    ::= { unisCBQoSCpApplyObjectEntry 1 }

unisCBQoSCpApplyObjectSlot OBJECT-TYPE
    SYNTAX Unsigned32
    MAX-ACCESS not-accessible
    STATUS current
    DESCRIPTION
        "Slot ID."
    ::= { unisCBQoSCpApplyObjectEntry 2 }

unisCBQoSCpApplyObjectIndex OBJECT-TYPE
    SYNTAX Unsigned32
    MAX-ACCESS read-only
    STATUS current
    DESCRIPTION
        "QoS apply object index."
    ::= { unisCBQoSCpApplyObjectEntry 3 }

-- Statistics

unisCBQoSStaticsObjects OBJECT IDENTIFIER
    ::= { unisCBQoSApplyPolicyStaticsObjects 6 }

-- CBQ statistics

unisCBQoSCbqRunInfoTable OBJECT-TYPE
    SYNTAX SEQUENCE OF UnisCBQoSCbqRunInfoEntry
    MAX-ACCESS not-accessible
    STATUS current
    DESCRIPTION
        "A table of CBQ running statistics.
         When policy using queue behavior is applied on QoS apply
         object, the QoS apply object will use Class Based Queuing."
    ::= { unisCBQoSStaticsObjects 1 }

unisCBQoSCbqRunInfoEntry OBJECT-TYPE
    SYNTAX UnisCBQoSCbqRunInfoEntry
    MAX-ACCESS not-accessible
    STATUS current
    DESCRIPTION
        "CBQ statistics entry of QoS apply object."
    INDEX { unisCBQoSApplyObjectIndex }
    ::= { unisCBQoSCbqRunInfoTable 1 }

UnisCBQoSCbqRunInfoEntry ::=
    SEQUENCE
    {
        unisCBQoSCbqQueueSize
            Integer32,
        unisCBQoSCbqDiscard
            Counter64,
        unisCBQoSCbqEfQueueSize
            Integer32,
        unisCBQoSCbqAfQueueSize
            Integer32,
        unisCBQoSCbqBeQueueSize
            Integer32,
        unisCBQoSCbqBeActiveQueueNum
            Integer32,
        unisCBQoSCbqBeMaxActiveQueueNum
            Integer32,
        unisCBQoSCbqBeTotalQueueNum
            Integer32,
        unisCBQoSCbqAfAllocatedQueueNum
            Integer32
    }

unisCBQoSCbqQueueSize OBJECT-TYPE
    SYNTAX Integer32
    MAX-ACCESS read-only
    STATUS current
    DESCRIPTION
        "Number of packets in CBQ queue."
    ::= { unisCBQoSCbqRunInfoEntry 1 }

unisCBQoSCbqDiscard OBJECT-TYPE
    SYNTAX Counter64
    MAX-ACCESS read-only
    STATUS current
    DESCRIPTION
        "Number of discarded packets which couldn't queue."
    ::= { unisCBQoSCbqRunInfoEntry 2 }

unisCBQoSCbqEfQueueSize OBJECT-TYPE
    SYNTAX Integer32
    MAX-ACCESS read-only
    STATUS current
    DESCRIPTION
        "Number of packets in EF queue."
    ::= { unisCBQoSCbqRunInfoEntry 3 }

unisCBQoSCbqAfQueueSize OBJECT-TYPE
    SYNTAX Integer32
    MAX-ACCESS read-only
    STATUS current
    DESCRIPTION
        "Number of packets in AF queue."
    ::= { unisCBQoSCbqRunInfoEntry 4 }

unisCBQoSCbqBeQueueSize OBJECT-TYPE
    SYNTAX Integer32
    MAX-ACCESS read-only
    STATUS current
    DESCRIPTION
        "Number of packets in BE Queue."
    ::= { unisCBQoSCbqRunInfoEntry 5 }

unisCBQoSCbqBeActiveQueueNum OBJECT-TYPE
    SYNTAX Integer32
    MAX-ACCESS read-only
    STATUS current
    DESCRIPTION
        "Number of Active BE Queues."
    ::= { unisCBQoSCbqRunInfoEntry 6 }

unisCBQoSCbqBeMaxActiveQueueNum OBJECT-TYPE
    SYNTAX Integer32
    MAX-ACCESS read-only
    STATUS current
    DESCRIPTION
        "The max number of Active BE Queues."
    ::= { unisCBQoSCbqRunInfoEntry 7 }

unisCBQoSCbqBeTotalQueueNum OBJECT-TYPE
    SYNTAX Integer32
    MAX-ACCESS read-only
    STATUS current
    DESCRIPTION
        "Number of total BE Queues."
    ::= { unisCBQoSCbqRunInfoEntry 8 }

unisCBQoSCbqAfAllocatedQueueNum OBJECT-TYPE
    SYNTAX Integer32
    MAX-ACCESS read-only
    STATUS current
    DESCRIPTION
        "Number of allocated AF Queues."
    ::= { unisCBQoSCbqRunInfoEntry 9 }

-- Class match statistics

unisCBQoSClassMatchRunInfoTable OBJECT-TYPE
    SYNTAX SEQUENCE OF UnisCBQoSClassMatchRunInfoEntry
    MAX-ACCESS not-accessible
    STATUS current
    DESCRIPTION
        "A table of running statistics for matching a classifier on a
         QoS apply object."
    ::= { unisCBQoSStaticsObjects 2 }

unisCBQoSClassMatchRunInfoEntry OBJECT-TYPE
    SYNTAX UnisCBQoSClassMatchRunInfoEntry
    MAX-ACCESS not-accessible
    STATUS current
    DESCRIPTION
        "Classifier's matching statistics information entry."
    INDEX { unisCBQoSApplyObjectIndex,
            unisCBQoSPolicyClassIndex }
    ::= { unisCBQoSClassMatchRunInfoTable 1 }

UnisCBQoSClassMatchRunInfoEntry ::=
    SEQUENCE
    {
        unisCBQoSClassMatchedPackets
            Counter64,
        unisCBQoSClassMatchedBytes
            Counter64,
        unisCBQoSClassFwdPktpps
            Unsigned32,
        unisCBQoSClassFwdPktbps
            Unsigned32,
        unisCBQoSClassDropPktpps
            Unsigned32,
        unisCBQoSClassDropPktbps
            Unsigned32,
        unisCBQoSClassFlowStatInterval
            Unsigned32,
        unisCBQoSClassBehaviorStatus
            INTEGER
    }

unisCBQoSClassMatchedPackets OBJECT-TYPE
    SYNTAX Counter64
    MAX-ACCESS read-only
    STATUS current
    DESCRIPTION
        "Number of packets matching a class in a QoS policy."
    ::= { unisCBQoSClassMatchRunInfoEntry 1 }

unisCBQoSClassMatchedBytes OBJECT-TYPE
    SYNTAX Counter64
    MAX-ACCESS read-only
    STATUS current
    DESCRIPTION
        "Number of bytes matching a class in a QoS policy."
    ::= { unisCBQoSClassMatchRunInfoEntry 2 }

unisCBQoSClassFwdPktpps OBJECT-TYPE
    SYNTAX Unsigned32
    MAX-ACCESS read-only
    STATUS current
    DESCRIPTION
        "Average number of packets macthing the class forwarded
         per second in the last interval.
         Unit: pps."
    ::= { unisCBQoSClassMatchRunInfoEntry 3 }

unisCBQoSClassFwdPktbps OBJECT-TYPE
    SYNTAX Unsigned32
    MAX-ACCESS read-only
    STATUS current
    DESCRIPTION
        "Average bits of packets matching the class forwarded
         per second in the last interval.
         Unit: bps."
    ::= { unisCBQoSClassMatchRunInfoEntry 4 }

unisCBQoSClassDropPktpps OBJECT-TYPE
    SYNTAX Unsigned32
    MAX-ACCESS read-only
    STATUS current
    DESCRIPTION
        "Average number of packets matching the class dropped
         per second in the last interval.
         Unit: pps."
    ::= { unisCBQoSClassMatchRunInfoEntry 5 }

unisCBQoSClassDropPktbps OBJECT-TYPE
    SYNTAX Unsigned32
    MAX-ACCESS read-only
    STATUS current
    DESCRIPTION
        "Average bits of packets matching the class dropped
         per second in the last interval.
         Unit: bps."
    ::= { unisCBQoSClassMatchRunInfoEntry 6 }

unisCBQoSClassFlowStatInterval OBJECT-TYPE
    SYNTAX Unsigned32
    MAX-ACCESS read-only
    STATUS current
    DESCRIPTION
        "Interval of collecting traffic statistics.
         Unit: minute."
    ::= { unisCBQoSClassMatchRunInfoEntry 7 }

unisCBQoSClassBehaviorStatus OBJECT-TYPE
    SYNTAX INTEGER
    {
        success(1),
        failure(2),
        partialSuccess(3)
    }
    MAX-ACCESS read-only
    STATUS current
    DESCRIPTION
        "Classifier-behavior applying status."
    ::= { unisCBQoSClassMatchRunInfoEntry 8 }

-- CAR statistics

unisCBQoSCarRunInfoTable OBJECT-TYPE
    SYNTAX SEQUENCE OF UnisCBQoSCarRunInfoEntry
    MAX-ACCESS not-accessible
    STATUS current
    DESCRIPTION
        "A table of running statistics for CAR on a QoS apply object."
    ::= { unisCBQoSStaticsObjects 3 }

unisCBQoSCarRunInfoEntry OBJECT-TYPE
    SYNTAX UnisCBQoSCarRunInfoEntry
    MAX-ACCESS not-accessible
    STATUS current
    DESCRIPTION
        "CAR statistics information entry."
    INDEX { unisCBQoSApplyObjectIndex,
            unisCBQoSPolicyClassIndex }
    ::= { unisCBQoSCarRunInfoTable 1 }

UnisCBQoSCarRunInfoEntry ::=
    SEQUENCE
    {
        unisCBQoSCarGreenPackets
            Counter64,
        unisCBQoSCarGreenBytes
            Counter64,
        unisCBQoSCarRedPackets
            Counter64,
        unisCBQoSCarRedBytes
            Counter64,
        unisCBQoSCarYellowPackets
            Counter64,
        unisCBQoSCarYellowBytes
            Counter64,
        unisCBQoSCarClassName
            OCTET STRING,
        unisCBQoSCarGreenpps
            Counter64,
        unisCBQoSCarGreenbps
            Counter64,
        unisCBQoSCarRedpps
            Counter64,
        unisCBQoSCarRedbps
            Counter64,
        unisCBQoSCarYellowpps
            Counter64,
        unisCBQoSCarYellowbps
            Counter64
    }

unisCBQoSCarGreenPackets OBJECT-TYPE
    SYNTAX Counter64
    MAX-ACCESS read-only
    STATUS current
    DESCRIPTION
        "Number of green packets."
    ::= { unisCBQoSCarRunInfoEntry 1 }

unisCBQoSCarGreenBytes OBJECT-TYPE
    SYNTAX Counter64
    MAX-ACCESS read-only
    STATUS current
    DESCRIPTION
        "Number of green bytes."
    ::= { unisCBQoSCarRunInfoEntry 2 }

unisCBQoSCarRedPackets OBJECT-TYPE
    SYNTAX Counter64
    MAX-ACCESS read-only
    STATUS current
    DESCRIPTION
        "Number of red packets."
    ::= { unisCBQoSCarRunInfoEntry 3 }

unisCBQoSCarRedBytes OBJECT-TYPE
    SYNTAX Counter64
    MAX-ACCESS read-only
    STATUS current
    DESCRIPTION
        "Number of red bytes."
    ::= { unisCBQoSCarRunInfoEntry 4 }

unisCBQoSCarYellowPackets OBJECT-TYPE
    SYNTAX Counter64
    MAX-ACCESS read-only
    STATUS current
    DESCRIPTION
        "Number of yellow packets."
    ::= { unisCBQoSCarRunInfoEntry 5 }

unisCBQoSCarYellowBytes OBJECT-TYPE
    SYNTAX Counter64
    MAX-ACCESS read-only
    STATUS current
    DESCRIPTION
        "Number of yellow bytes."
    ::= { unisCBQoSCarRunInfoEntry 6 }

unisCBQoSCarClassName OBJECT-TYPE
    SYNTAX OCTET STRING (SIZE (1..31))
    MAX-ACCESS read-only
    STATUS current
    DESCRIPTION
        "Name of classifier."
    ::= { unisCBQoSCarRunInfoEntry 7 }

unisCBQoSCarGreenpps OBJECT-TYPE
    SYNTAX Counter64
    MAX-ACCESS read-only
    STATUS current
    DESCRIPTION
        "Average number of green packets matching a class in a QoS policy
         per second in the last interval.
         Unit: pps."
    ::= { unisCBQoSCarRunInfoEntry 8 }

unisCBQoSCarGreenbps OBJECT-TYPE
    SYNTAX Counter64
    MAX-ACCESS read-only
    STATUS current
    DESCRIPTION
       "Average bits of green packets matching a class in a QoS policy
         per second in the last interval.
         Unit: bps."
    ::= { unisCBQoSCarRunInfoEntry 9 }

unisCBQoSCarRedpps OBJECT-TYPE
    SYNTAX Counter64
    MAX-ACCESS read-only
    STATUS current
    DESCRIPTION
        "Average number of red packets matching a class in a QoS policy
         per second in the last interval.
         Unit: pps."
    ::= { unisCBQoSCarRunInfoEntry 10 }

unisCBQoSCarRedbps OBJECT-TYPE
    SYNTAX Counter64
    MAX-ACCESS read-only
    STATUS current
    DESCRIPTION
        "Average bits of red packets matching a class in a QoS policy
         per second in the last interval.
         Unit: bps."
    ::= { unisCBQoSCarRunInfoEntry 11 }

unisCBQoSCarYellowpps OBJECT-TYPE
    SYNTAX Counter64
    MAX-ACCESS read-only
    STATUS current
    DESCRIPTION
        "Average number of yellow packets matching a class in a QoS policy
         per second in the last interval.
         Unit: pps."
    ::= { unisCBQoSCarRunInfoEntry 12 }

unisCBQoSCarYellowbps OBJECT-TYPE
    SYNTAX Counter64
    MAX-ACCESS read-only
    STATUS current
    DESCRIPTION
        "Average bits of yellow packets matching a class in a QoS policy
         per second in the last interval.
         Unit: bps."
    ::= { unisCBQoSCarRunInfoEntry 13 }

-- GTS statistics

unisCBQoSGtsRunInfoTable OBJECT-TYPE
    SYNTAX SEQUENCE OF UnisCBQoSGtsRunInfoEntry
    MAX-ACCESS not-accessible
    STATUS current
    DESCRIPTION
        "A table of running statistics for GTS on a QoS apply object."
    ::= { unisCBQoSStaticsObjects 4 }

unisCBQoSGtsRunInfoEntry OBJECT-TYPE
    SYNTAX UnisCBQoSGtsRunInfoEntry
    MAX-ACCESS not-accessible
    STATUS current
    DESCRIPTION
        "GTS statistics entry."
    INDEX { unisCBQoSApplyObjectIndex,
            unisCBQoSPolicyClassIndex }
    ::= { unisCBQoSGtsRunInfoTable 1 }

UnisCBQoSGtsRunInfoEntry ::=
    SEQUENCE
    {
        unisCBQoSGtsPassedPackets
            Counter64,
        unisCBQoSGtsPassedBytes
            Counter64,
        unisCBQoSGtsDiscardedPackets
            Counter64,
        unisCBQoSGtsDiscardedBytes
            Counter64,
        unisCBQoSGtsDelayedPackets
            Counter64,
        unisCBQoSGtsDelayedBytes
            Counter64,
        unisCBQoSGtsQueueSize
            Integer32
    }

unisCBQoSGtsPassedPackets OBJECT-TYPE
    SYNTAX Counter64
    MAX-ACCESS read-only
    STATUS current
    DESCRIPTION
        "Number of packets passed by GTS."
    ::= { unisCBQoSGtsRunInfoEntry 1 }

unisCBQoSGtsPassedBytes OBJECT-TYPE
    SYNTAX Counter64
    MAX-ACCESS read-only
    STATUS current
    DESCRIPTION
        "Number of bytes passed by GTS."
    ::= { unisCBQoSGtsRunInfoEntry 2 }

unisCBQoSGtsDiscardedPackets OBJECT-TYPE
    SYNTAX Counter64
    MAX-ACCESS read-only
    STATUS current
    DESCRIPTION
        "Number of packets discarded by GTS."
    ::= { unisCBQoSGtsRunInfoEntry 3 }

unisCBQoSGtsDiscardedBytes OBJECT-TYPE
    SYNTAX Counter64
    MAX-ACCESS read-only
    STATUS current
    DESCRIPTION
        "Number of bytes discarded by GTS."
    ::= { unisCBQoSGtsRunInfoEntry 4 }

unisCBQoSGtsDelayedPackets OBJECT-TYPE
    SYNTAX Counter64
    MAX-ACCESS read-only
    STATUS current
    DESCRIPTION
        "Number of packets delayed by GTS."
    ::= { unisCBQoSGtsRunInfoEntry 5 }

unisCBQoSGtsDelayedBytes OBJECT-TYPE
    SYNTAX Counter64
    MAX-ACCESS read-only
    STATUS current
    DESCRIPTION
        "Number of bytes delayed by GTS."
    ::= { unisCBQoSGtsRunInfoEntry 6 }

unisCBQoSGtsQueueSize OBJECT-TYPE
    SYNTAX Integer32
    MAX-ACCESS read-only
    STATUS current
    DESCRIPTION
        "Number of packets in GTS queue."
    ::= { unisCBQoSGtsRunInfoEntry 7 }

-- Remark statistics

unisCBQoSRemarkRunInfoTable OBJECT-TYPE
    SYNTAX SEQUENCE OF UnisCBQoSRemarkRunInfoEntry
    MAX-ACCESS not-accessible
    STATUS current
    DESCRIPTION
        "A table of running statistics for remarking on a QoS apply
         object."
    ::= { unisCBQoSStaticsObjects 5 }

unisCBQoSRemarkRunInfoEntry OBJECT-TYPE
    SYNTAX UnisCBQoSRemarkRunInfoEntry
    MAX-ACCESS not-accessible
    STATUS current
    DESCRIPTION
        "Remarking statistics entry."
    INDEX { unisCBQoSApplyObjectIndex,
            unisCBQoSPolicyClassIndex }
    ::= { unisCBQoSRemarkRunInfoTable 1 }

UnisCBQoSRemarkRunInfoEntry ::=
    SEQUENCE
    {
        unisCBQoSRemarkedPackets
            Counter64
    }

unisCBQoSRemarkedPackets OBJECT-TYPE
    SYNTAX Counter64
    MAX-ACCESS read-only
    STATUS current
    DESCRIPTION
        "Number of remarked packets."
    ::= { unisCBQoSRemarkRunInfoEntry 1 }

-- Queue statistics

unisCBQoSQueueRunInfoTable OBJECT-TYPE
    SYNTAX SEQUENCE OF UnisCBQoSQueueRunInfoEntry
    MAX-ACCESS not-accessible
    STATUS current
    DESCRIPTION
        "A table of running statistics for queue on a QoS apply
         object."
    ::= { unisCBQoSStaticsObjects 6 }

unisCBQoSQueueRunInfoEntry OBJECT-TYPE
    SYNTAX UnisCBQoSQueueRunInfoEntry
    MAX-ACCESS not-accessible
    STATUS current
    DESCRIPTION
        "Queue statistics entry."
    INDEX { unisCBQoSApplyObjectIndex,
            unisCBQoSPolicyClassIndex }
    ::= { unisCBQoSQueueRunInfoTable 1 }

UnisCBQoSQueueRunInfoEntry ::=
    SEQUENCE
    {
        unisCBQoSQueueMatchedPackets
            Counter64,
        unisCBQoSQueueMatchedBytes
            Counter64,
        unisCBQoSQueueEnqueuedPackets
            Counter64,
        unisCBQoSQueueEnqueuedBytes
            Counter64,
        unisCBQoSQueueDiscardedPackets
            Counter64,
        unisCBQoSQueueDiscardedBytes
            Counter64
    }

unisCBQoSQueueMatchedPackets OBJECT-TYPE
    SYNTAX Counter64
    MAX-ACCESS read-only
    STATUS current
    DESCRIPTION
        "Number of packets matched to queue."
    ::= { unisCBQoSQueueRunInfoEntry 1 }

unisCBQoSQueueMatchedBytes OBJECT-TYPE
    SYNTAX Counter64
    MAX-ACCESS read-only
    STATUS current
    DESCRIPTION
        "Number of bytes matched to queue."
    ::= { unisCBQoSQueueRunInfoEntry 2 }

unisCBQoSQueueEnqueuedPackets OBJECT-TYPE
    SYNTAX Counter64
    MAX-ACCESS read-only
    STATUS current
    DESCRIPTION
        "Number of packets queued."
    ::= { unisCBQoSQueueRunInfoEntry 3 }

unisCBQoSQueueEnqueuedBytes OBJECT-TYPE
    SYNTAX Counter64
    MAX-ACCESS read-only
    STATUS current
    DESCRIPTION
        "Number of bytes queued."
    ::= { unisCBQoSQueueRunInfoEntry 4 }

unisCBQoSQueueDiscardedPackets OBJECT-TYPE
    SYNTAX Counter64
    MAX-ACCESS read-only
    STATUS current
    DESCRIPTION
        "Number of packets discarded when queued by discard method."
    ::= { unisCBQoSQueueRunInfoEntry 5 }

unisCBQoSQueueDiscardedBytes OBJECT-TYPE
    SYNTAX Counter64
    MAX-ACCESS read-only
    STATUS current
    DESCRIPTION
        "Number of bytes discarded when queued by discard method."
    ::= { unisCBQoSQueueRunInfoEntry 6 }

-- WRED statistics

unisCBQoSWredRunInfoTable OBJECT-TYPE
    SYNTAX SEQUENCE OF UnisCBQoSWredRunInfoEntry
    MAX-ACCESS not-accessible
    STATUS current
    DESCRIPTION
        "A table of running statistics for WRED on a QoS apply object."
    ::= { unisCBQoSStaticsObjects 7 }

unisCBQoSWredRunInfoEntry OBJECT-TYPE
    SYNTAX UnisCBQoSWredRunInfoEntry
    MAX-ACCESS not-accessible
    STATUS current
    DESCRIPTION
        "WRED statistics entry."
    INDEX { unisCBQoSApplyObjectIndex,
            unisCBQoSPolicyClassIndex,
            unisCBQoSWredClassValue }
    ::= { unisCBQoSWredRunInfoTable 1 }

UnisCBQoSWredRunInfoEntry ::=
    SEQUENCE
    {
        unisCBQoSWredRandomDiscardedPackets
            Counter64,
        unisCBQoSWredTailDiscardedPackets
            Counter64
    }

unisCBQoSWredRandomDiscardedPackets OBJECT-TYPE
    SYNTAX Counter64
    MAX-ACCESS read-only
    STATUS current
    DESCRIPTION
        "Number of packets random-discarded by WRED."
    ::= { unisCBQoSWredRunInfoEntry 1 }

unisCBQoSWredTailDiscardedPackets OBJECT-TYPE
    SYNTAX Counter64
    MAX-ACCESS read-only
    STATUS current
    DESCRIPTION
        "Number of packets tail-discarded by WRED."
    ::= { unisCBQoSWredRunInfoEntry 2 }

--
-- Accounting RunInfo
--
unisCBQoSAccountingRunInfoTable OBJECT-TYPE
    SYNTAX SEQUENCE OF UnisCBQoSAccountingRunInfoEntry
    MAX-ACCESS not-accessible
    STATUS current
    DESCRIPTION
        "A table of running statistics for account on a QoS apply
         object."
    ::= { unisCBQoSStaticsObjects 8 }

unisCBQoSAccountingRunInfoEntry OBJECT-TYPE
    SYNTAX UnisCBQoSAccountingRunInfoEntry
    MAX-ACCESS not-accessible
    STATUS current
    DESCRIPTION
        "Account statistics entry."
    INDEX { unisCBQoSApplyObjectIndex,
            unisCBQoSPolicyClassIndex
          }
    ::= { unisCBQoSAccountingRunInfoTable 1 }

UnisCBQoSAccountingRunInfoEntry ::=
    SEQUENCE
    {
        unisCBQoSAccountingPackets
            Counter64,
        unisCBQoSAccountingBytes
            Counter64,
        unisCBQoSAccountingPktpps
            Counter64,
        unisCBQoSAccountingPktbps
            Counter64
    }

unisCBQoSAccountingPackets OBJECT-TYPE
    SYNTAX Counter64
    MAX-ACCESS read-only
    STATUS current
    DESCRIPTION
        "Number of packets matching a class in a QoS policy."
    ::= { unisCBQoSAccountingRunInfoEntry 1 }

unisCBQoSAccountingBytes OBJECT-TYPE
    SYNTAX Counter64
    MAX-ACCESS read-only
    STATUS current
    DESCRIPTION
        "Number of bytes matching a class in a QoS policy."
    ::= { unisCBQoSAccountingRunInfoEntry 2 }

unisCBQoSAccountingPktpps OBJECT-TYPE
    SYNTAX Counter64
    MAX-ACCESS read-only
    STATUS current
    DESCRIPTION
        "Average number of packets matching a class in a QoS policy
         per second in the last interval.
         Unit: pps."
    ::= { unisCBQoSAccountingRunInfoEntry 3 }

unisCBQoSAccountingPktbps OBJECT-TYPE
    SYNTAX Counter64
    MAX-ACCESS read-only
    STATUS current
    DESCRIPTION
        "Average bits of packets matching a class in a QoS policy
         per second in the last interval.
         Unit: bps."
    ::= { unisCBQoSAccountingRunInfoEntry 4 }

--
-- Policy Accounting RunInfo
--
unisCBQoSPolicyAccRunInfoTable OBJECT-TYPE
    SYNTAX SEQUENCE OF UnisCBQoSPolicyAccRunInfoEntry
    MAX-ACCESS not-accessible
    STATUS current
    DESCRIPTION
        "A table of running statistics for account on a QoS apply
         object."
    ::= { unisCBQoSStaticsObjects 9 }

unisCBQoSPolicyAccRunInfoEntry OBJECT-TYPE
    SYNTAX UnisCBQoSPolicyAccRunInfoEntry
    MAX-ACCESS not-accessible
    STATUS current
    DESCRIPTION
        "Policy account statistics entry."
    INDEX { unisCBQoSApplyObjectIndex }
    ::= { unisCBQoSPolicyAccRunInfoTable 1 }

UnisCBQoSPolicyAccRunInfoEntry ::=
    SEQUENCE
    {
        unisCBQoSPolicyAccPackets
            Counter64,
        unisCBQoSPolicyAccBytes
            Counter64
    }

unisCBQoSPolicyAccPackets OBJECT-TYPE
    SYNTAX Counter64
    MAX-ACCESS read-only
    STATUS current
    DESCRIPTION
        "Number of packets matching a QoS policy."
    ::= { unisCBQoSPolicyAccRunInfoEntry 1 }

unisCBQoSPolicyAccBytes OBJECT-TYPE
    SYNTAX Counter64
    MAX-ACCESS read-only
    STATUS current
    DESCRIPTION
        "Number of bytes matching a QoS policy."
    ::= { unisCBQoSPolicyAccRunInfoEntry 2 }

-- Policy applying status

unisCBQoSApplyingStatusObjects OBJECT IDENTIFIER ::= { unisCBQoSObjects 6 }

-- System status when applying policy

unisCBQoSApplyingStatus OBJECT-TYPE
    SYNTAX INTEGER
    {
        idle(1),
        busy(2)
    }
    MAX-ACCESS read-only
    STATUS current
    DESCRIPTION
        "This object shows the status of the system when applying policy.
        It is forbidden to set or read in this MIB module except current
        table when the value is busy."
    ::= { unisCBQoSApplyingStatusObjects 1 }

-- Notifications

unisCBQoSNotifications OBJECT IDENTIFIER ::= { unisCBQoSObjects 7 }

-- All trap definitions should be placed under this object.

unisCBQoSNotificationsPrefix OBJECT IDENTIFIER ::= { unisCBQoSNotifications 0 }

-- All objects used for TRAP only are defined here.

unisCBQoSIfPolicyChanged NOTIFICATION-TYPE
    OBJECTS
        {
            unisCBQoSIfApplyPolicyIfIndex,
            unisCBQoSIfApplyPolicyDirection
        }
    STATUS current
    DESCRIPTION
        "This notification will be sent when the applying status
        of the policy on the interface is changed."
    ::= { unisCBQoSNotificationsPrefix 1 }

unisCBQoSVlanPolicyChanged NOTIFICATION-TYPE
    OBJECTS
        {
            unisCBQoSVlanApplyPolicyVlanid,
            unisCBQoSVlanApplyPolicyDirection
        }
    STATUS current
    DESCRIPTION
        "This notification will be sent when the applying status
        of the policy on the VLAN is changed."
    ::= { unisCBQoSNotificationsPrefix 2 }

END
