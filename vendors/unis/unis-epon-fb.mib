-- ===========================================================
-- Copyright (c) 2020 Unisyue Technologies Co., Ltd.  All rights reserved.
--
-- Description:
-- The information of EPON fiber backup.
-- Reference:
-- Version: V1.0
-- History:
-- V1.0 created by zhaodan.
-- Initial version for unisEponFBMibObjects of unisEpon.
-- ===========================================================
UNIS-EPON-FB-MIB DEFINITIONS ::= BEGIN

IMPORTS
        unisEpon
    FROM UNIS-OID-MIB
        Integer32, OBJECT-TYPE, MODULE-IDENTITY
    FROM SNMPv2-SMI
        RowStatus
    FROM SNMPv2-TC;


unisEponFBMibObjects MODULE-IDENTITY
    LAST-UPDATED "200711271008Z"
    ORGANIZATION
        "Unisyue Technologies Co., Ltd."
    CONTACT-INFO
        ""
    DESCRIPTION
        "
        The objects in this MIB module are used to manage and
        display current configuration of fiber backup groups
        based on EPON OLT port.
        "
    ::= { unisEpon 6 }

unisEponFBMIB OBJECT IDENTIFIER ::= { unisEponFBMibObjects 1 }
--
-- unisEponFBMIBTable
--

unisEponFBMIBTable OBJECT-TYPE
    SYNTAX      SEQUENCE OF UnisEponFBMIBEntry
    MAX-ACCESS  not-accessible
    STATUS      current
    DESCRIPTION
        "This table defines several optical fiber-backup system parameters."
    ::= { unisEponFBMIB  1 }

unisEponFBMIBEntry OBJECT-TYPE
    SYNTAX      UnisEponFBMIBEntry
    MAX-ACCESS  not-accessible
    STATUS      current
    DESCRIPTION
        "The entry of unisEponFBMIBTable."
    INDEX
        {
            unisEponFBGroupIndex
        }
    ::= { unisEponFBMIBTable 1}


UnisEponFBMIBEntry ::= SEQUENCE
    {
        unisEponFBGroupIndex          Integer32,
        unisEponFBGroupRowStatus      RowStatus,
        unisEponFBMasterPort          Integer32,
        unisEponFBSlavePort           Integer32,
        unisEponFBMasterPortStatus    INTEGER,
        unisEponFBSlavePortStatus     INTEGER,
        unisEponFBSwitchover          INTEGER
    }

unisEponFBGroupIndex OBJECT-TYPE
    SYNTAX      Integer32
    MAX-ACCESS  not-accessible
    STATUS      current
    DESCRIPTION
        "The EPON fiber-backup group ID."
    ::= { unisEponFBMIBEntry 1 }

unisEponFBGroupRowStatus OBJECT-TYPE
    SYNTAX      RowStatus
    MAX-ACCESS  read-create
    STATUS      current
    DESCRIPTION
        "This object allows entry to be created and deleted
        from the unisEponFBMIBTable."
    ::= { unisEponFBMIBEntry 2 }

unisEponFBMasterPort OBJECT-TYPE
    SYNTAX      Integer32
    MAX-ACCESS  read-create
    STATUS      current
    DESCRIPTION
        "OLT port ifindex of the fiber-backup group.
        Use it to set or get the group master port."
    ::= { unisEponFBMIBEntry 3 }

unisEponFBSlavePort OBJECT-TYPE
    SYNTAX      Integer32
    MAX-ACCESS  read-create
    STATUS      current
    DESCRIPTION
        "OLT port ifindex of the fiber-backup group.
        Use it to set or get the group slave port.
        unisEponFBSlavePort must be set after unisEponFBMasterPort.
        "
    ::= { unisEponFBMIBEntry 4 }

unisEponFBMasterPortStatus OBJECT-TYPE
    SYNTAX      INTEGER
        {
            active(1),
            down(2)
        }
    MAX-ACCESS  read-only
    STATUS      current
    DESCRIPTION
        "The master port status of the fiber-backup group.
        The active state indicates that the port's role is master, the olt chip is right
        and the optical module is inserted.
        The down state indicates others conditions."
    ::= { unisEponFBMIBEntry 5 }

unisEponFBSlavePortStatus OBJECT-TYPE
    SYNTAX      INTEGER
        {
            ready(1),
            down(2)
        }
    MAX-ACCESS  read-only
    STATUS      current
    DESCRIPTION
        "The slave port status of the fiber-backup group.
        The ready state indicates that the port's role is slave, the olt chip is right
        and optical module is inserted.
        The down state indicates others conditions."
    ::= { unisEponFBMIBEntry 6 }

unisEponFBSwitchover OBJECT-TYPE
    SYNTAX      INTEGER
        {
            false(1),
            true(2)
        }
    MAX-ACCESS  read-create
    STATUS      current
    DESCRIPTION
        "Switch the fiber backup group's two port manually.
        The group must has two ports
        and the value of unisEponFBSlavePortStatus must be ready before Switchover.
        after Switchover the port's role will be changed.
        The value true is for switch-over.  The default value is false."
    ::= { unisEponFBMIBEntry 7 }

END
