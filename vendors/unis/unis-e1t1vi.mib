-- =============================================================
-- Copyright (c) 2020 Unisyue Technologies Co., Ltd.  All rights reserved.
--
-- Description: E1T1VI MIB
-- Reference:
-- Version: V1.3
-- History:
--   V1.0 2007-04-05 Initial Version by yandehan
--   V1.1 2009-06-08 modified by TONGWEI
--        Added unisE1T1VIUsingTimeslotsRatio
--          and unisE1T1VINotifications
--   V1.2 2010-04-08 modified by TONGWEI
--        Added unisE1T1VIGeneral
--   V1.3 2015-08-19 modified by YUHAIYAN
--        Added unisE1T1VITimeslotsUsedUpCount
--          and unisE1T1VITimeslotSampleInterval
--          and unisE1T1VIUsingTimeslotsPeak
--          and unisE1T1VITrapTimeSlotsThreshold
--       Modified unisE1T1VITrapTimeSlot
-- =============================================================
UNIS-E1T1VI-MIB DEFINITIONS ::= BEGIN
    IMPORTS
        MODULE-IDENTITY, OBJECT-TYPE, Integer32, Unsigned32, NOTIFICATION-TYPE
            FROM SNMPv2-SMI
        ifIndex ,ifDescr
            FROM IF-MIB
        unisCommon
            FROM UNIS-OID-MIB;


-- =============================================================
-- E1T1VI Module
-- =============================================================
unisE1T1VI MODULE-IDENTITY
    LAST-UPDATED    "201508191800Z"         -- Aug. 19, 2015 at 18:00 GMT
    ORGANIZATION
        "Unisyue Technologies Co., Ltd."
    CONTACT-INFO
        ""
    DESCRIPTION
        "This MIB provides E1/T1 voice interface information that are
        excluded by RFC 1213 and RFC 2233"
    REVISION        "201508191800Z"
    DESCRIPTION
        "Added unisE1T1VITimeslotsUsedUpCount
         and unisE1T1VITimeslotSampleInterval
         and unisE1T1VIUsingTimeslotsPeak
         and unisE1T1VITrapTimeSlotThreshold
         Modified unisE1T1VITrapTimeSlot"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { unisCommon 76 }


unisE1T1VITable OBJECT-TYPE
    SYNTAX      SEQUENCE OF UnisE1T1VIEntry
    MAX-ACCESS  not-accessible
    STATUS      current
    DESCRIPTION
        "This table contains E1/T1 voice interface information,
        such as the total number of using time slot."
    ::= { unisE1T1VI 1 }

unisE1T1VIEntry OBJECT-TYPE
    SYNTAX      UnisE1T1VIEntry
    MAX-ACCESS  not-accessible
    STATUS      current
    DESCRIPTION
        "This entry contains E1/T1 voice interface information.
        The index of this Entry is ifIndex defined in ifTable
        of RFC1213-MIB."
    INDEX
        {
            ifIndex
        }
    ::= { unisE1T1VITable 1 }

UnisE1T1VIEntry ::= SEQUENCE
    {
        unisE1T1VIUsingTimeslots    Integer32,
        unisE1T1VIUsingTimeslotsRatio    Integer32,
        unisE1T1VITimeslotsUsedUpCount    Unsigned32,
        unisE1T1VITimeslotSampleInterval    Integer32,
        unisE1T1VIUsingTimeslotsPeak    Integer32,
        unisE1T1VITrapTimeSlotsThreshold    Integer32
    }

unisE1T1VIUsingTimeslots OBJECT-TYPE
    SYNTAX      Integer32
    MAX-ACCESS  read-only
    STATUS      current
    DESCRIPTION
        "The total number of using time slots on this interface."
    ::= { unisE1T1VIEntry 1 }

unisE1T1VIUsingTimeslotsRatio OBJECT-TYPE
    SYNTAX      Integer32
    MAX-ACCESS  read-only
    STATUS      current
    DESCRIPTION
        "The total ratio of using time slots on this interface."
    ::= { unisE1T1VIEntry 2 }

unisE1T1VITimeslotsUsedUpCount OBJECT-TYPE
    SYNTAX      Unsigned32
    MAX-ACCESS  read-only
    STATUS      current
    DESCRIPTION
        "Total number of times that all time slots were used up on this interface."
    ::= { unisE1T1VIEntry 3 }

unisE1T1VITimeslotSampleInterval OBJECT-TYPE
    SYNTAX      Integer32
    MAX-ACCESS  read-write
    STATUS      current
    DESCRIPTION
        "Sampling interval in seconds for used time slots on this interface."
    ::= { unisE1T1VIEntry 4 }

unisE1T1VIUsingTimeslotsPeak OBJECT-TYPE
    SYNTAX      Integer32
    MAX-ACCESS  read-only
    STATUS      current
    DESCRIPTION
        "The peak number of used time slots in the entire sampling period on this interface."
    ::= { unisE1T1VIEntry 5 }

unisE1T1VITrapTimeSlotsThreshold OBJECT-TYPE
    SYNTAX      Integer32
    MAX-ACCESS  read-write
    STATUS      current
    DESCRIPTION
        "When the number of used time slots reaches the threshold, the unisE1T1VITrapTimeSlot trap will
         be sent.  The valid range is from 1 to total number of time slots on the interface."
    ::= { unisE1T1VIEntry 6 }


unisE1T1VINotifications OBJECT IDENTIFIER ::= { unisE1T1VI 2 }
unisE1T1VITrapPrefix    OBJECT IDENTIFIER ::= { unisE1T1VINotifications 0 }

unisE1T1VITrapTimeSlot NOTIFICATION-TYPE
    OBJECTS { ifIndex, ifDescr }
    STATUS current
    DESCRIPTION
        "This trap is sent to the manager under the following
         condition: The number of used time slots of an E1/T1
         interface reaches the threshold."
    ::= { unisE1T1VITrapPrefix 1 }

unisE1T1VIGeneral  OBJECT IDENTIFIER ::= { unisE1T1VI 3 }

unisE1T1VITrapTimeSlotEnable OBJECT-TYPE
    SYNTAX  INTEGER {
            enable(1),
            disable(2)
        }
    MAX-ACCESS  read-write
    STATUS      current
    DESCRIPTION
        "This attribute controls whether the unisE1T1VITrapTimeSlot trap will
        be sent or not."
    DEFVAL { enable }
    ::= { unisE1T1VIGeneral 1 }

END
