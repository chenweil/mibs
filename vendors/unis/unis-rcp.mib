-- =================================================================
-- Copyright (c) 2020 Unisyue Technologies Co., Ltd.  All rights reserved.
--
-- Description: Private MIB for RCP information
-- Reference:
-- Version: V1.0
-- History:
--   V1.0 2006-09-20, Created by ChaiYongfu
-- =================================================================
UNIS-RCP-MIB DEFINITIONS ::= BEGIN
IMPORTS
    unisRCP
        FROM UNIS-OID-MIB
    OBJECT-TYPE, MODULE-IDENTITY, Integer32
        FROM SNMPv2-SMI
    DisplayString, RowStatus, TruthValue
        FROM SNMPv2-TC
    InetAddressType, InetAddress
        FROM INET-ADDRESS-MIB
    InterfaceIndexOrZero
        FROM IF-MIB;

unisRCPMIB MODULE-IDENTITY
    LAST-UPDATED "200609200000Z"
    ORGANIZATION
        "Unisyue Technologies Co., Ltd."
    CONTACT-INFO
        ""
    DESCRIPTION
        "The MIB module is used for managing RCP protocol server."
    REVISION "200609200000Z"
    DESCRIPTION
        "The Initial Version of unisRCPMIB."
    ::= { unisRCP 1 }

unisRCPLeaf OBJECT IDENTIFIER ::= { unisRCPMIB 1 }

unisRCPServerEnableStatus OBJECT-TYPE
    SYNTAX      TruthValue
    MAX-ACCESS  read-write
    STATUS      current
    DESCRIPTION
        "This attribute controls the system wide operation of RCP server.
        The value TRUE means that the RCP server is enabled.
        The value FALSE means that the RCP server is disabled."
    ::= { unisRCPLeaf 1 }

unisRCPConnTimeout OBJECT-TYPE
    SYNTAX      Integer32
    MAX-ACCESS  read-write
    STATUS      current
    DESCRIPTION
        "Specifies the maximum time in seconds that a RCP client connection
        is idle."
    ::= { unisRCPLeaf 2 }

unisRCPRuleTimeout OBJECT-TYPE
    SYNTAX      Integer32
    MAX-ACCESS  read-write
    STATUS      current
    DESCRIPTION
        "Specifies the time in seconds before a RCP rule is aged out.
        If its value is 0, it indicates RCP rule will not be aged out."
    ::= { unisRCPLeaf 3 }

unisRCPServerMaxConn OBJECT-TYPE
    SYNTAX      Integer32
    MAX-ACCESS  read-write
    STATUS      current
    DESCRIPTION
        "Specifies the maximum number of clients that permitted to connect with
        RCP server at the same time."
    ::= { unisRCPLeaf 4 }

unisRCPServerCurConn OBJECT-TYPE
    SYNTAX      Integer32
    MAX-ACCESS  read-only
    STATUS      current
    DESCRIPTION
        "The current actual number of clients that connecting with RCP server."
    ::= { unisRCPLeaf 5 }

unisRCPConnTimeoutMaxValue OBJECT-TYPE
    SYNTAX      Integer32
    MAX-ACCESS  read-only
    STATUS      current
    DESCRIPTION
        "Specifies the maximum value of unisRCPConnTimeout."
    ::= { unisRCPLeaf 6 }

unisRCPRuleTimeoutMaxValue OBJECT-TYPE
    SYNTAX      Integer32
    MAX-ACCESS  read-only
    STATUS      current
    DESCRIPTION
        "Specifies the maximum value of unisRCPRuleTimeout."
    ::= { unisRCPLeaf 7 }

unisRCPServerMaxConnMaxValue OBJECT-TYPE
    SYNTAX      Integer32
    MAX-ACCESS  read-only
    STATUS      current
    DESCRIPTION
        "Specifies the maximum value of unisRCPServerMaxConn."
    ::= { unisRCPLeaf 8 }

unisRCPBalanceGroupIdMinValue OBJECT-TYPE
    SYNTAX      Integer32
    MAX-ACCESS  read-only
    STATUS      current
    DESCRIPTION
        "Specifies the minimum value of balance group identity."
    ::= { unisRCPLeaf 9 }

unisRCPBalanceGroupIdMaxValue OBJECT-TYPE
    SYNTAX      Integer32
    MAX-ACCESS  read-only
    STATUS      current
    DESCRIPTION
        "Specifies the maximum value of balance group identity."
    ::= { unisRCPLeaf 10 }

unisRCPTotalUsers OBJECT-TYPE
    SYNTAX      Integer32
    MAX-ACCESS  read-only
    STATUS      current
    DESCRIPTION
        "Specifies the total number of RCP user."
    ::= { unisRCPLeaf 11 }

unisRCPTotalClientIPs OBJECT-TYPE
    SYNTAX      Integer32
    MAX-ACCESS  read-only
    STATUS      current
    DESCRIPTION
        "Specifies the total number of RCP client IP."
    ::= { unisRCPLeaf 12 }

unisRCPTable OBJECT IDENTIFIER ::= { unisRCPMIB 2 }

unisRCPUserTable OBJECT-TYPE
    SYNTAX      SEQUENCE OF UnisRCPUserEntry
    MAX-ACCESS  not-accessible
    STATUS      current
    DESCRIPTION
        "RCP User Info Table."
    ::= { unisRCPTable 1 }

unisRCPUserEntry OBJECT-TYPE
    SYNTAX      UnisRCPUserEntry
    MAX-ACCESS  not-accessible
    STATUS      current
    DESCRIPTION
        "The entry of unisRCPUserTable."
    INDEX
        {
            unisRCPUserName
        }
    ::= { unisRCPUserTable 1 }

UnisRCPUserEntry ::= SEQUENCE
    {
        unisRCPUserName                    DisplayString,
        unisRCPUserPassword                DisplayString,
        unisRCPUserRedirectInterface       InterfaceIndexOrZero,
        unisRCPUserRedirectBalanceGroup    Integer32,
        unisRCPUserRowStatus               RowStatus
    }

unisRCPUserName OBJECT-TYPE
    SYNTAX      DisplayString(SIZE(1..16))
    MAX-ACCESS  not-accessible
    STATUS      current
    DESCRIPTION
        "The name of RCP user."
    ::= { unisRCPUserEntry 1 }

unisRCPUserPassword OBJECT-TYPE
    SYNTAX      DisplayString(SIZE(1..16))
    MAX-ACCESS  read-create
    STATUS      current
    DESCRIPTION
        " The password of RCP user.
        It is invisible to users and displayed as '***'."
    ::= { unisRCPUserEntry 2 }

unisRCPUserRedirectInterface OBJECT-TYPE
    SYNTAX      InterfaceIndexOrZero
    MAX-ACCESS  read-create
    STATUS      current
    DESCRIPTION
        "The redirect interface index of RCP user.
        The RCP rule assigned by the user can be associated with the redirect
        interface.
        If the redirect interface is invalid, its value is set to be 0."
    ::= { unisRCPUserEntry 3 }

unisRCPUserRedirectBalanceGroup OBJECT-TYPE
    SYNTAX      Integer32
    MAX-ACCESS  read-create
    STATUS      current
    DESCRIPTION
        "The redirect balance group identity of RCP user.
        The RCP rule assigned by the user can be associated with the redirect
        balance group.
        If the balance group is invalid, its value is set to be 0."
    ::= { unisRCPUserEntry 4 }

unisRCPUserRowStatus OBJECT-TYPE
    SYNTAX      RowStatus
    MAX-ACCESS  read-create
    STATUS      current
    DESCRIPTION
        "This manages the creation and deletion of rows, and shows
        the current status of the indexed user name. This object has the
        following values.

        active(1)        The indexed user name is configured on the device.
        notInService(2)  Not Supported.
        notReady(3)      Not Supported.
        createAndGo(4)   Create a new user.
        createAndWait(5) Not Supported.
        destroy(6)       Delete this entry.

        The associated entry can be modified when the value of
        unisRCPUserRowStatus is active(1).
        When deleting an inexistence entry, return noError."
    ::= { unisRCPUserEntry 5 }

unisRCPClientIPTable OBJECT-TYPE
    SYNTAX      SEQUENCE OF UnisRCPClientIPEntry
    MAX-ACCESS  not-accessible
    STATUS      current
    DESCRIPTION
        "RCP Client IP Table."
    ::= { unisRCPTable 2 }

unisRCPClientIPEntry OBJECT-TYPE
    SYNTAX      UnisRCPClientIPEntry
    MAX-ACCESS  not-accessible
    STATUS      current
    DESCRIPTION
        "The entry of unisRCPClientIPTable."
    INDEX
        {
            unisRCPClientIPType,
            unisRCPClientIP
        }
    ::= { unisRCPClientIPTable 1 }

UnisRCPClientIPEntry ::= SEQUENCE
    {
        unisRCPClientIPType         InetAddressType,
        unisRCPClientIP             InetAddress,
        unisRCPClientIPRowStatus    RowStatus
    }

unisRCPClientIPType OBJECT-TYPE
    SYNTAX      InetAddressType
    MAX-ACCESS  not-accessible
    STATUS      current
    DESCRIPTION
        "The IP address type (IPv4 or IPv6) of RCP client."
    ::= { unisRCPClientIPEntry 1 }

unisRCPClientIP OBJECT-TYPE
    SYNTAX      InetAddress
    MAX-ACCESS  not-accessible
    STATUS      current
    DESCRIPTION
        "The IP address of RCP client."
    ::= { unisRCPClientIPEntry 2 }

unisRCPClientIPRowStatus OBJECT-TYPE
    SYNTAX      RowStatus
    MAX-ACCESS  read-create
    STATUS      current
    DESCRIPTION
        "This manages the creation and deletion or rows, and shows
        the current status of the indexed client IP address.  This object has
        the following values.

        active(1)        The indexed client IP is configured on the device.
        notInService(2)  Not Supported.
        notReady(3)      Not Supported.
        createAndGo(4)   Create a new client IP.
        createAndWait(5) Not Supported.
        destroy(6)       Delete this entry.

        The associated entry can be modified when the value of
        unisRCPClientIPRowStatus is active(1).
        When deleting an inexistence entry, return noError."
    ::= { unisRCPClientIPEntry 3 }

unisRCPSessionTable OBJECT-TYPE
    SYNTAX      SEQUENCE OF UnisRCPSessionEntry
    MAX-ACCESS  not-accessible
    STATUS      current
    DESCRIPTION
        "RCP session Table."
    ::= { unisRCPTable 3 }

unisRCPSessionEntry OBJECT-TYPE
    SYNTAX      UnisRCPSessionEntry
    MAX-ACCESS  not-accessible
    STATUS      current
    DESCRIPTION
        "The entry of unisRCPSessionTable."
    INDEX
        {
            unisRCPSessionId
        }
    ::= { unisRCPSessionTable 1 }

UnisRCPSessionEntry ::= SEQUENCE
    {
        unisRCPSessionId               Integer32,
        unisRCPSessionClientIPType     InetAddressType,
        unisRCPSessionClientIP         InetAddress,
        unisRCPSessionRunningStatus    INTEGER,
        unisRCPSessionUserName         DisplayString
    }

unisRCPSessionId OBJECT-TYPE
    SYNTAX      Integer32
    MAX-ACCESS  not-accessible
    STATUS      current
    DESCRIPTION
        "RCP session identity."
    ::= { unisRCPSessionEntry 1 }

unisRCPSessionClientIPType OBJECT-TYPE
    SYNTAX      InetAddressType
    MAX-ACCESS  read-only
    STATUS      current
    DESCRIPTION
        "The IP address type (IPv4 or IPv6) of RCP client."
    ::= { unisRCPSessionEntry 2 }

unisRCPSessionClientIP OBJECT-TYPE
    SYNTAX      InetAddress
    MAX-ACCESS  read-only
    STATUS      current
    DESCRIPTION
        "RCP client IP address."
    ::= { unisRCPSessionEntry 3 }

unisRCPSessionRunningStatus OBJECT-TYPE
    SYNTAX      INTEGER
        {
            connected(1),
            operational(2)
        }
    MAX-ACCESS  read-only
    STATUS      current
    DESCRIPTION
        "RCP server running status.
         It is one of the following status:
         connected: The connection is established and the RCP client is waiting
                    for authentication.
         operational: The RCP client is authenticated and the server is ready
                      for rule configuration request."
    ::= { unisRCPSessionEntry 4 }

unisRCPSessionUserName OBJECT-TYPE
    SYNTAX      DisplayString
    MAX-ACCESS  read-only
    STATUS      current
    DESCRIPTION
        "RCP user name."
    ::= { unisRCPSessionEntry 5 }

END
