-- =====================================================================
-- Copyright (c) 2020 Unisyue Technologies Co., Ltd.  All rights reserved.
--
-- Description: LACP extend MIB
-- Reference:
-- Version: V1.7
-- History:
--   V1.0 Initial version
--   V1.1 2004-10-12 updated by gaolong
--        Remove OID comments.
--        Change MAX-ACCESS clause value of unisAggLinkNumber to accessible-for-notify
--        because this index object is used when sending notification.
--        Fix a default value error of unisAggResourceAllocationValue.
--   V1.2 2004-10-25 updated by fuzhenyu
--        Change the range of unisAggLinkNumber from (1..256) to (1..728)
--        Change the size of unisAggPortNotAttachedString from (1..50) to (1..255)
--   V1.3 2006-03-05 updated by zhangjian
--        Edit the description of unisAggPortNotAttachedReason.
--        Change value range of unisAggLinkNumber.
--   V1.4 2006-11-15 updated by zhangjian
--        Change MAX-ACCESS clause of unisAggPortIndex to accessible-for-notify.
--        Add unisAggPortInactiveNotification2 and unisAggPortActiveNotification.
--   V1.5 2009-10-09 updated by songjianyong
--        Change value range of unisAggPortNotAttachedReason.
--   V1.6 2010-03-26 updated by songjianyong
--        Change value range of unisAggPortNotAttachedReason.
--   V1.7 2011-10-12 updated by liyugang
--        Change some descriptions.
-- =====================================================================
UNIS-LAG-MIB DEFINITIONS ::= BEGIN

    IMPORTS
        OBJECT-GROUP, MODULE-COMPLIANCE, NOTIFICATION-GROUP
            FROM SNMPv2-CONF
        Integer32, Gauge32, OBJECT-TYPE, MODULE-IDENTITY, NOTIFICATION-TYPE
            FROM SNMPv2-SMI
        DisplayString, RowStatus,TruthValue,TEXTUAL-CONVENTION
            FROM SNMPv2-TC
        unisRhw
            FROM UNIS-OID-MIB
        PortList
            FROM Q-BRIDGE-MIB;

    unisLAG MODULE-IDENTITY
        LAST-UPDATED "200310091942Z"    -- October 09, 2003 at 19:42 GMT
        ORGANIZATION
            "Unisyue Technologies Co., Ltd."
        CONTACT-INFO
            ""
        DESCRIPTION
            "LACP extend MIB."
        ::= { unisRhw 25 }

--
-- Node definitions
--

    unisLAGMibObjects OBJECT IDENTIFIER ::= { unisLAG 1 }


    unisAggLinkTable OBJECT-TYPE
        SYNTAX SEQUENCE OF UnisAggLinkEntry
        MAX-ACCESS not-accessible
        STATUS current
        DESCRIPTION
            "A table of aggregate link objects."
        ::= { unisLAGMibObjects 1 }


    unisAggLinkEntry OBJECT-TYPE
        SYNTAX UnisAggLinkEntry
        MAX-ACCESS not-accessible
        STATUS current
        DESCRIPTION
            "Entry of table."
        INDEX { unisAggLinkNumber }
        ::= { unisAggLinkTable 1 }


    UnisAggLinkEntry ::=
        SEQUENCE {
            unisAggLinkNumber
                Integer32,
            unisAggLinkName
                DisplayString,
            unisAggLinkMode
                INTEGER,
            unisAggLinkPortList
                PortList,
            unisAggLinkState
                RowStatus,
            unisAggPortListSelectedPorts
                PortList,
            unisAggPortListSamePartnerPorts
                PortList
         }

    unisAggLinkNumber OBJECT-TYPE
        SYNTAX Integer32
        MAX-ACCESS accessible-for-notify
        STATUS current
        DESCRIPTION
            "The serial number of aggregation group."
        ::= { unisAggLinkEntry 1 }


    unisAggLinkName OBJECT-TYPE
        SYNTAX DisplayString (SIZE (0..32))
        MAX-ACCESS read-create
        STATUS current
        DESCRIPTION
            "Aggregation name."
        ::= { unisAggLinkEntry 2 }


    unisAggLinkMode OBJECT-TYPE
        SYNTAX INTEGER
            {
            manual(1),
            static(2),
            dynamic(3)
            }
        MAX-ACCESS read-create
        STATUS current
        DESCRIPTION
            "Type of aggregation.
             manual: Manual aggregation, no LACP.
             static: Membership specified by user, LACP is
                     used to validate.
             dynamic: Completely dynamic aggregation detected
                      by LACP."
        ::= { unisAggLinkEntry 3 }


    unisAggLinkPortList OBJECT-TYPE
        SYNTAX PortList
        MAX-ACCESS read-create
        STATUS current
        DESCRIPTION
            "List of ports in this link aggregation group, by bridge port
             number. If the mode of the link aggregation group is manual
             or static, you can update this list to your
             hearts content. However, if the link aggregation group is
             dynamic, the system will maintain it. You are not
             permitted to set the value of this to
             all zeroes."
        ::= { unisAggLinkEntry 4 }


    unisAggLinkState OBJECT-TYPE
        SYNTAX RowStatus
        MAX-ACCESS read-create
        STATUS current
        DESCRIPTION
            "RowStatus, now support three states:
            createAndGo, active, destroy."
        ::= { unisAggLinkEntry 5 }


    unisAggPortListSelectedPorts OBJECT-TYPE
        SYNTAX PortList
        MAX-ACCESS read-only
        STATUS current
        DESCRIPTION
            "A PortList of physical ports that have been
             selected but not attached to this aggregator.
             When the bit is set to 1,it means the
             corresponding port is in the portlist."
        ::= { unisAggLinkEntry 6 }


    unisAggPortListSamePartnerPorts OBJECT-TYPE
        SYNTAX PortList
        MAX-ACCESS read-only
        STATUS current
        DESCRIPTION
            "PortList of physical ports that have the
             same Actor SystemID and partner systemID as
             this aggregator, but have different actor
             and partner keys of aggregator."
        ::= { unisAggLinkEntry 7 }


    unisAggPortTable OBJECT-TYPE
        SYNTAX SEQUENCE OF UnisAggPortEntry
        MAX-ACCESS not-accessible
        STATUS current
        DESCRIPTION
            "A table of aggregate port objects."
        ::= { unisLAGMibObjects 2 }


    unisAggPortEntry OBJECT-TYPE
        SYNTAX UnisAggPortEntry
        MAX-ACCESS not-accessible
        STATUS current
        DESCRIPTION
            "Entry of table."
        INDEX { unisAggPortIndex }
        ::= { unisAggPortTable 1 }


    UnisAggPortEntry ::=
        SEQUENCE {
            unisAggPortIndex
                Gauge32,
            unisAggPortNotAttachedReason
                Integer32,
            unisAggPortLacpState
                TruthValue,
            unisAggPortNotAttachedString
                DisplayString
        }

    unisAggPortIndex OBJECT-TYPE
        SYNTAX Gauge32
        MAX-ACCESS accessible-for-notify
        STATUS current
        DESCRIPTION
            "Port ifindex which is according to RFC1213 MIB."
        ::= { unisAggPortEntry 1 }


    unisAggPortNotAttachedReason OBJECT-TYPE
        SYNTAX Integer32 (0..10)
        MAX-ACCESS read-write
        STATUS current
        DESCRIPTION
            "Reason why this port is selected for an
             aggregator but not attached,
             0: The port is attached to this aggregator.
             1: The current number of active ports has
                reached the upper limit.
             2: All aggregation resources are already in-use.
             3: The port's configuration is improper
                for being attached.
             4: The port's partner is improper for being attached.
             5: The number of current active ports
                has not reached the lower limit.
             6: The port's physical state (down) is
                improper for being attached.
             7: The port is not selected for an aggregator.
             8: The port's hardware restriction is
                improper for being attached.
             9: The port's speed is improper for being attached.
             10: The port's duplex mode is improper for being attached."
        ::= { unisAggPortEntry 2 }

    unisAggPortLacpState OBJECT-TYPE
        SYNTAX TruthValue
        MAX-ACCESS read-write
        STATUS current
        DESCRIPTION
            "Control ports' lacp enble or disable."
        ::= { unisAggPortEntry 3 }

    unisAggPortNotAttachedString OBJECT-TYPE
        SYNTAX DisplayString (SIZE (0..255))
        MAX-ACCESS read-write
        STATUS current
        DESCRIPTION
            "The string which interprets this
             port is selected for an aggregator
             but not attached."
        ::= { unisAggPortEntry 4 }


    unisAggResourceAllocationValue OBJECT-TYPE
        SYNTAX PortList
        MAX-ACCESS read-only
        STATUS current
        DESCRIPTION
            "The priority value calculated to decide which
             aggregations have first call on the load-sharing
             aggregation resources in the hardware. It
             depends on the aggregation type and total
             speed."
        DEFVAL { "0" }
        ::= { unisLAGMibObjects 3 }


    unisLAGMibNotifications OBJECT IDENTIFIER ::= { unisLAG 2 }


    unisAggSpeedChangedNotification NOTIFICATION-TYPE
        OBJECTS { unisAggLinkNumber }
        STATUS current
        DESCRIPTION
            "This event will be triggered whenever an
             aggregation changes its speed."
        ::= { unisLAGMibNotifications 1 }


    unisAggPortInactiveNotification NOTIFICATION-TYPE
        OBJECTS { unisAggLinkNumber }
        STATUS current
        DESCRIPTION
            "This event will be triggered whenever any port
             in aggregator is made inactive."
        ::= { unisLAGMibNotifications 2 }


    unisAggPortInactiveNotification2 NOTIFICATION-TYPE
        OBJECTS { unisAggLinkNumber,
                  unisAggPortIndex }
        STATUS current
        DESCRIPTION
            "This event will be triggered whenever the port
             in aggregator is made inactive."
        ::= { unisLAGMibNotifications 3 }


    unisAggPortActiveNotification NOTIFICATION-TYPE
        OBJECTS { unisAggLinkNumber,
                  unisAggPortIndex }
        STATUS current
        DESCRIPTION
            "This event will be triggered whenever the port
             in aggregator is made active."
        ::= { unisLAGMibNotifications 4 }


    unisLAGMibConformance OBJECT IDENTIFIER ::= { unisLAG 3 }


    unisLAGMibCompliances OBJECT IDENTIFIER ::= { unisLAGMibConformance 1 }


    unisLAGMibCompliance MODULE-COMPLIANCE
        STATUS current
        DESCRIPTION
            "The compliance statement for SNMP entities
             which implement the Lag MIB."
        MODULE -- this module
            MANDATORY-GROUPS
                { unisLAGMibObjectGroup, unisLAGMibNotificationGroup }
        ::= { unisLAGMibCompliances 1 }


    unisLAGMibGroup OBJECT IDENTIFIER ::= { unisLAGMibConformance 2 }


    unisLAGMibObjectGroup OBJECT-GROUP
        OBJECTS { unisAggLinkName, unisAggLinkMode, unisAggLinkPortList,
                unisAggLinkState, unisAggPortListSelectedPorts,
                unisAggPortListSamePartnerPorts,
                unisAggPortNotAttachedReason, unisAggPortLacpState,
                unisAggPortNotAttachedString,
                unisAggResourceAllocationValue }
        STATUS current
        DESCRIPTION
            "The collection of objects which are used to
             represent LAG objects."
        ::= { unisLAGMibGroup 1 }


    unisLAGMibNotificationGroup NOTIFICATION-GROUP
        NOTIFICATIONS { unisAggSpeedChangedNotification,
                        unisAggPortInactiveNotification,
                        unisAggPortInactiveNotification2,
                        unisAggPortActiveNotification }
        STATUS current
        DESCRIPTION
            "The collection of objects which are used to
             represent notifications."
        ::= { unisLAGMibGroup 2 }

END
