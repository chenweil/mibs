-- =============================================================================
-- Copyright (c) 2020 Unisyue Technologies Co., Ltd.  All rights reserved.
--
-- Description: This MIB module contains managed object definitions for
--              Multi-Protocol Label Switching (MPLS)/
--              Border Gateway Protocol (BGP) Virtual Private Networks (VPNs).
-- Reference: This MIB was extracted from draft-ietf-mpls-arch-06.txt
-- Version: V1.2
-- History:
--   V1.0 2014-12-03 Initial version Created by YifanZhou
--   V1.1 2015-11-14 Modified description of unisMplsVpnVrfBgpPAtrIpAddrPrefix,
--        unisMplsVpnVrfConfMaxRts, unisMplsVpnVrfBgpPAtrPeerType,
--        unisMplsVpnVrfBgpPAtrAtomicAggregate by dairuiqiang.
--   V1.2 2016-10-26 add unisMplsVpnVrfBgpNbrState in UnisMplsVpnVrfBgpNbrAddrEntry by xukele 11706
-- =============================================================================
UNIS-MPLS-VPN-BGP-MIB DEFINITIONS ::= BEGIN
IMPORTS
    MODULE-IDENTITY, OBJECT-TYPE,
    Integer32, Unsigned32,IpAddress
        FROM SNMPv2-SMI
    InetAddressType
        FROM INET-ADDRESS-MIB
    TEXTUAL-CONVENTION, TruthValue, RowStatus
        FROM SNMPv2-TC
    unisCommon
        FROM UNIS-OID-MIB;

-- =============================================================================
-- module identity part
-- =============================================================================
unisMplsVpnBgp MODULE-IDENTITY
    LAST-UPDATED "201610262000Z"
    ORGANIZATION
        "Unisyue Technologies Co., Ltd."
    CONTACT-INFO
        ""
    DESCRIPTION
        "This MIB contains managed object definitions for the
         Multiprotocol Label Switching (MPLS)/Border Gateway
         Protocol (BGP) Virtual Private Networks (VPNs) as
         defined in : Rosen, E., Viswanathan, A., and R.
         Callon, Multiprotocol Label Switching Architecture,
         Internet Draft <draft-ietf-mpls-arch-06.txt>,
         August 1999."
    REVISION
        "201610262000Z"
    DESCRIPTION
        "Add unisMplsVpnVrfBgpNbrState in UnisMplsVpnVrfBgpNbrAddrEntry."
    REVISION
        "201511142000Z"
    DESCRIPTION
        "Modified description of unisMplsVpnVrfBgpPAtrIpAddrPrefix,
        unisMplsVpnVrfConfMaxRts, unisMplsVpnVrfBgpPAtrPeerType,
        unisMplsVpnVrfBgpPAtrAtomicAggregate."
    REVISION
        "201412032000Z"  -- 03 Dec 2014 20:00:00 GMT
    DESCRIPTION
        "Initial version of this MIB."
    ::= { unisCommon 160 }

-- Textual Conventions.

UnisMplsVpnId ::= TEXTUAL-CONVENTION
    DISPLAY-HINT "31a"
    STATUS       current
    DESCRIPTION
        "An identifier that is assigned to each MPLS/BGP VPN and
         is used to uniquely identify it.  This is assigned by the
         system operator or NMS and SHOULD be unique throughout
         the MPLS domain.  If this is the case, then this identifier
         can then be used at any LSR within a specific MPLS domain
         to identify this MPLS/BGP VPN.  It may also be possible to
         preserve the uniqueness of this identifier across MPLS
         domain boundaries, in which case this identifier can then
         be used to uniquely identify MPLS/BGP VPNs on a more global
         basis."
    REFERENCE
        "RFC 2685 [VPN-RFC2685] Fox B., et al, 'Virtual Private
         Networks Identifier', September 1999."
    SYNTAX OCTET STRING(SIZE (0..31))

UnisMplsVpnRtDistinguisher ::= TEXTUAL-CONVENTION
    DISPLAY-HINT "256a"
    STATUS       current
    DESCRIPTION
        "Syntax for a route distinguisher and route target."
    SYNTAX  OCTET STRING(SIZE (0..256))

-- =============================================================================
-- object definition begin
-- =============================================================================
unisMplsVpnObjects OBJECT IDENTIFIER ::= { unisMplsVpnBgp 1 }
unisMplsVpnConf    OBJECT IDENTIFIER ::= { unisMplsVpnObjects 1 }

-- =============================================================================
-- unisMplsVpnVrfConfTable Definition
-- =============================================================================
unisMplsVpnVrfConfTable OBJECT-TYPE
    SYNTAX      SEQUENCE OF UnisMplsVpnVrfConfEntry
    MAX-ACCESS  not-accessible
    STATUS      current
    DESCRIPTION
        "This table specifies per-interface MPLS/BGP VPN
         VRF Table capability and associated information.
         Entries in this table define VRF routing instances
         associated with MPLS/VPN interfaces.  Note that
         multiple interfaces can belong to the same VRF
         instance.  The collection of all VRF instances
         comprises an actual VPN."
   ::= { unisMplsVpnConf 1 }

unisMplsVpnVrfConfEntry OBJECT-TYPE
    SYNTAX      UnisMplsVpnVrfConfEntry
    MAX-ACCESS  not-accessible
    STATUS      current
    DESCRIPTION
        "An entry in this table is created by an LSR for
         every VRF capable of supporting MPLS/BGP VPN.  The
         indexing provides an ordering of VRFs per-VPN
         interface."
    INDEX {
            unisMplsVpnVrfName
          }
    ::= { unisMplsVpnVrfConfTable 1 }

UnisMplsVpnVrfConfEntry ::= SEQUENCE {
    unisMplsVpnVrfName                   UnisMplsVpnId,
    unisMplsVpnVrfRtDistinguisher        UnisMplsVpnRtDistinguisher,
    unisMplsVpnVrfNetPrefixType          INTEGER,
    unisMplsVpnVrfNetPrefix              IpAddress,
    unisMplsVpnVrfIpRtRedistributeConn   TruthValue,
    unisMplsVpnVrfIpRtRedistributeStatic TruthValue,
    unisMplsVpnVrfIpRtRedistributeRip    TruthValue,
    unisMplsVpnVrfConfHighRtThreshold    Unsigned32,
    unisMplsVpnVrfConfIsWarnOnly         TruthValue,
    unisMplsVpnVrfConfMaxRts             Unsigned32,
    unisMplsVpnVrfConfRowStatus          RowStatus
}

unisMplsVpnVrfName OBJECT-TYPE
    SYNTAX      UnisMplsVpnId
    MAX-ACCESS  not-accessible
    STATUS      current
    DESCRIPTION
        "The human-readable name of this VPN.  This MAY
         be equivalent to the RFC2685 VPN-ID."
    REFERENCE
        "RFC 2685 [VPN-RFC2685] Fox B., et al, `Virtual
         Private Networks Identifier`, September 1999."
    ::= { unisMplsVpnVrfConfEntry 1 }

unisMplsVpnVrfRtDistinguisher OBJECT-TYPE
    SYNTAX      UnisMplsVpnRtDistinguisher
    MAX-ACCESS  read-create
    STATUS      current
    DESCRIPTION
        "The route distinguisher for this VRF."
    ::= { unisMplsVpnVrfConfEntry 2 }

unisMplsVpnVrfNetPrefixType OBJECT-TYPE
    SYNTAX      INTEGER { other(1),
                          rip(2),
                          ospf(3),
                          isis(4),
                          bgp(5),
                          static(6)
                        }
    MAX-ACCESS  read-only
    STATUS      current
    DESCRIPTION
        "Denotes the type of the network prefix in use for the
         PE-CE connections. "
    ::= { unisMplsVpnVrfConfEntry 3 }

unisMplsVpnVrfNetPrefix OBJECT-TYPE
    SYNTAX      IpAddress
    MAX-ACCESS  read-only
    STATUS      current
    DESCRIPTION
        "Denotes the network prefix for the
         PE-CE connections."
   ::= { unisMplsVpnVrfConfEntry 4 }

unisMplsVpnVrfIpRtRedistributeConn OBJECT-TYPE
    SYNTAX      TruthValue
    MAX-ACCESS  read-create
    STATUS      current
    DESCRIPTION
        "Denotes the redistribution of directly connected
         networks into the VRF BGP table."
    ::= { unisMplsVpnVrfConfEntry 5 }

unisMplsVpnVrfIpRtRedistributeStatic OBJECT-TYPE
    SYNTAX      TruthValue
    MAX-ACCESS  read-create
    STATUS      current
    DESCRIPTION
        "Denotes the redistribution of static routes
         into the VRF BGP table."
   ::= { unisMplsVpnVrfConfEntry 6 }

unisMplsVpnVrfIpRtRedistributeRip OBJECT-TYPE
    SYNTAX        TruthValue
    MAX-ACCESS    read-create
    STATUS        current
    DESCRIPTION
     "Denotes the redistribution of RIP routes
      into the VRF BGP table."
   ::= { unisMplsVpnVrfConfEntry 7 }

unisMplsVpnVrfConfHighRtThreshold OBJECT-TYPE
    SYNTAX      Unsigned32
    MAX-ACCESS  read-create
    STATUS      current
    DESCRIPTION
        "Denotes high-level water marker for the number of
         routes which this VRF may hold."
    ::= { unisMplsVpnVrfConfEntry 8 }

unisMplsVpnVrfConfIsWarnOnly OBJECT-TYPE
    SYNTAX      TruthValue
    MAX-ACCESS  read-create
    STATUS      current
    DESCRIPTION
        "Denotes the action when the amount of VPN's routes
         exceed the unisMplsVpnVrfConfHighRtThreshold."
    ::= { unisMplsVpnVrfConfEntry 9 }

unisMplsVpnVrfConfMaxRts OBJECT-TYPE
    SYNTAX      Unsigned32
    MAX-ACCESS  read-create
    STATUS      current
    DESCRIPTION
        "Denotes maximum number of routes which this VRF is
         configured to hold.  This value MUST be less than or
         equal to unisMplsVrfMaxPossibleRts unless it is set
         to 0."
    ::= { unisMplsVpnVrfConfEntry 10 }

unisMplsVpnVrfConfRowStatus OBJECT-TYPE
    SYNTAX      RowStatus
    MAX-ACCESS  read-create
    STATUS      current
    DESCRIPTION
        "This variable is used to create, modify, and/or
         delete a row in this table."
    ::= { unisMplsVpnVrfConfEntry 11 }

-- =============================================================================
-- End of unisMplsVpnVrfConfTable Definition
-- =============================================================================

-- =============================================================================
-- unisMplsVpnVrfBgpNbrAddrTable Definition
-- Ed Note: how does this table relate to the BGP peering table;
--          this is only EBGP; what about IBGP info?
--          route/tag distributions
-- =============================================================================
unisMplsVpnVrfBgpNbrAddrTable OBJECT-TYPE
    SYNTAX      SEQUENCE OF UnisMplsVpnVrfBgpNbrAddrEntry
    MAX-ACCESS  not-accessible
    STATUS      current
    DESCRIPTION
        "This table specifies per-interface MPLS/BGP neighbor
         addresses for both PEs and CEs."
    ::= { unisMplsVpnConf 2 }

unisMplsVpnVrfBgpNbrAddrEntry OBJECT-TYPE
    SYNTAX      UnisMplsVpnVrfBgpNbrAddrEntry
    MAX-ACCESS  not-accessible
    STATUS      current
    DESCRIPTION
        "An entry in this table is created by an LSR for
         every VRF capable of supporting MPLS/BGP VPN.  The
         indexing provides an ordering of VRFs per-VPN
         interface."
    INDEX {
            unisMplsVpnVrfName,
            unisMplsVpnVrfBgpNbrAddr
          }
    ::= { unisMplsVpnVrfBgpNbrAddrTable 1 }

UnisMplsVpnVrfBgpNbrAddrEntry ::= SEQUENCE {
    unisMplsVpnVrfBgpNbrAddr        IpAddress,
    unisMplsVpnVrfBgpNbrRole        INTEGER,
    unisMplsVpnVrfBgpNbrAsNumber    Unsigned32,
    unisMplsVpnVrfBgpNbrAdminStatus INTEGER,
    unisMplsVpnVrfBgpNbrRowStatus   RowStatus,
    unisMplsVpnVrfBgpNbrState       INTEGER
}

unisMplsVpnVrfBgpNbrAddr OBJECT-TYPE
    SYNTAX      IpAddress
    MAX-ACCESS  not-accessible
    STATUS      current
    DESCRIPTION
        "Denotes the BGP neighbor address."
    ::= { unisMplsVpnVrfBgpNbrAddrEntry 1 }

unisMplsVpnVrfBgpNbrRole OBJECT-TYPE
    SYNTAX      INTEGER { ce(1),
                          pe(2)
                        }
    MAX-ACCESS  read-create
    STATUS      current
    DESCRIPTION
        "Denotes the role played by this BGP neighbor
         with respect to this VRF."
    ::= { unisMplsVpnVrfBgpNbrAddrEntry 2 }

unisMplsVpnVrfBgpNbrAsNumber OBJECT-TYPE
    SYNTAX      Unsigned32
    MAX-ACCESS  read-create
    STATUS      current
    DESCRIPTION
        "The Autonomous System that the BGP's neighbour in."
    ::= { unisMplsVpnVrfBgpNbrAddrEntry 3 }

unisMplsVpnVrfBgpNbrAdminStatus OBJECT-TYPE
    SYNTAX      INTEGER { mplsVpnVrfBgpNbrSetUp   (1),
                          mplsVpnVrfBgpNbrSetDown (2)
                        }
    MAX-ACCESS  read-create
    STATUS      current
    DESCRIPTION
        "The action set by SNMP client."
    ::= { unisMplsVpnVrfBgpNbrAddrEntry 4 }

unisMplsVpnVrfBgpNbrRowStatus OBJECT-TYPE
    SYNTAX      RowStatus
    MAX-ACCESS  read-create
    STATUS      current
    DESCRIPTION
        "This variable is used to create, modify, and/or
         delete a row in this table."
    ::= { unisMplsVpnVrfBgpNbrAddrEntry 5 }

unisMplsVpnVrfBgpNbrState OBJECT-TYPE
    SYNTAX     INTEGER { idle(1),
                         connect(2),
                         active(3),
                         opensent(4),
                         openconfirm(5),
                         established(6)
                       }
    MAX-ACCESS read-only
    STATUS     current
    DESCRIPTION
        "The BGP neighbor connection state."
    ::= { unisMplsVpnVrfBgpNbrAddrEntry 6 }
-- =============================================================================
-- End of unisMplsVpnVrfBgpNbrAddrTable Definition
-- =============================================================================

-- =============================================================================
-- unisMplsVpnVrfBgpNbrPrefixTable Definition
-- =============================================================================
unisMplsVpnVrfBgpNbrPrefixTable OBJECT-TYPE
    SYNTAX      SEQUENCE OF UnisMplsVpnVrfBgpNbrPrefixEntry
    MAX-ACCESS  not-accessible
    STATUS      current
    DESCRIPTION
        "This table specifies per-VRF vpnv4 multi-protocol
         prefixes supported by BGP."
    ::= { unisMplsVpnConf 3 }

unisMplsVpnVrfBgpNbrPrefixEntry OBJECT-TYPE
    SYNTAX      UnisMplsVpnVrfBgpNbrPrefixEntry
    MAX-ACCESS  not-accessible
    STATUS      current
    DESCRIPTION
        "An entry in this table is created by an LSR for
         every BGP prefix associated with a VRF supporting a
         MPLS/BGP VPN.  The indexing provides an ordering of
         BGP prefixes per VRF."
    INDEX {
            unisMplsVpnVrfName,
            unisMplsVpnVrfBgpPAtrPeer,
            unisMplsVpnVrfBgpPAtrIpAddrPrefixLen,
            unisMplsVpnVrfBgpPAtrIpAddrPrefix
          }
    ::= { unisMplsVpnVrfBgpNbrPrefixTable 1 }

UnisMplsVpnVrfBgpNbrPrefixEntry ::= SEQUENCE {
    unisMplsVpnVrfBgpPAtrPeer            IpAddress,
    unisMplsVpnVrfBgpPAtrIpAddrPrefixLen Integer32,
    unisMplsVpnVrfBgpPAtrIpAddrPrefix    IpAddress,
    unisMplsVpnVrfBgpPAtrPeerType        InetAddressType,
    unisMplsVpnVrfBgpPAtrOrigin          INTEGER,
    unisMplsVpnVrfBgpPAtrASPathSegment   OCTET STRING,
    unisMplsVpnVrfBgpPAtrNextHop         IpAddress,
    unisMplsVpnVrfBgpPAtrMultiExitDisc   Integer32,
    unisMplsVpnVrfBgpPAtrLocalPref       Integer32,
    unisMplsVpnVrfBgpPAtrAtomicAggregate INTEGER,
    unisMplsVpnVrfBgpPAtrAggregatorAS    Integer32,
    unisMplsVpnVrfBgpPAtrAggregatorAddr  IpAddress,
    unisMplsVpnVrfBgpPAtrCalcLocalPref   Integer32,
    unisMplsVpnVrfBgpPAtrBest            TruthValue,
    unisMplsVpnVrfBgpPAtrUnknown         OCTET STRING
}

unisMplsVpnVrfBgpPAtrPeer OBJECT-TYPE
    SYNTAX      IpAddress
    MAX-ACCESS  not-accessible
    STATUS      current
    DESCRIPTION
        "The IP address of the peer where the path
         information was learned."
    ::= { unisMplsVpnVrfBgpNbrPrefixEntry 1 }

unisMplsVpnVrfBgpPAtrIpAddrPrefixLen OBJECT-TYPE
    SYNTAX      Integer32  (0..32)
    MAX-ACCESS  not-accessible
    STATUS      current
    DESCRIPTION
       "Length in bits of the IP address prefix
        in the Network Layer Reachability
        Information field."
    ::= { unisMplsVpnVrfBgpNbrPrefixEntry 2 }

unisMplsVpnVrfBgpPAtrIpAddrPrefix OBJECT-TYPE
    SYNTAX      IpAddress
    MAX-ACCESS  not-accessible
    STATUS      current
    DESCRIPTION
        "An IP address prefix in the Network Layer
         Reachability Information field.  This object
         is an IP address containing the prefix with
         length specified by mplsVpnVrfBgpPAtrIpAddrPrefixLen.
         Any bits beyond the length specified by
         MplsVpnVrfBgpPAtrIpAddrPrefixLen are zeroed."
    ::= { unisMplsVpnVrfBgpNbrPrefixEntry 3 }

unisMplsVpnVrfBgpPAtrPeerType OBJECT-TYPE
    SYNTAX      InetAddressType
    MAX-ACCESS  read-only
    STATUS      current
    DESCRIPTION
        "Address type of the mplsVpnVrfBgpPAtrPeer object."
    ::= { unisMplsVpnVrfBgpNbrPrefixEntry 4 }

unisMplsVpnVrfBgpPAtrOrigin OBJECT-TYPE
    SYNTAX      INTEGER { igp(1),-- networks are interior
                          egp(2),-- networks learned via EGP
                          incomplete(3) -- undetermined
                        }
    MAX-ACCESS  read-only
    STATUS      current
    DESCRIPTION
        "The ultimate origin of the path
         information."
    ::= { unisMplsVpnVrfBgpNbrPrefixEntry 5 }

unisMplsVpnVrfBgpPAtrASPathSegment OBJECT-TYPE
    SYNTAX      OCTET STRING (SIZE (2..255))
    MAX-ACCESS  read-only
    STATUS      current
    DESCRIPTION
        "The sequence of AS path segments.  Each AS
         path segment is represented by a triple
         <type, length, value>.

          The type is a 1-octet field which has two
          possible values:
              1      AS_SET: unordered set of ASs a
                     route in the UPDATE
                     message has traversed
              2      AS_SEQUENCE: ordered set of ASs
                     a route in the UPDATE
                     message has traversed.
                     The length is a 1-octet field containing the
                     number of ASs in the value field.

                     The value field contains one or more AS
                     numbers, each AS is represented in the octet
                     string as a pair of octets according to the
                     following algorithm:
                     first-byte-of-pair = ASNumber / 256;
                     second-byte-of-pair = ASNumber & 255;"
    ::= { unisMplsVpnVrfBgpNbrPrefixEntry 6 }

unisMplsVpnVrfBgpPAtrNextHop OBJECT-TYPE
    SYNTAX      IpAddress
    MAX-ACCESS  read-only
    STATUS      current
    DESCRIPTION
        "The address of the border router that
         should be used for the destination
         network."
    ::= { unisMplsVpnVrfBgpNbrPrefixEntry 7 }

unisMplsVpnVrfBgpPAtrMultiExitDisc OBJECT-TYPE
    SYNTAX      Integer32 (-1..2147483647)
    MAX-ACCESS  read-only
    STATUS      current
    DESCRIPTION
        "This metric is used to discriminate
         between multiple exit points to an
         adjacent autonomous system.  A value of -1
         indicates the absence of this attribute."
    ::= { unisMplsVpnVrfBgpNbrPrefixEntry 8 }

unisMplsVpnVrfBgpPAtrLocalPref OBJECT-TYPE
    SYNTAX      Integer32 (-1..2147483647)
    MAX-ACCESS  read-only
    STATUS      current
    DESCRIPTION
        "The originating BGP4 speaker's degree of
         preference for an advertised route.  A
         value of -1 indicates the absence of this
         attribute."
    ::= { unisMplsVpnVrfBgpNbrPrefixEntry 9 }

unisMplsVpnVrfBgpPAtrAtomicAggregate OBJECT-TYPE
    SYNTAX      INTEGER { lessSpecificRtNotSelected(1),
                          lessSpecificRtSelected(2)
                        }
    MAX-ACCESS  read-only
    STATUS      current
    DESCRIPTION
        "If the ATOMIC_AGGREGATE attribute is present
        in the Path Attributes then this object MUST
        have a value of 'lessSpecificRouteNotSelected'.
        If the ATOMIC_AGGREGATE attribute is missing
        in the Path Attributes then this object MUST
        have a value of 'lessSpecificRouteSelected'.
        Note that ATOMIC_AGGREGATE is now a primarily
        informational attribute."
    ::= { unisMplsVpnVrfBgpNbrPrefixEntry 10 }

unisMplsVpnVrfBgpPAtrAggregatorAS OBJECT-TYPE
    SYNTAX      Integer32 (0..65535)
    MAX-ACCESS  read-only
    STATUS      current
    DESCRIPTION
        "The AS number of the last BGP4 speaker that
         performed route aggregation.  A value of
         zero (0) indicates the absence of this
         attribute."
    ::= { unisMplsVpnVrfBgpNbrPrefixEntry 11 }

unisMplsVpnVrfBgpPAtrAggregatorAddr OBJECT-TYPE
    SYNTAX      IpAddress
    MAX-ACCESS  read-only
    STATUS      current
    DESCRIPTION
        "The IP address of the last BGP4 speaker
         that performed route aggregation.  A value
         of 0.0.0.0 indicates the absence of this
         attribute."
    ::= { unisMplsVpnVrfBgpNbrPrefixEntry 12 }

unisMplsVpnVrfBgpPAtrCalcLocalPref OBJECT-TYPE
    SYNTAX      Integer32 (-1..2147483647)
    MAX-ACCESS  read-only
    STATUS      current
    DESCRIPTION
         "The degree of preference calculated by the
          receiving BGP4 speaker for an advertised
          route.  A value of -1 indicates the
          absence of this attribute."
    ::= { unisMplsVpnVrfBgpNbrPrefixEntry 13 }

unisMplsVpnVrfBgpPAtrBest OBJECT-TYPE
    SYNTAX      TruthValue
    MAX-ACCESS  read-only
    STATUS      current
    DESCRIPTION
        "An indication of whether or not this route
         was chosen as the best BGP4 route."
    ::= { unisMplsVpnVrfBgpNbrPrefixEntry 14 }

unisMplsVpnVrfBgpPAtrUnknown OBJECT-TYPE
    SYNTAX      OCTET STRING (SIZE(0..255))
    MAX-ACCESS  read-only
    STATUS      current
    DESCRIPTION
        "One or more path attributes not understood
         by this BGP4 speaker.  A zero-length string
         indicates the absence of such
         attribute(s).  Octets beyond the maximum
         size, if any, are not recorded by this
         object."
    ::= { unisMplsVpnVrfBgpNbrPrefixEntry 15 }

-- =============================================================================
-- End of unisMplsVpnVrfBgpNbrPrefixTable Definition
-- =============================================================================
-- End of MPLS-VPN-MIB
END
