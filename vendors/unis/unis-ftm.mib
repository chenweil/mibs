-- ============================================================================
-- Copyright (c) 2020 Unisyue Technologies Co., Ltd.  All rights reserved.
--
-- Description: this MIB is a MIB for fabric topology management
--
-- Reference:
-- Version:     V2.3
-- History:
-- V1.0 2004/01/13 created by wangjiao
-- V1.1 2004/06/15 modifyied by huxiaolong
-- V1.2 2004/07/13 modified by huxiaolong add unisFtmUnitRole node
-- V1.3 2004/07/16 add unisFtmUnitRole to UnisFtmUnitEntry SEQUENCE { }
--           add unisFtmUnitRole OBJECT
-- V2.0 2004-10-12 updated by gaolong
--      Relocate unisFtmManMIB MODULE-IDENTITY.
--      Change MAX-ACCESS clause value of unisFtmIndex to accessible-for-notify
--      because this index is used when sending trap.
--      Relocate unisFtmManMIBNotification.
--      Add MODULE clause for unisFtmMIBCompliance.
--      Change value of unisFtmAuthMode from underscores to hephens.
-- V2.1 2004-11-20 updated by xuhui
--      Add unisFtmFabricVlanID
-- V2.2 2004-12-22 add unisFtmFabricType node by zhuchaopeng
-- V2.3 2005-03-31 add unisFtmNumberMode by yangjianfeng
-- ============================================================================
UNIS-FTM-MIB DEFINITIONS ::= BEGIN

        IMPORTS
            unisCommon
                FROM UNIS-OID-MIB
            OBJECT-GROUP, MODULE-COMPLIANCE, NOTIFICATION-GROUP
                FROM SNMPv2-CONF
            Integer32, OBJECT-TYPE, MODULE-IDENTITY, NOTIFICATION-TYPE
                FROM SNMPv2-SMI;

        unisFtmManMIB MODULE-IDENTITY
            LAST-UPDATED "200401131055Z"        -- January 13, 2004 at 10:55 GMT
            ORGANIZATION
                "Unisyue Technologies Co., Ltd."
            CONTACT-INFO
                ""
            DESCRIPTION
                "this MIB will maintain Fabric topology management.
                 The MIB includes unit-id, unit-name and
                      fabric authentication information."
            ::= { unisFtm 1 }

        unisFtm    OBJECT IDENTIFIER ::= { unisCommon 1 }

--
-- Node definitions
--

        unisFtmManMIBObjects OBJECT IDENTIFIER ::= { unisFtmManMIB 1 }

        unisFtmUnitTable OBJECT-TYPE
            SYNTAX SEQUENCE OF UnisFtmUnitEntry
            MAX-ACCESS not-accessible
            STATUS current
            DESCRIPTION
                "A table of informations of XRN-Fabric Unit."
            ::= { unisFtmManMIBObjects 1 }

        unisFtmUnitEntry OBJECT-TYPE
            SYNTAX UnisFtmUnitEntry
            MAX-ACCESS not-accessible
            STATUS current
            DESCRIPTION
                "An entry for configuring unit informations of XRN-Fabric."
            INDEX { unisFtmIndex }
            ::= { unisFtmUnitTable 1 }

        UnisFtmUnitEntry ::=
            SEQUENCE {
                unisFtmIndex
                    Integer32,
                unisFtmUnitID
                    INTEGER,
                unisFtmUnitName
                    OCTET STRING,
                unisFtmUnitRole
                    INTEGER,
                unisFtmNumberMode
                    INTEGER
             }

        unisFtmIndex OBJECT-TYPE
            SYNTAX Integer32
            MAX-ACCESS accessible-for-notify
            STATUS current
            DESCRIPTION
                "The unique index of a unit."
            ::= { unisFtmUnitEntry 1 }

        unisFtmUnitID OBJECT-TYPE
            SYNTAX INTEGER
            MAX-ACCESS read-write
            STATUS current
            DESCRIPTION
                "Identifer of unit in fabric. Its value should be between 1 and the maximum which defines
                in product specification.
                An exception is described in description of unisFtmNumberMode. In that case, the value
                of this object remains its original value after set to zero.
                "
            ::= { unisFtmUnitEntry 2 }

        unisFtmUnitName OBJECT-TYPE
            SYNTAX OCTET STRING
            MAX-ACCESS read-write
            STATUS current
            DESCRIPTION
                "Name of unit in XRN-Fabric. It consists of no more than 64 characters."
            ::= { unisFtmUnitEntry 3 }

        unisFtmUnitRole OBJECT-TYPE
            SYNTAX INTEGER
            {
                master(0),   -- master unit
                slave(1)     -- slave unit
            }
            MAX-ACCESS read-only
            STATUS current
            DESCRIPTION
                "Role of unit in XRN-Fabric. One unit in a XRN-Fabric acts as master role and others
                act as slave roles"
            ::= { unisFtmUnitEntry 4 }

        unisFtmNumberMode OBJECT-TYPE
            SYNTAX INTEGER
            {
                automatic(0),
                manual (1)
            }
            MAX-ACCESS read-only
            STATUS current
            DESCRIPTION
                "Numbering Mode of unit in XRN-Fabric.  If the unit ID is assigned by the auto
                numbering algorithm, the numbering mode will be automatic numbering; if the
                unit ID (unisFtmUnitID) is assigned by the user, the numbering mode will be manual
                numbering; if unisFtmUnitID is set to be zero, the numbering mode will become
                automatic numbering."
            ::= { unisFtmUnitEntry 5 }

        unisFtmAuthMode OBJECT-TYPE
            SYNTAX INTEGER
                {
                ftm-none(0),
                ftm-simple(1),
                ftm-md5(2)
                }
            MAX-ACCESS read-write
            STATUS current
            DESCRIPTION
                "Authentication mode of XRN-Fabric."
            ::= { unisFtmManMIBObjects 2 }

        unisFtmAuthValue OBJECT-TYPE
            SYNTAX OCTET STRING
            MAX-ACCESS read-write
            STATUS current
            DESCRIPTION
                "Authentication value of XRN-Fabric Feature. ftm_none mode means no authentication.
                In simple mode, the value is password of a string of 1 to 16 charactors.
                While in md5 mode, the value is key of a string within 16 charactors."
            ::= { unisFtmManMIBObjects 3 }

        unisFtmFabricVlanID OBJECT-TYPE
            SYNTAX INTEGER(2..4094)
            MAX-ACCESS read-write
            STATUS current
            DESCRIPTION
                "The object is used for get and set the Fabric VlanID.
                Only is the equipment not in the stacking status, the value can be set."
            ::= { unisFtmManMIBObjects 4 }

        unisFtmFabricType OBJECT-TYPE
            SYNTAX INTEGER
                {
                outofStack(1),
                line(2),
                ring(3),
                mesh(4)
                }
            MAX-ACCESS read-only
            STATUS current
            DESCRIPTION
                "Topology type of Fabric.
                outofStack means this unit is not in stack."
            ::= { unisFtmManMIBObjects 5 }

        unisFtmManMIBNotification OBJECT IDENTIFIER ::= { unisFtmManMIB 3 }

        unisFtmUnitIDChange NOTIFICATION-TYPE
            OBJECTS { unisFtmIndex, unisFtmUnitID}
            STATUS current
            DESCRIPTION
                "When unit id changes in fabric, this trap is sent with unit index and its new id ."
            ::= { unisFtmManMIBNotification 1 }

        unisFtmUnitNameChange NOTIFICATION-TYPE
            OBJECTS { unisFtmIndex, unisFtmUnitName }
            STATUS current
            DESCRIPTION
                "When unit name changes in fabric, this trap is sent with unit index and its new name."
            ::= { unisFtmManMIBNotification 2 }

        unisFtmManMIBComformance OBJECT IDENTIFIER ::= { unisFtmManMIB 2 }

        unisFtmMIBCompliances OBJECT IDENTIFIER ::= { unisFtmManMIBComformance 1 }

        unisFtmMIBCompliance MODULE-COMPLIANCE
            STATUS current
            DESCRIPTION
                "The compliance statement for FTM implementing the MIB."
            MODULE UNIS-FTM-MIB
                MANDATORY-GROUPS { unisFtmConfigGroup, unisFtmNotificationGroup
                     }
            ::= { unisFtmMIBCompliances 1 }

        unisFtmMIBGroups OBJECT IDENTIFIER ::= { unisFtmManMIBComformance 2 }

        unisFtmConfigGroup OBJECT-GROUP
            OBJECTS { unisFtmUnitID, unisFtmUnitName, unisFtmAuthMode, unisFtmAuthValue, unisFtmFabricVlanID,
                      unisFtmFabricType }
            STATUS current
            DESCRIPTION
                "The basic collection of objects for sending trap of FTM Management."
            ::= { unisFtmMIBGroups 1 }

        unisFtmNotificationGroup NOTIFICATION-GROUP
            NOTIFICATIONS { unisFtmUnitIDChange, unisFtmUnitNameChange }
            STATUS current
            DESCRIPTION
                "The basic collection of objects for sending trap of FTM Management."
            ::= { unisFtmMIBGroups 2 }

END
