-- =========================================================================
-- Copyright (c) 2020 Unisyue Technologies Co., Ltd.  All rights reserved.
--
-- Description: Secure Shell(SSH) MIB
-- Reference: draft-ylonen-ssh-protocol-00.txt
-- Version: V1.5
-- History:
--  V1.0 2007-11-19 created by ZhangJun 03132
--       Initial version.
--  V1.1 2013-12-21 Added enum value scp(5) to unisSSHUserServiceType by DaiRuiqiang 04358.
--  V1.2 2014-01-17 Added enum value scp(4) to unisSSHSessionServiceType by DaiRuiqiang 04358.
--       2014-02-20 Added unisSCPServerEnable and unisSTelnetServerEnable by DaiRuiqiang 04358.
--  V1.3 2014-10-25 Added enum value netconf(6) to unisSSHUserServiceType,
--                  added enum value netconf(5) to unisSSHSessionServiceType by DaiRuiqiang 04358.
--  V1.4 2016-04-26 Added unisSSHUserPublicKeyName2 to UnisSSHUserConfigEntry,
--                  added unisSSHUserPublicKeyName3 to UnisSSHUserConfigEntry,
--                  added unisSSHUserPublicKeyName4 to UnisSSHUserConfigEntry,
--                  added unisSSHUserPublicKeyName5 to UnisSSHUserConfigEntry,
--                  added unisSSHUserPublicKeyName6 to UnisSSHUserConfigEntry by DaiRuiqiang 04358.
--                  Added enum values aes128CTR(5), aes192CTR(6), aes256CTR(7), aes128GCM(8),
--                  aes256GCM(9), and aes256CBC(10) to unisSSHSessionEncry by DaiRuiqiang 04358.
--       2018-02-06 Added enum value keyboard-interactive(6) in unisSSHUserAuthType by DaiRuiqiang 04358
--  V1.5 2018-06-28 Added enum value other(11) to unisSSHSessionEncry by DaiRuiqiang 04358.
-- =========================================================================
UNIS-SSH-MIB DEFINITIONS ::= BEGIN

IMPORTS
        unisCommon
    FROM UNIS-OID-MIB
        Integer32, OBJECT-TYPE, MODULE-IDENTITY, NOTIFICATION-TYPE
    FROM SNMPv2-SMI
        InetAddressType, InetAddress
    FROM INET-ADDRESS-MIB
        DisplayString, RowStatus
    FROM SNMPv2-TC;

unisSSH MODULE-IDENTITY
    LAST-UPDATED "201806280000Z"
    ORGANIZATION
        "Unisyue Technologies Co., Ltd."
    CONTACT-INFO
        ""
    DESCRIPTION
        "This MIB is used to configure SSH server."
    REVISION "201806280000Z"
    DESCRIPTION
        "Added enum value other(11) to unisSSHSessionEncry."
    REVISION "201802060000Z"
    DESCRIPTION
        "Added enum value keyboardInteractive(6) to unisSSHUserAuthType."
    REVISION "201604260000Z"
    DESCRIPTION
        "Added enum values aes128CTR(5), aes192CTR(6), aes256CTR(7), aes128GCM(8),
         aes256GCM(9), and aes256CBC(10) to unisSSHSessionEncry.
         Added unisSSHUserPublicKeyName2, and unisSSHUserPublicKeyName3, unisSSHUserPublicKeyName4,
         unisSSHUserPublicKeyName5, and unisSSHUserPublicKeyName6 to UnisSSHUserConfigEntry."
    REVISION "201410250000Z"
    DESCRIPTION
        "Added enum value netconf(6) to unisSSHUserServiceType, add enum value netconf(5) to unisSSHSessionServiceType."
    REVISION "201402200000Z"
    DESCRIPTION
        "Added unisSCPServerEnable and unisSTelnetServerEnable."
    REVISION "201401170000Z"
    DESCRIPTION
        "Added enum value scp(4) to unisSSHSessionServiceType."
    REVISION "201312210000Z"
    DESCRIPTION
        "Added enum value scp(5) to unisSSHUserServiceType."
    REVISION "200711190000Z"
    DESCRIPTION
        "The initial version."
    ::= { unisCommon 22 }

--
-- Node definitions
--
-- Scalar MIB objects are defined in this section.
unisSSHServerMIB OBJECT IDENTIFIER ::= { unisSSH 1 }

unisSSHServerMIBObjects OBJECT IDENTIFIER ::= { unisSSHServerMIB 1 }

-- Scalar MIB objects, which are considered as global variables
-- to SSH server, are defined in this section.
unisSSHServerGlobalConfig OBJECT IDENTIFIER ::= { unisSSHServerMIBObjects 1 }

unisSSHServerVersion OBJECT-TYPE
    SYNTAX      DisplayString
    MAX-ACCESS  read-only
    STATUS      current
    DESCRIPTION
        "The protocol version of the SSH server."
    ::= { unisSSHServerGlobalConfig 1 }

unisSSHServerCompatibleSSH1x OBJECT-TYPE
    SYNTAX      INTEGER
        {
            enableCompatibleSSH1x(1),
            disableCompatibleSSH1x(2)
        }
    MAX-ACCESS  read-write
    STATUS      current
    DESCRIPTION
        "Supporting compatibility with SSH versions 1.x.  It is
        known that there are still devices using the previous
        versions.  During the transition period, it is important to
        be able to work in a way that is compatible with the
        installed SSH clients and servers that use the older version
        of the protocol."
    ::= { unisSSHServerGlobalConfig 2 }

unisSSHServerRekeyInterval OBJECT-TYPE
    SYNTAX      Integer32
    MAX-ACCESS  read-write
    STATUS      current
    DESCRIPTION
        "The time interval of regenerating SSH server key.  The unit
        is hour."
    ::= { unisSSHServerGlobalConfig 3 }

unisSSHServerAuthRetries OBJECT-TYPE
    SYNTAX      Integer32
    MAX-ACCESS  read-write
    STATUS      current
    DESCRIPTION
        "The limit times of a specified user can retry."
    ::= { unisSSHServerGlobalConfig 4 }

unisSSHServerAuthTimeout OBJECT-TYPE
    SYNTAX      Integer32
    MAX-ACCESS  read-write
    STATUS      current
    DESCRIPTION
        "The SSH server has a timeout for authentication and
        disconnect if the authentication has not been accepted
        within the timeout period.  The unit is second."
    ::= { unisSSHServerGlobalConfig 5 }

unisSFTPServerIdleTimeout OBJECT-TYPE
    SYNTAX      Integer32
    MAX-ACCESS  read-write
    STATUS      current
    DESCRIPTION
        "The SFTP server has a timeout for idle connection if a user
        has no activities within the timeout period.  The unit is
        minute."
    ::= { unisSSHServerGlobalConfig 6 }

unisSSHServerEnable OBJECT-TYPE
    SYNTAX      INTEGER
        {
            enableSSHServer(1),
            disableSSHServer(2)
        }
    MAX-ACCESS  read-write
    STATUS      current
    DESCRIPTION
        "Enable SSH server function."
    ::= { unisSSHServerGlobalConfig 7 }

unisSFTPServerEnable OBJECT-TYPE
    SYNTAX      INTEGER
        {
            enableSFTPService(1),
            disableSFTPService(2)
        }
    MAX-ACCESS  read-write
    STATUS      current
    DESCRIPTION
        "Enable SFTP server function."
    ::= { unisSSHServerGlobalConfig 8 }

unisSTelnetServerEnable OBJECT-TYPE
    SYNTAX      INTEGER
        {
            enableSTelnetServer(1),
            disableSTelnetServer(2)
        }
    MAX-ACCESS  read-write
    STATUS      current
    DESCRIPTION
        "Enable STelnet server function."
    ::= { unisSSHServerGlobalConfig 9 }

unisSCPServerEnable OBJECT-TYPE
    SYNTAX      INTEGER
        {
            enableSCPService(1),
            disableSCPService(2)
        }
    MAX-ACCESS  read-write
    STATUS      current
    DESCRIPTION
        "Enable SCP server function."
    ::= { unisSSHServerGlobalConfig 10 }

-- SSH users are defined in this section.
unisSSHUserConfig OBJECT IDENTIFIER ::= { unisSSHServerMIBObjects 2 }

-- Define a group which consists of all objects used for users.
unisSSHUserConfigTable OBJECT-TYPE
    SYNTAX      SEQUENCE OF UnisSSHUserConfigEntry
    MAX-ACCESS  not-accessible
    STATUS      current
    DESCRIPTION
        "A table for managing SSH users."
    ::= { unisSSHUserConfig 1 }

unisSSHUserConfigEntry OBJECT-TYPE
    SYNTAX      UnisSSHUserConfigEntry
    MAX-ACCESS  not-accessible
    STATUS      current
    DESCRIPTION
        "SSH users configuration entry."
    INDEX
        {
            unisSSHUserName
        }
    ::= { unisSSHUserConfigTable 1 }

UnisSSHUserConfigEntry ::= SEQUENCE
    {
        unisSSHUserName             DisplayString,
        unisSSHUserServiceType      INTEGER,
        unisSSHUserAuthType         INTEGER,
        unisSSHUserPublicKeyName    DisplayString,
        unisSSHUserWorkDirectory    DisplayString,
        unisSSHUserRowStatus        RowStatus,
        unisSSHUserPublicKeyName2    DisplayString,
        unisSSHUserPublicKeyName3    DisplayString,
        unisSSHUserPublicKeyName4    DisplayString,
        unisSSHUserPublicKeyName5    DisplayString,
        unisSSHUserPublicKeyName6    DisplayString
    }

unisSSHUserName OBJECT-TYPE
    SYNTAX      DisplayString
    MAX-ACCESS  not-accessible
    STATUS      current
    DESCRIPTION
        "The name of SSH user."
    ::= { unisSSHUserConfigEntry 1 }

unisSSHUserServiceType OBJECT-TYPE
    SYNTAX      INTEGER
        {
            invalid(1),
            all(2),
            stelnet(3),
            sftp(4),
            scp(5),
            netconf(6)
        }
    MAX-ACCESS  read-create
    STATUS      current
    DESCRIPTION
        "The service type of SSH user uses."
    DEFVAL      { invalid }
    ::= { unisSSHUserConfigEntry 2 }

unisSSHUserAuthType OBJECT-TYPE
    SYNTAX      INTEGER
        {
            invalid(1),
            password(2),
            publicKey(3),
            any(4),
            publicKeyPassword(5),
            keyboardInteractive(6)
        }
    MAX-ACCESS  read-create
    STATUS      current
    DESCRIPTION
        "The authentication type of SSH user chooses."
    DEFVAL      { invalid }
    ::= { unisSSHUserConfigEntry 3 }

unisSSHUserPublicKeyName OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 4 }

unisSSHUserWorkDirectory OBJECT-TYPE
    SYNTAX      DisplayString
    MAX-ACCESS  read-create
    STATUS      current
    DESCRIPTION
        "The SFTP user's work directory associates with an existing user."
    DEFVAL      { "" }
    ::= { unisSSHUserConfigEntry 5 }

unisSSHUserRowStatus OBJECT-TYPE
    SYNTAX      RowStatus
    MAX-ACCESS  read-create
    STATUS      current
    DESCRIPTION
        "The row status variable, used in accordance to installation
        and removal conventions for conceptual rows.

        When the `unisSSHUserRowStatus' is set to active(1), no objects
        in this table can be modified.

        When 'unisSSHUserRowStatus' is set to notInService(2), every object
        except the 'unisSSHUserName' object in this table can be modified.

        To create a row in this table, a manager must set this object
        to createAndGo(4).  Until instances of all corresponding columns
        are appropriately configured, the value of the corresponding
        instance of the unisSSHUserRowStatus column is 'notReady'."
    ::= { unisSSHUserConfigEntry 6 }

unisSSHUserPublicKeyName2 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 7 }

unisSSHUserPublicKeyName3 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 8 }

unisSSHUserPublicKeyName4 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 9 }

unisSSHUserPublicKeyName5 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 10 }

unisSSHUserPublicKeyName6 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { unisSSHUserConfigEntry 11 }

-- Define a group which consists of all objects used for sessions.
unisSSHSessionInfoTable OBJECT-TYPE
    SYNTAX      SEQUENCE OF UnisSSHSessionInfoEntry
    MAX-ACCESS  not-accessible
    STATUS      current
    DESCRIPTION
        "A table for SSH sessions."
    ::= { unisSSHServerMIBObjects 3 }

unisSSHSessionInfoEntry OBJECT-TYPE
    SYNTAX      UnisSSHSessionInfoEntry
    MAX-ACCESS  not-accessible
    STATUS      current
    DESCRIPTION
        "The SSH session information entry."
    INDEX
        {
            unisSSHSessionID
        }
    ::= { unisSSHSessionInfoTable 1 }

UnisSSHSessionInfoEntry ::= SEQUENCE
    {
        unisSSHSessionID               Integer32,
        unisSSHSessionUserName         DisplayString,
        unisSSHSessionUserIpAddrType   InetAddressType,
        unisSSHSessionUserIpAddr       InetAddress,
        unisSSHSessionClientVersion    DisplayString,
        unisSSHSessionServiceType      INTEGER,
        unisSSHSessionEncry            INTEGER,
        unisSSHSessionState            INTEGER
    }

unisSSHSessionID OBJECT-TYPE
    SYNTAX      Integer32
    MAX-ACCESS  not-accessible
    STATUS      current
    DESCRIPTION
        "The identifier of SSH session."
    ::= { unisSSHSessionInfoEntry 1 }

unisSSHSessionUserName OBJECT-TYPE
    SYNTAX      DisplayString
    MAX-ACCESS  read-only
    STATUS      current
    DESCRIPTION
        "The user name of SSH session."
    ::= { unisSSHSessionInfoEntry 2 }

unisSSHSessionUserIpAddrType OBJECT-TYPE
    SYNTAX      InetAddressType
    MAX-ACCESS  read-only
    STATUS      current
    DESCRIPTION
        "The user IP address type of SSH session."
    ::= { unisSSHSessionInfoEntry 3 }

unisSSHSessionUserIpAddr OBJECT-TYPE
    SYNTAX      InetAddress
    MAX-ACCESS  read-only
    STATUS      current
    DESCRIPTION
        "The user IP address of SSH session."
    ::= { unisSSHSessionInfoEntry 4 }

unisSSHSessionClientVersion OBJECT-TYPE
    SYNTAX      DisplayString
    MAX-ACCESS  read-only
    STATUS      current
    DESCRIPTION
        "The client version of SSH session.  It is known that there are still
        devices using the previous versions."
    ::= { unisSSHSessionInfoEntry 5 }

unisSSHSessionServiceType OBJECT-TYPE
    SYNTAX      INTEGER
        {
            invalid(1),
            stelnet(2),
            sftp(3),
            scp(4),
            netconf(5)
        }
    MAX-ACCESS  read-only
    STATUS      current
    DESCRIPTION
        "The service type of SSH session."
    ::= { unisSSHSessionInfoEntry 6 }

unisSSHSessionEncry OBJECT-TYPE
    SYNTAX      INTEGER
        {
            invalid(1),
            aes128CBC(2),
            desCBC(3),
            des3CBC(4),
            aes128CTR(5),
            aes192CTR(6),
            aes256CTR(7),
            aes128GCM(8),
            aes256GCM(9),
            aes256CBC(10),
            other(11)
        }
    MAX-ACCESS  read-only
    STATUS      current
    DESCRIPTION
        "The encryption algorithm of SSH session.  There are several encryption
        algorithms used in SSH protocol, please refer to RFC4253 Section 6.3."
    ::= { unisSSHSessionInfoEntry 7 }

unisSSHSessionState OBJECT-TYPE
    SYNTAX      INTEGER
        {
            init(1),
            verExchange(2),
            keysExchange(3),
            authRequest(4),
            serviceRequest(5),
            established(6),
            disconnect(7)
        }
    MAX-ACCESS  read-only
    STATUS      current
    DESCRIPTION
        "The status of SSH session.
        init           : This session is in initial status.
        verExchange    : This session is in version exchanging.
        keysExchange   : This session is in keys exchanging.
        authRequest    : This session is in authentication requesting.
        serviceRequest : This session is in service requesting.
        established    : This session has been established.
        disconnected   : This session has been disconnected."
    ::= { unisSSHSessionInfoEntry 8 }


-- Define a group which consists of all objects used for trap.
unisSSHServerObjForTrap OBJECT IDENTIFIER ::= { unisSSHServerMIB 2 }

unisSSHAttemptUserName OBJECT-TYPE
    SYNTAX      DisplayString
    MAX-ACCESS  accessible-for-notify
    STATUS      current
    DESCRIPTION
        "The user name of the attacker who attempted to log in."
    ::= { unisSSHServerObjForTrap 1 }

unisSSHAttemptIpAddrType OBJECT-TYPE
    SYNTAX      InetAddressType
    MAX-ACCESS  accessible-for-notify
    STATUS      current
    DESCRIPTION
        "The IP address type of the attacker who attempted to log in."
    ::= { unisSSHServerObjForTrap 2 }

unisSSHAttemptIpAddr OBJECT-TYPE
    SYNTAX      InetAddress
    MAX-ACCESS  accessible-for-notify
    STATUS      current
    DESCRIPTION
        "The IP address of the attacker who attempted to log in."
    ::= { unisSSHServerObjForTrap 3 }

unisSSHUserAuthFailureReason OBJECT-TYPE
    SYNTAX      INTEGER
        {
            exceedRetries(1),
            authTimeout(2),
            otherReason(3)
        }
    MAX-ACCESS  accessible-for-notify
    STATUS      current
    DESCRIPTION
        "The reason for that a user failed to log in."
    ::= { unisSSHServerObjForTrap 4 }

--
-- Notification definitions
--
-- =================================================================
-- Traps are defined below.
unisSSHServerNotifications OBJECT IDENTIFIER ::= { unisSSHServerMIB 3 }

-- All trap definitions should be placed under this object.
unisSSHServerNotificationsPrefix OBJECT IDENTIFIER ::= { unisSSHServerNotifications 0 }

-- All objects used for TRAP only are defined here.
unisSSHUserAuthFailure NOTIFICATION-TYPE
    OBJECTS
        {
            unisSSHAttemptUserName,
            unisSSHAttemptIpAddrType,
            unisSSHAttemptIpAddr,
            unisSSHUserAuthFailureReason
        }
    STATUS      current
    DESCRIPTION
        "The trap is generated when a user fails to authentication."
    ::= { unisSSHServerNotificationsPrefix 1 }

unisSSHVersionNegotiationFailure NOTIFICATION-TYPE
    OBJECTS
        {
            unisSSHAttemptIpAddrType,
            unisSSHAttemptIpAddr
        }
    STATUS      current
    DESCRIPTION
        "The trap is generated when a user fails to negotiate SSH
        protocol version."
    ::= { unisSSHServerNotificationsPrefix 2 }

unisSSHUserLogin NOTIFICATION-TYPE
    OBJECTS
        {
            unisSSHSessionUserName,
            unisSSHSessionUserIpAddrType,
            unisSSHSessionUserIpAddr
        }
    STATUS      current
    DESCRIPTION
        "The trap is generated when a user logs in successfully."
    ::= { unisSSHServerNotificationsPrefix 3 }

unisSSHUserLogoff NOTIFICATION-TYPE
    OBJECTS
        {
            unisSSHSessionUserName,
            unisSSHSessionUserIpAddrType,
            unisSSHSessionUserIpAddr
        }
    STATUS      current
    DESCRIPTION
        "The trap is generated when a user logs off."
    ::= { unisSSHServerNotificationsPrefix 4 }

END
