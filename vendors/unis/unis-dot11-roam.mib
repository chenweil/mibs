-- =====================================================================
-- Copyright (c) 2020 Unisyue Technologies Co., Ltd.  All rights reserved.
--
-- Description: The file defines a MIB to provide WLAN roaming configuration.
-- Reference:
-- Version: V1.3
-- History:
-- V1.0 2008-7-23 created by heziqi
-- V1.1 2009-05-07 modified by Li Yugang
--      Add unisDot11RoamStatisGroup to unisDot11ROAM.
-- V1.2 2009-12-24 modified for Guangdong Mobile
--      Add unisDot11InterACRoamOutSuccCnt to unisDot11RoamStatisGroup.
--      2010-08-04 modefied by l07769 for Guangdong CMCC
--      Add unisDot11IntraACRoamingSuccCnt2, unisDot11InterACRoamingSuccCnt2
--      and unisDot11InterACRoamOutSuccCnt2 to unisDot11RoamStatis2Group.
-- V1.3 2016-3-11 modified by yubo 04460
--      Add unisDot11InterACRoamInSuccCnt to unisDot11RoamStatusGroup
--      Add unisDot11InterACRoamInSuccCnt2 to unisDot11RoamStatis2Group
-- =====================================================================
UNIS-DOT11-ROAM-MIB DEFINITIONS ::= BEGIN

IMPORTS
        TruthValue,
        MacAddress,
        RowStatus,
        TEXTUAL-CONVENTION
    FROM SNMPv2-TC
        MODULE-IDENTITY,
        OBJECT-TYPE,
        Integer32,
        Counter32
    FROM SNMPv2-SMI
        InetAddressType,
        InetAddress
    FROM INET-ADDRESS-MIB
        unisDot11
    FROM UNIS-DOT11-REF-MIB;

unisDot11ROAM MODULE-IDENTITY
    LAST-UPDATED "201603111800Z"        -- Mar 11, 2016 at 18:00 GMT
    ORGANIZATION
        "Unisyue Technologies Co., Ltd."
    CONTACT-INFO
        ""
    DESCRIPTION
        "This MIB provides information about WLAN roaming configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        BSS
        IEEE 802.11 Basic Service Set (Radio Cell).  The
        BSS of an AP comprises of the stations directly
        associating with the AP.

        Radio
        The chip set to receive and send wireless signal.

        HA
        The AC to which a wireless station is connected by
        associating with an AP for the first time is the
        HA of the station.

        FA
        An AC that is other than the HA and to which a
        station is currently connected is an FA of the
        station.

        Fast-roam capable station
        A wireless station which directly associates to
        a fast-roam service (rsn+dot1X) with one AC for
        the first time.

        Roam-out station
        A wireless station which has associated with an
        AC other than the HA in the mobility-group is
        referred to as a roam-out station at its HA.

        Roam-in station
        A wireless station which has associated with an
        AC other than the HA in the mobility-group is
        referred to as a roam-in station at the FA.

        Intra-AC roaming
        A procedure where a wireless station roams from
        one AP to another AP, which are connected to the
        same AC.

        Inter-AC roaming
        A procedure where a wireless station roams from
        one AP to another AP, which are connected to
        different ACs.

        Inter-AC fast roaming capability
        If a station uses 802.1x (RSN) authentication
        through negotiation, this station has inter-AC
        fast roaming capability.

        WLAN-tunnel
        One type of layer 2 interface which is bound with
        an IACTP data tunnel and used to tunnel
        unicast/broadcast frames between ACs."
    REVISION "201603111800Z"        -- Mar 11, 2016 at 18:00 GMT
    DESCRIPTION
            "add new nodes."
    REVISION "201008041800Z"        -- Aug 04, 2010 at 18:00 GMT
    DESCRIPTION
            "Modified to add new unisDot11RoamStatis2Group."
    REVISION "200905072000Z"
    DESCRIPTION
            "Modified to add new unisDot11RoamStatisGroup."
    REVISION "200807231200Z"
    DESCRIPTION
            "The initial revision of this MIB module."
    ::= { unisDot11 10 }

-- ==================================================================
-- Textual Conventions
-- ==================================================================
UnisDot11RoamMobileTunnelType ::=  TEXTUAL-CONVENTION
    STATUS      current
    DESCRIPTION
        "The protocol type of the mobility-tunnel.
        This object has two defined values:
        - 'ipv4', which indicates that the protocol type of the mobility-tunnel
          is IPv4.
        - 'ipv6', which indicates that the protocol type of the mobility-tunnel
          is IPv6.
        "
    SYNTAX      INTEGER
        {
            ipv4(1),
            ipv6(2)
        }

UnisDot11RoamAuthMode ::=  TEXTUAL-CONVENTION
    STATUS      current
    DESCRIPTION
        "The authentication mode of the mobility-tunnel.
        This object has two defined values:
        - 'none', which indicates that the authentication mode of the
          mobility-tunnel is None.
        - 'md5', which indicates that the authentication mode of the
          mobility-tunnel is MD5.
        "
    SYNTAX      INTEGER
        {
            none(1),
            md5(2)
        }

UnisDot11RoamIACTPStatus ::=  TEXTUAL-CONVENTION
    STATUS      current
    DESCRIPTION
        "The status of IACTP state machine."
    SYNTAX      INTEGER
        {
            init(1),
            idle(2),
            joinRequestWait(3),
            joinResponseWait(4),
            joinConfirmWait(5),
            joinError(6),
            run(7)
        }

-- ==================================================================
-- Major sections
-- ==================================================================
unisDot11RoamCfgGroup OBJECT IDENTIFIER  ::= { unisDot11ROAM 1 }
--  Roaming Configuration Group has the following children:
--  unisDot11MobGrpTable            ::= { unisDot11RoamCfgGroup 1 }
--  unisDot11MobGrpMemberTable      ::= { unisDot11RoamCfgGroup 2 }

unisDot11RoamStatusGroup OBJECT IDENTIFIER  ::= { unisDot11ROAM 2 }
--  Roaming Status Group has the following children:
--  unisDot11RoamInInfoTable             ::= { unisDot11RoamStatusGroup 1 }
--  unisDot11RoamOutInfoTable            ::= { unisDot11RoamStatusGroup 2 }
--  unisDot11RoamTrackTable              ::= { unisDot11RoamStatusGroup 3 }

unisDot11RoamStatisGroup OBJECT IDENTIFIER  ::= { unisDot11ROAM 3 }
--  Roaming Statis Group has the following children:
--  unisDot11IntraACRoamingSuccCnt       ::= { unisDot11RoamStatusGroup 1 }
--  unisDot11InterACRoamingSuccCnt       ::= { unisDot11RoamStatusGroup 2 }
--  unisDot11InterACRoamOutSuccCnt       ::= { unisDot11RoamStatusGroup 3 }
--  unisDot11InterACRoamInSuccCnt        ::= { unisDot11RoamStatusGroup 4 }

unisDot11RoamStatis2Group OBJECT IDENTIFIER  ::= { unisDot11ROAM 4 }
--  Roaming Statis Group has the following children:
--  unisDot11IntraACRoamingSuccCnt2     ::= { unisDot11RoamStatus2Group 1 }
--  unisDot11InterACRoamingSuccCnt2     ::= { unisDot11RoamStatus2Group 2 }
--  unisDot11InterACRoamOutSuccCnt2     ::= { unisDot11RoamStatus2Group 3 }
--  unisDot11InterACRoamInSuccCnt2      ::= { unisDot11RoamStatus2Group 4 }

-- ==================================================================
-- unisDot11RoamCfgGroup Definition
-- ==================================================================
-- ==================================================================
-- unisDot11MobGrpTable Definition
-- ==================================================================
unisDot11MobGrpTable OBJECT-TYPE
    SYNTAX      SEQUENCE OF UnisDot11MobGrpEntry
    MAX-ACCESS  not-accessible
    STATUS      current
    DESCRIPTION
        "The table defines the parameters for roaming group configuration."
    ::= { unisDot11RoamCfgGroup 1 }

unisDot11MobGrpEntry OBJECT-TYPE
    SYNTAX      UnisDot11MobGrpEntry
    MAX-ACCESS  not-accessible
    STATUS      current
    DESCRIPTION
        "This entry contains information of mobile group."
    INDEX
        {
            unisDot11MobGrpName
        }
    ::= { unisDot11MobGrpTable 1 }

UnisDot11MobGrpEntry ::= SEQUENCE
    {
        unisDot11MobGrpName        OCTET STRING,
        unisdot11MobGrpTunnelType  UnisDot11RoamMobileTunnelType,
        unisDot11MobGrpSrcIPAddr   InetAddress,
        unisDot11MobGrpAuthMode    UnisDot11RoamAuthMode,
        unisDot11MobGrpAuthKey     OCTET STRING,
        unisDot11MobGrpEnable      TruthValue,
        unisDot11MobGrpRowStatus   RowStatus
    }

unisDot11MobGrpName OBJECT-TYPE
    SYNTAX      OCTET STRING(SIZE(1..15))
    MAX-ACCESS  not-accessible
    STATUS      current
    DESCRIPTION
        "Represents the name of roam group."
    ::= { unisDot11MobGrpEntry 1 }

unisdot11MobGrpTunnelType OBJECT-TYPE
    SYNTAX      UnisDot11RoamMobileTunnelType
    MAX-ACCESS  read-create
    STATUS      current
    DESCRIPTION
        "Represents the protocol type of mobility-tunnel."
    DEFVAL      { ipv4 }
    ::= { unisDot11MobGrpEntry 2 }

unisDot11MobGrpSrcIPAddr OBJECT-TYPE
    SYNTAX      InetAddress
    MAX-ACCESS  read-create
    STATUS      current
    DESCRIPTION
        "Represents the IP address of tunnel source.  The IP address
         type must be the same as unisdot11MobGrpTunnelType.
         The default value is zero."
    ::= { unisDot11MobGrpEntry 3 }

unisDot11MobGrpAuthMode OBJECT-TYPE
    SYNTAX      UnisDot11RoamAuthMode
    MAX-ACCESS  read-create
    STATUS      current
    DESCRIPTION
        "Represents the authentication mode of IACTP tunnel.
         This object can be used to enable IACTP control message
         integrity authentication."
    DEFVAL      { none }
    ::= { unisDot11MobGrpEntry 4 }

unisDot11MobGrpAuthKey OBJECT-TYPE
    SYNTAX      OCTET STRING(SIZE(0..16))
    MAX-ACCESS  read-create
    STATUS      current
    DESCRIPTION
        "Represents the authentication key of IACTP tunnel.
         Authentication key to be used with the given
         authentication method.
         This object can not be modified when the value of
         unisDot11MobGrpAuthMode is 'none'."
    ::= { unisDot11MobGrpEntry 5 }

unisDot11MobGrpEnable OBJECT-TYPE
    SYNTAX      TruthValue
    MAX-ACCESS  read-create
    STATUS      current
    DESCRIPTION
        "State of a mobile group.
         'true'  : The WLAN mobility group will be enabled.
         'false' : The inter-AC tunnel communication for the
                   mobility group will be disabled.
         A mobility group can be enabled only when the source
         IP address is configured.  The other objects in this entry
         can become effective only when mobility group is enabled.
         The other objects in this entry can not be modified
         after enabling mobility group."
    DEFVAL      { false }
    ::= { unisDot11MobGrpEntry 6 }

unisDot11MobGrpRowStatus OBJECT-TYPE
    SYNTAX      RowStatus
    MAX-ACCESS  read-create
    STATUS      current
    DESCRIPTION
        "The status of this table entry."
    ::= { unisDot11MobGrpEntry 7 }

-- ==================================================================
-- unisDot11MobGrpMemberTable Definition
-- ==================================================================

unisDot11MobGrpMemberTable OBJECT-TYPE
    SYNTAX      SEQUENCE OF UnisDot11MobGrpMemberEntry
    MAX-ACCESS  not-accessible
    STATUS      current
    DESCRIPTION
        "The table defines the parameters for roaming member configuration."
    ::= { unisDot11RoamCfgGroup 2 }

unisDot11MobGrpMemberEntry OBJECT-TYPE
    SYNTAX      UnisDot11MobGrpMemberEntry
    MAX-ACCESS  not-accessible
    STATUS      current
    DESCRIPTION
        "This entry contains information of mobile group member."
    INDEX
        {
            unisDot11MobGrpName,
            unisDot11MobGrpMemberIpAddr
        }
    ::= { unisDot11MobGrpMemberTable 1 }

UnisDot11MobGrpMemberEntry ::= SEQUENCE
    {
        unisDot11MobGrpMemberIpAddr      InetAddress,
        unisDot11MobGrpMemberStatus      UnisDot11RoamIACTPStatus,
        unisDot11MobGrpMemberIf          OCTET STRING,
        unisDot11MobGrpMemberUpTime      Integer32,
        unisDot11MobGrpMemberRowStatus   RowStatus
    }

unisDot11MobGrpMemberIpAddr OBJECT-TYPE
    SYNTAX      InetAddress
    MAX-ACCESS  not-accessible
    STATUS      current
    DESCRIPTION
        "Represents the IP address of group member.  It can not be
         the same as the source IP address of the mobile group.
         The address type must be the same as the unisdot11MobGrpTunnelType."
    ::= { unisDot11MobGrpMemberEntry 1 }

unisDot11MobGrpMemberStatus OBJECT-TYPE
    SYNTAX      UnisDot11RoamIACTPStatus
    MAX-ACCESS  read-only
    STATUS      current
    DESCRIPTION
        "Represents the status of group member."
    ::= { unisDot11MobGrpMemberEntry 2 }

unisDot11MobGrpMemberIf OBJECT-TYPE
    SYNTAX      OCTET STRING
    MAX-ACCESS  read-only
    STATUS      current
    DESCRIPTION
        "Represents the tunnel interface name of group member."
    ::= { unisDot11MobGrpMemberEntry 3 }

unisDot11MobGrpMemberUpTime OBJECT-TYPE
    SYNTAX      Integer32
    UNITS       "second"
    MAX-ACCESS  read-only
    STATUS      current
    DESCRIPTION
        "Represents the sustaining time from tunnel up.  If tunnel
         is down, MemberUpTime is zero."
    ::= { unisDot11MobGrpMemberEntry 4 }

unisDot11MobGrpMemberRowStatus OBJECT-TYPE
    SYNTAX      RowStatus
    MAX-ACCESS  read-create
    STATUS      current
    DESCRIPTION
        "The status of this table entry."
    ::= { unisDot11MobGrpMemberEntry 5 }

-- ==================================================================
-- unisDot11RoamStatusGroup Definition
-- ==================================================================
-- ==================================================================
-- unisDot11RoamInInfoTable Definition
-- ==================================================================
unisDot11RoamInInfoTable OBJECT-TYPE
    SYNTAX      SEQUENCE OF UnisDot11RoamInInfoEntry
    MAX-ACCESS  not-accessible
    STATUS      current
    DESCRIPTION
        "The table can used to display the information of roaming in client."
    ::= { unisDot11RoamStatusGroup 1 }

unisDot11RoamInInfoEntry OBJECT-TYPE
    SYNTAX      UnisDot11RoamInInfoEntry
    MAX-ACCESS  not-accessible
    STATUS      current
    DESCRIPTION
        "This entry contains information of roaming in client."
    INDEX
        {
            unisDot11RoamClientMAC
        }
    ::= { unisDot11RoamInInfoTable 1 }

UnisDot11RoamInInfoEntry ::= SEQUENCE
    {
        unisDot11RoamClientMAC         MacAddress,
        unisDot11RoamInClientBSSID     MacAddress,
        unisDot11RoamInClientVlanID    Integer32,
        unisDot11RoamInHomeACIPType    InetAddressType,
        unisDot11RoamInHomeACIPAddr    InetAddress
    }

unisDot11RoamClientMAC OBJECT-TYPE
    SYNTAX      MacAddress
    MAX-ACCESS  not-accessible
    STATUS      current
    DESCRIPTION
        "Represents the MAC address of roaming in client."
    ::= { unisDot11RoamInInfoEntry 1 }

unisDot11RoamInClientBSSID OBJECT-TYPE
    SYNTAX      MacAddress
    MAX-ACCESS  read-only
    STATUS      current
    DESCRIPTION
        "Represents BSSID of the AP to which the Roam-In client is associated."
    ::= { unisDot11RoamInInfoEntry 2 }

unisDot11RoamInClientVlanID OBJECT-TYPE
    SYNTAX      Integer32
    MAX-ACCESS  read-only
    STATUS      current
    DESCRIPTION
        "Represents the VLAN ID of Roam-In client."
    ::= { unisDot11RoamInInfoEntry 3 }

unisDot11RoamInHomeACIPType OBJECT-TYPE
    SYNTAX      InetAddressType
    MAX-ACCESS  read-only
    STATUS      current
    DESCRIPTION
        "Represents the protocol type of home AC address."
    ::= { unisDot11RoamInInfoEntry 4 }

unisDot11RoamInHomeACIPAddr OBJECT-TYPE
    SYNTAX      InetAddress
    MAX-ACCESS  read-only
    STATUS      current
    DESCRIPTION
        "Represents the address of home AC."
    ::= { unisDot11RoamInInfoEntry 5 }

-- ==================================================================
-- unisDot11RoamOutInfoTable Definition
-- ==================================================================

unisDot11RoamOutInfoTable OBJECT-TYPE
    SYNTAX      SEQUENCE OF UnisDot11RoamOutInfoEntry
    MAX-ACCESS  not-accessible
    STATUS      current
    DESCRIPTION
        "The table can used to display the information of roaming out client."
    ::= { unisDot11RoamStatusGroup 2 }

unisDot11RoamOutInfoEntry OBJECT-TYPE
    SYNTAX      UnisDot11RoamOutInfoEntry
    MAX-ACCESS  not-accessible
    STATUS      current
    DESCRIPTION
        "This entry contains information of roaming out client."
    INDEX
        {
            unisDot11RoamClientMAC
        }
    ::= { unisDot11RoamOutInfoTable 1 }

UnisDot11RoamOutInfoEntry ::= SEQUENCE
    {
        unisDot11RoamOutClientBSSID       MacAddress,
        unisDot11RoamOutClientVlanID      Integer32,
        unisDot11RoamOutForeignACIPType   InetAddressType,
        unisDot11RoamOutForeignACIPAddr   InetAddress,
        unisDot11RoamOutClientUpTime      Integer32
    }

unisDot11RoamOutClientBSSID OBJECT-TYPE
    SYNTAX      MacAddress
    MAX-ACCESS  read-only
    STATUS      current
    DESCRIPTION
        "Represents the BSSID of the AP to which the Roam-Out client is
         associated."
    ::= { unisDot11RoamOutInfoEntry 1 }

unisDot11RoamOutClientVlanID OBJECT-TYPE
    SYNTAX      Integer32
    MAX-ACCESS  read-only
    STATUS      current
    DESCRIPTION
        "Represents the VLAN ID of Roam-Out client."
    ::= { unisDot11RoamOutInfoEntry 2 }

unisDot11RoamOutForeignACIPType OBJECT-TYPE
    SYNTAX      InetAddressType
    MAX-ACCESS  read-only
    STATUS      current
    DESCRIPTION
        "Represents the protocol type of foreign AC address."
    ::= { unisDot11RoamOutInfoEntry 3 }

unisDot11RoamOutForeignACIPAddr OBJECT-TYPE
    SYNTAX      InetAddress
    MAX-ACCESS  read-only
    STATUS      current
    DESCRIPTION
        "Represents the address of foreign AC."
    ::= { unisDot11RoamOutInfoEntry 4 }

unisDot11RoamOutClientUpTime OBJECT-TYPE
    SYNTAX      Integer32
    UNITS       "second"
    MAX-ACCESS  read-only
    STATUS      current
    DESCRIPTION
        "Represents how long the Roam-Out client is associated with the foreign
         AC."
    ::= { unisDot11RoamOutInfoEntry 5 }

-- ==================================================================
-- unisDot11RoamTrackTable Definition
-- ==================================================================
unisDot11RoamTrackTable OBJECT-TYPE
    SYNTAX      SEQUENCE OF UnisDot11RoamTrackEntry
    MAX-ACCESS  not-accessible
    STATUS      current
    DESCRIPTION
        "The table contains the roam-track information of a
         specified client on the client's HA."
    ::= { unisDot11RoamStatusGroup 3 }

unisDot11RoamTrackEntry OBJECT-TYPE
    SYNTAX      UnisDot11RoamTrackEntry
    MAX-ACCESS  not-accessible
    STATUS      current
    DESCRIPTION
        "This entry contains information of a specified client on the
         client's HA."
    INDEX
        {
            unisDot11RoamTrackIndex
        }
    ::= { unisDot11RoamTrackTable 1 }

UnisDot11RoamTrackEntry ::= SEQUENCE
    {
        unisDot11RoamTrackIndex        Integer32,
        unisDot11RoamTrackClientMAC    MacAddress,
        unisDot11RoamTrackBSSID        MacAddress,
        unisDot11RoamTrackUpTime       Integer32,
        unisDot11RoamTrackACIPType     InetAddressType,
        unisDot11RoamTrackACIPAddr     InetAddress
    }

unisDot11RoamTrackIndex OBJECT-TYPE
    SYNTAX      Integer32
    MAX-ACCESS  not-accessible
    STATUS      current
    DESCRIPTION
        "Represents the index of this entry."
    ::= { unisDot11RoamTrackEntry 1 }

unisDot11RoamTrackClientMAC OBJECT-TYPE
    SYNTAX      MacAddress
    MAX-ACCESS  read-only
    STATUS      current
    DESCRIPTION
        "Represents the MAC address of the roamed client."
    ::= { unisDot11RoamTrackEntry 2 }

unisDot11RoamTrackBSSID OBJECT-TYPE
    SYNTAX      MacAddress
    MAX-ACCESS  read-only
    STATUS      current
    DESCRIPTION
        "Represents the BSSID of the AP with which the client is associated."
    ::= { unisDot11RoamTrackEntry 3 }

unisDot11RoamTrackUpTime OBJECT-TYPE
    SYNTAX      Integer32
    UNITS       "second"
    MAX-ACCESS  read-only
    STATUS      current
    DESCRIPTION
        "Represents how long the client is associated with the BSSID."
    ::= { unisDot11RoamTrackEntry 4 }

unisDot11RoamTrackACIPType OBJECT-TYPE
    SYNTAX      InetAddressType
    MAX-ACCESS  read-only
    STATUS      current
    DESCRIPTION
        "Represents the protocol type of the IP address of the access
         controller with which the client is connected."
    ::= { unisDot11RoamTrackEntry 5 }

unisDot11RoamTrackACIPAddr OBJECT-TYPE
    SYNTAX      InetAddress
    MAX-ACCESS  read-only
    STATUS      current
    DESCRIPTION
        "Represents the IP address of the access controller with which
         the client is connected."
    ::= { unisDot11RoamTrackEntry 6 }

-- ==================================================================
-- unisDot11RoamStatisGroup Definition
-- ==================================================================
unisDot11IntraACRoamingSuccCnt OBJECT-TYPE
    SYNTAX      Integer32
    MAX-ACCESS  read-only
    STATUS      current
    DESCRIPTION
        "Represents the count of client successfully roam Intra-AC."
    ::= { unisDot11RoamStatisGroup 1 }

unisDot11InterACRoamingSuccCnt OBJECT-TYPE
    SYNTAX      Integer32
    MAX-ACCESS  read-only
    STATUS      current
    DESCRIPTION
        "Represents the count of client successfully roam in Inter-AC."
    ::= { unisDot11RoamStatisGroup 2 }

unisDot11InterACRoamOutSuccCnt OBJECT-TYPE
    SYNTAX      Integer32
    MAX-ACCESS  read-only
    STATUS      current
    DESCRIPTION
        "Represents the count of client successfully roam out Inter-AC."
    ::= { unisDot11RoamStatisGroup 3 }

unisDot11InterACRoamInSuccCnt OBJECT-TYPE
    SYNTAX      Integer32
    MAX-ACCESS  read-only
    STATUS      current
    DESCRIPTION
        "Represents the number of clients successfully roamed in inter-AC roaming."
    ::= { unisDot11RoamStatisGroup 4 }

-- ==================================================================
-- End of unisDot11RoamStatisGroup Definition
-- ==================================================================

-- ==================================================================
-- unisDot11RoamStatis2Group Definition
-- ==================================================================
unisDot11IntraACRoamingSuccCnt2 OBJECT-TYPE
    SYNTAX      Counter32
    MAX-ACCESS  read-only
    STATUS      current
    DESCRIPTION
        "Represents the count of client successfully roam Intra-AC in Counter32."
    ::= { unisDot11RoamStatis2Group 1 }

unisDot11InterACRoamingSuccCnt2 OBJECT-TYPE
    SYNTAX      Counter32
    MAX-ACCESS  read-only
    STATUS      current
    DESCRIPTION
        "Represents the count of client successfully roam in Inter-AC in Counter32."
    ::= { unisDot11RoamStatis2Group 2 }

unisDot11InterACRoamOutSuccCnt2 OBJECT-TYPE
    SYNTAX      Counter32
    MAX-ACCESS  read-only
    STATUS      current
    DESCRIPTION
        "Represents the count of client successfully roam out Inter-AC in Counter32."
    ::= { unisDot11RoamStatis2Group 3 }

unisDot11InterACRoamInSuccCnt2 OBJECT-TYPE
    SYNTAX      Counter32
    MAX-ACCESS  read-only
    STATUS      current
    DESCRIPTION
        "Represents the number of clients successfully roamed in inter-AC roaming in Counter32."
    ::= { unisDot11RoamStatis2Group 4 }

-- ==================================================================
-- End of unisDot11RoamStatis2Group Definition
-- ==================================================================
END
