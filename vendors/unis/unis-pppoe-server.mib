-- =================================================================
-- Copyright (c) 2020 Unisyue Technologies Co., Ltd.  All rights reserved.
--
-- Description: PPPoE server MIB
-- Reference:
-- Version:     V1.1
-- History:
-- V1.0 Initial version by y04444
-- V1.1 2009-09-07 Modify by yuhaibo
--      Add PPPoE server trap
-- =================================================================
UNIS-PPPOE-SERVER-MIB DEFINITIONS ::= BEGIN
IMPORTS
    unisCommon
        FROM UNIS-OID-MIB
    OBJECT-TYPE, MODULE-IDENTITY, Integer32, Counter32, NOTIFICATION-TYPE
        FROM SNMPv2-SMI;

unisPPPoEServer MODULE-IDENTITY
    LAST-UPDATED "200905060000Z"            -- May 06th, 2009 at 00:00 GMT
    ORGANIZATION
        "Unisyue Technologies Co., Ltd."
    CONTACT-INFO
        ""
    DESCRIPTION
        "The MIB module is used for PPPoE server."
    REVISION    "200905060000Z"
    DESCRIPTION
        "Initial version"
    ::= { unisCommon 102 }

unisPPPoEServerObject OBJECT IDENTIFIER ::= { unisPPPoEServer 1 }

--
-- PPPOE SERVER MAXIMUM SESSIONS SUPPORT
--

unisPPPoEServerMaxSessions OBJECT-TYPE
    SYNTAX      Integer32
    MAX-ACCESS  read-only
    STATUS      current
    DESCRIPTION
        "The maximum sessions supported by PPPoE server."
    ::= { unisPPPoEServerObject 1 }

--
-- PPPOE SERVER CURRENT SESSION NUMBERS
--

unisPPPoEServerCurrSessions OBJECT-TYPE
    SYNTAX      Integer32
    MAX-ACCESS  read-only
    STATUS      current
    DESCRIPTION
        "The number of current sessions on the PPPoE server."
    ::= { unisPPPoEServerObject 2 }

--
-- PPPOE SERVER AUTHENTICATION REQUEST NUMBERS
--

unisPPPoEServerAuthRequests OBJECT-TYPE
    SYNTAX      Counter32
    MAX-ACCESS  read-only
    STATUS      current
    DESCRIPTION
        "The number of authentication requests."
    ::= { unisPPPoEServerObject 3 }

--
-- PPPOE SERVER AUTHENTICATION SUCCESS NUMBERS
--

unisPPPoEServerAuthSuccesses OBJECT-TYPE
    SYNTAX      Counter32
    MAX-ACCESS  read-only
    STATUS      current
    DESCRIPTION
        "The number of authentication succeses."
    ::= { unisPPPoEServerObject 4 }

--
-- PPPOE SERVER AUTHENTICATION FAIL NUMBERS
--

unisPPPoEServerAuthFailures OBJECT-TYPE
    SYNTAX      Counter32
    MAX-ACCESS  read-only
    STATUS      current
    DESCRIPTION
        "The number of authentication failure."
    ::= { unisPPPoEServerObject 5 }

--
-- PPPOE SERVER ABNORMAL OFFLINE COUNT THRESHOLD
--

unisPPPoESAbnormOffsThreshold OBJECT-TYPE
    SYNTAX      Integer32 (0..65535)
    MAX-ACCESS  read-write
    STATUS      current
    DESCRIPTION
        "The threshold of abnormal offline count."
    ::= { unisPPPoEServerObject 6 }

--
-- PPPOE SERVER ABNORMAL OFFLINE PERCENT THRESHOLD
--

unisPPPoESAbnormOffPerThreshold OBJECT-TYPE
    SYNTAX      Integer32 (0..100)
    MAX-ACCESS  read-write
    STATUS      current
    DESCRIPTION
        "The threshold of abnormal offline percent."
    ::= { unisPPPoEServerObject 7 }

--
-- PPPOE SERVER NORMAL OFFLINE PERCENT THRESHOLD
--

unisPPPoESNormOffPerThreshold OBJECT-TYPE
    SYNTAX      Integer32 (0..100)
    MAX-ACCESS  read-write
    STATUS      current
    DESCRIPTION
        "The threshold of normal offline percent."
    ::= { unisPPPoEServerObject 8 }

--
-- Define the PPPoE Server Traps.
--
    unisPPPoEServerTraps OBJECT IDENTIFIER ::= { unisPPPoEServer 2 }

    unisPPPoeServerTrapPrefix OBJECT IDENTIFIER ::= { unisPPPoEServerTraps 0 }

    unisPPPoESAbnormOffsAlarm NOTIFICATION-TYPE
        STATUS      current
        DESCRIPTION
            "This trap is generated when the PPPoE server abnormal
            offline counts over threshold in five minutes."
        ::= { unisPPPoeServerTrapPrefix 1 }

    unisPPPoESAbnormOffPerAlarm NOTIFICATION-TYPE
        STATUS      current
        DESCRIPTION
            "This trap is generated when the PPPoE server abnormal
            offline percent over threshold in five minutes."
        ::= { unisPPPoeServerTrapPrefix 2 }

    unisPPPoESNormOffPerAlarm NOTIFICATION-TYPE
        STATUS      current
        DESCRIPTION
            "This trap is generated when the PPPoE server normal
            offline percent under threshold in five minutes."
        ::= { unisPPPoeServerTrapPrefix 3 }

END
