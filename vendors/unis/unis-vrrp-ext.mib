-- =========================================================================
-- Copyright (c) 2020 Unisyue Technologies Co., Ltd.  All rights reserved.
--
-- Description: This file describes various common MIB objects implemented 
-- by both Routers and Switches.
-- Reference: VRRP-MIB
-- Version: V1.0
-- History:
--      V1.0 2004-12-09
--        Initial version
-- =========================================================================
UNIS-VRRP-EXT-MIB DEFINITIONS ::= BEGIN

 IMPORTS
     MODULE-IDENTITY, OBJECT-TYPE, Integer32                         
         FROM SNMPv2-SMI

     RowStatus       
         FROM SNMPv2-TC

     ifIndex               
         FROM IF-MIB  

     vrrpOperVrId                        
         FROM VRRP-MIB     

     unisCommon                          
         FROM UNIS-OID-MIB;


 unisVrrpExt MODULE-IDENTITY
     LAST-UPDATED 
         "200412090000Z"
     ORGANIZATION
         "Unisyue Technologies Co., Ltd."
     CONTACT-INFO
         ""
     DESCRIPTION
         "This MIB describes objects used for managing Virtual Router
         Redundancy Protocol (VRRP) routers."
     ::= { unisCommon 24 }


-- ===================================================================
--  Start of MIB objects
-- ===================================================================

 unisVrrpExtMibObject      OBJECT IDENTIFIER ::= { unisVrrpExt 1 }        

-- ===================================================================
--  VRRP EXT Table
-- ===================================================================

 unisVrrpExtTable OBJECT-TYPE
     SYNTAX       SEQUENCE OF UnisVrrpExtEntry
     MAX-ACCESS   not-accessible
     STATUS       current
     DESCRIPTION
         "Table extends for a VRRP router which consists of a
         sequence (i.e., one or more conceptual rows) of
         unisVrrpExtEntry items."
     ::= { unisVrrpExtMibObject 1 }

 unisVrrpExtEntry OBJECT-TYPE
     SYNTAX       UnisVrrpExtEntry
     MAX-ACCESS   not-accessible
     STATUS       current
     DESCRIPTION
         "An entry in the unisVrrpExtTable containing the status
         values of a virtual router."
     INDEX    { ifIndex, vrrpOperVrId, unisVrrpExtTrackInterface }
     ::= { unisVrrpExtTable 1 }

 UnisVrrpExtEntry ::=
     SEQUENCE {
         unisVrrpExtTrackInterface
             INTEGER,
         unisVrrpExtPriorityReduce
             Integer32,
         unisVrrpExtRowStatus
             RowStatus
 }

 unisVrrpExtTrackInterface OBJECT-TYPE
     SYNTAX INTEGER (0..2147483647)
     MAX-ACCESS not-accessible
     STATUS current
     DESCRIPTION
         "This value is the ifIndex that identifies which interface 
         the virtual router tracked."
     ::= { unisVrrpExtEntry 1 }

 unisVrrpExtPriorityReduce  OBJECT-TYPE
     SYNTAX       Integer32 (1..255)
     MAX-ACCESS   read-create
     STATUS       current
     DESCRIPTION
         "This value identifies how much priority of a virtual router
         will be reduced/increased when the interface tracked is down/up."
     DEFVAL { 10 }
     ::= { unisVrrpExtEntry 2 }

 unisVrrpExtRowStatus OBJECT-TYPE
     SYNTAX       RowStatus
     MAX-ACCESS   read-create
     STATUS       current
     DESCRIPTION   
         "The row status variable, used according to installation
         and removal conventions for conceptual rows. Setting this
         object to active(1) or createAndGo(4) results in the
         addition of the ifIndex tracked by a virtual router.
         Destroying the entry removes the tracked ifIndex from the 
         virtual router. Other values is not supported now."
     ::= { unisVrrpExtEntry 3 }

END
