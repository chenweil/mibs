-- ==================================================================
-- Copyright (c) 2020 Unisyue Technologies Co., Ltd.  All rights reserved.
--
-- Description: Igmp snooping MIB
-- Reference:
-- Version: V1.4
-- History:
--(1) Created by Zhangshilin, 2001.06.29
--(2) Revised by Qi Zhenglin, 2002.1.8
-- V1.1 2004-10-12 updated by gaolong
--        Import TEXTUAL-CONVENTION.
--        Relocate unisLswIgmpsnoopingMib MODULE-IDENTITY clause.
-- V1.2 Revised by yaochunyan, 2004.11.28
--        V1.2 Add unisIgmpSnoopingGroupLimitTable,
--        unisIgmpSnoopingFastLeaveTable and
--        unisIgmpSnoopingGroupPolicyTable.
--      Adjust format of the whole file by gaolong.
-- V1.3 2005-3-9 updated by fuzhenyu
--       Add object unisIgmpSnoopingNonFloodingStatus.
--       Change the descriptions of unisIgmpSnoopingGroupIfIndex,
--       unisIgmpSnoopingFastLeaveIfIndex, unisIgmpSnoopingGroupPolicyIfIndex
-- V1.4 2005-3-22 updated by wangxiaodong
--      Add unisIgmpSnoopingVlanStatusTable
--      Add unisRecvIGMPGQueryNum, unisRecvIGMPSQueryNum,
--          unisRecvIGMPV1ReportNum, unisRecvIGMPV2ReportNum,
--          unisRecvIGMPLeaveNum, unisRecvErrorIGMPPacketNum,
--          unisSentIGMPSQueryNum, unisIgmpSnoopingClearStats
--      Adjust file format
-- ==================================================================
--
-- ==================================================================
--
-- Varibles and types be imported
--
-- ==================================================================
UNIS-LswIGSP-MIB DEFINITIONS ::= BEGIN
IMPORTS

    Integer32,MODULE-IDENTITY,OBJECT-TYPE,Unsigned32,Counter32
        FROM SNMPv2-SMI

    TEXTUAL-CONVENTION,RowStatus
        FROM SNMPv2-TC

    unislswCommon
        FROM UNIS-OID-MIB

    InterfaceIndex
        FROM IF-MIB;

    unisLswIgmpsnoopingMib MODULE-IDENTITY
        LAST-UPDATED "200106290000Z"
        ORGANIZATION
            "Unisyue Technologies Co., Ltd."
        CONTACT-INFO
            ""
        DESCRIPTION
            ""
        REVISION "200106290000Z"
        DESCRIPTION
            ""
        ::= { unislswCommon  7 }

    EnabledStatus ::= TEXTUAL-CONVENTION
        STATUS      current
        DESCRIPTION
            "A simple status value for the object."
        SYNTAX      INTEGER { enabled(1), disabled(2) }


-- ==================================================================
--
-- ======================= definition begin =========================
--
-- ==================================================================

    unisLswIgmpsnoopingMibObject OBJECT IDENTIFIER ::= {   unisLswIgmpsnoopingMib 1  }

    unisIgmpSnoopingStatus    OBJECT-TYPE
        SYNTAX  EnabledStatus
        MAX-ACCESS read-write
        STATUS current
        DESCRIPTION "Configure to enable IGMP Snooping."
        ::= { unisLswIgmpsnoopingMibObject  1 }

    unisIgmpSnoopingRouterPortAge  OBJECT-TYPE
        SYNTAX  INTEGER (1..1000)
        MAX-ACCESS read-write
        STATUS current
        DESCRIPTION "Configure the aging time of the router port."
        DEFVAL  {105}
        ::= { unisLswIgmpsnoopingMibObject  2 }

    unisIgmpSnoopingResponseTime  OBJECT-TYPE
        SYNTAX  INTEGER   (1..25)
        MAX-ACCESS read-write
        STATUS current
        DESCRIPTION "Configure the maximum query response time."
        DEFVAL  {10}
        ::= { unisLswIgmpsnoopingMibObject  3 }

    unisIgmpSnoopingHostTime   OBJECT-TYPE
        SYNTAX  INTEGER  (200..1000)
        MAX-ACCESS read-write
        STATUS current
        DESCRIPTION "Configure the aging time of the multicast group port."
        DEFVAL  {260}
        ::= { unisLswIgmpsnoopingMibObject  4 }

    unisIgmpSnoopingGroupLimitTable OBJECT-TYPE
        SYNTAX  SEQUENCE OF UnisIgmpSnoopingGroupLimitEntry
        MAX-ACCESS not-accessible
        STATUS current
        DESCRIPTION
            "The table lists the maximum group number that one
             interface could do IGMP Snooping."
        ::= { unisLswIgmpsnoopingMibObject  5 }

    unisIgmpSnoopingGroupLimitEntry OBJECT-TYPE
        SYNTAX  UnisIgmpSnoopingGroupLimitEntry
        MAX-ACCESS not-accessible
        STATUS current
        DESCRIPTION
            "An entry (conceptual row) representing  the maximum
             group number on an interface which IGMP Snooping operation
             is enabled."
        INDEX  { unisIgmpSnoopingGroupIfIndex }
        ::= { unisIgmpSnoopingGroupLimitTable 1 }

    UnisIgmpSnoopingGroupLimitEntry ::= SEQUENCE {
        unisIgmpSnoopingGroupIfIndex    InterfaceIndex,
        unisIgmpSnoopingGroupLimitNumber  Unsigned32
        }

    unisIgmpSnoopingGroupIfIndex OBJECT-TYPE
        SYNTAX  InterfaceIndex
        MAX-ACCESS not-accessible
        STATUS current
        DESCRIPTION
            "The ifIndex value of the port on which IGMP
             snooping is enabled."
        ::= { unisIgmpSnoopingGroupLimitEntry 1 }

    unisIgmpSnoopingGroupLimitNumber OBJECT-TYPE
        SYNTAX  Unsigned32
        MAX-ACCESS read-write
        STATUS current
        DESCRIPTION
            "The maxmum group number of IGMP Snooping on a port."
        DEFVAL  { 4294967295 }
        ::= { unisIgmpSnoopingGroupLimitEntry 2 }

    unisIgmpSnoopingFastLeaveTable OBJECT-TYPE
        SYNTAX  SEQUENCE OF UnisIgmpSnoopingFastLeaveEntry
        MAX-ACCESS not-accessible
        STATUS current
        DESCRIPTION
            "The table specifies the fast leave status
             on those ports that do IGMP Snooping."
        ::= { unisLswIgmpsnoopingMibObject  6 }

    unisIgmpSnoopingFastLeaveEntry OBJECT-TYPE
        SYNTAX  UnisIgmpSnoopingFastLeaveEntry
        MAX-ACCESS not-accessible
        STATUS current
        DESCRIPTION
            "An entry specifies the fast leave status
             on those ports that do IGMP Snooping."
        INDEX  { unisIgmpSnoopingFastLeaveIfIndex }
        ::= { unisIgmpSnoopingFastLeaveTable 1 }

    UnisIgmpSnoopingFastLeaveEntry ::= SEQUENCE {
        unisIgmpSnoopingFastLeaveIfIndex  InterfaceIndex,
        unisIgmpSnoopingFastLeaveStatus  EnabledStatus
        }

    unisIgmpSnoopingFastLeaveIfIndex OBJECT-TYPE
        SYNTAX  InterfaceIndex
        MAX-ACCESS not-accessible
        STATUS current
        DESCRIPTION
            "The ifIndex value of the port on which IGMP
             snooping is enabled."
        ::= { unisIgmpSnoopingFastLeaveEntry 1 }

    unisIgmpSnoopingFastLeaveStatus OBJECT-TYPE
        SYNTAX  EnabledStatus
        MAX-ACCESS read-write
        STATUS current
        DESCRIPTION
            "The fast leave status of the port on which IGMP
             Snooping is enabled."
        DEFVAL  { 2 }
        ::= { unisIgmpSnoopingFastLeaveEntry 2 }

    unisIgmpSnoopingGroupPolicyTable OBJECT-TYPE
        SYNTAX  SEQUENCE OF UnisIgmpSnoopingGroupPolicyEntry
        MAX-ACCESS not-accessible
        STATUS current
        DESCRIPTION
            "This is a table specifies the group policy parameter and
             Vlan ID of the IGMP Snooping port."
        ::= { unisLswIgmpsnoopingMibObject  7 }

    unisIgmpSnoopingGroupPolicyEntry OBJECT-TYPE
        SYNTAX  UnisIgmpSnoopingGroupPolicyEntry
        MAX-ACCESS not-accessible
        STATUS current
        DESCRIPTION
            "An entry representing the group policy parameter and Vlan ID
             of a port on which IGMP Snooping operation is enabled."
        INDEX  { unisIgmpSnoopingGroupPolicyIfIndex,
            unisIgmpSnoopingGroupPolicyVlanID }
        ::= { unisIgmpSnoopingGroupPolicyTable 1 }

    UnisIgmpSnoopingGroupPolicyEntry ::= SEQUENCE {
        unisIgmpSnoopingGroupPolicyIfIndex  InterfaceIndex,
        unisIgmpSnoopingGroupPolicyVlanID  Integer32,
        unisIgmpSnoopingGroupPolicyParameter  Integer32,
        unisIgmpSnoopingGroupPolicyStatus  RowStatus
        }

    unisIgmpSnoopingGroupPolicyIfIndex OBJECT-TYPE
        SYNTAX  InterfaceIndex
        MAX-ACCESS not-accessible
        STATUS current
        DESCRIPTION
            "The ifIndex value of the port on which
             IGMP Snooping is enabled."
        ::= { unisIgmpSnoopingGroupPolicyEntry 1 }

    unisIgmpSnoopingGroupPolicyVlanID OBJECT-TYPE
        SYNTAX  Integer32(1..4094)
        MAX-ACCESS not-accessible
        STATUS current
        DESCRIPTION
            "The Vlan ID which the IGMP Snooping port
             is attached to."
        ::= { unisIgmpSnoopingGroupPolicyEntry 2 }

    unisIgmpSnoopingGroupPolicyParameter OBJECT-TYPE
        SYNTAX  Integer32(2000..2999)
        MAX-ACCESS read-create
        STATUS current
        DESCRIPTION
            "The ACL Number which is used as the group policy parameter
             of the IGMP Snooping port."
        ::= { unisIgmpSnoopingGroupPolicyEntry 3 }

    unisIgmpSnoopingGroupPolicyStatus OBJECT-TYPE
        SYNTAX  RowStatus
        MAX-ACCESS read-create
        STATUS current
        DESCRIPTION
            "This object is used to create or delete a row
             and represent the current status of this row.
             Now support three state:CreateAndGo,Active,Destroy."
        ::= { unisIgmpSnoopingGroupPolicyEntry 4 }

    unisIgmpSnoopingNonFloodingStatus OBJECT-TYPE
        SYNTAX EnabledStatus
        MAX-ACCESS read-write
        STATUS current
        DESCRIPTION
            "Configure to disable multicast flooding when no member exists
             in the destinated group. To use this function,IGMP snooping
             must be enabled."
        ::= { unisLswIgmpsnoopingMibObject 8 }

    unisIgmpSnoopingVlanStatusTable OBJECT-TYPE
        SYNTAX     SEQUENCE OF UnisIgmpSnoopingVlanStatusEntry
        MAX-ACCESS not-accessible
        STATUS     current
        DESCRIPTION
            "The table used to enable or disable IGMP snooping 
             on the specified VLAN."
        ::= { unisLswIgmpsnoopingMibObject 9 }

    unisIgmpSnoopingVlanStatusEntry OBJECT-TYPE
        SYNTAX     UnisIgmpSnoopingVlanStatusEntry
        MAX-ACCESS not-accessible
        STATUS     current
        DESCRIPTION
            "An entry representing the IGMP snooping status on 
             the specified VLAN."
        INDEX      {  unisIgmpSnoopingVlanID }
        ::= { unisIgmpSnoopingVlanStatusTable 1 }

    UnisIgmpSnoopingVlanStatusEntry ::= SEQUENCE {
        unisIgmpSnoopingVlanID            Integer32,
        unisIgmpSnoopingVlanEnabled       EnabledStatus
        }
        
    unisIgmpSnoopingVlanID OBJECT-TYPE
        SYNTAX     Integer32(1..4094)
        MAX-ACCESS not-accessible
        STATUS     current
        DESCRIPTION
            "An index uniquely identifies on which VLAN IGMP 
             snooping is enabled or disabled. "
        ::= { unisIgmpSnoopingVlanStatusEntry 1 }

    unisIgmpSnoopingVlanEnabled OBJECT-TYPE
        SYNTAX     EnabledStatus
        MAX-ACCESS read-write
        STATUS     current
        DESCRIPTION
            "Indicating whether IGMP snooping is enabled on this VLAN."
        DEFVAL     { disabled }
        ::= { unisIgmpSnoopingVlanStatusEntry 2 }

    unisIgmpSnoopingStatsObjects OBJECT IDENTIFIER ::= { unisLswIgmpsnoopingMibObject 10 }

    unisRecvIGMPGQueryNum OBJECT-TYPE
        SYNTAX     Counter32
        MAX-ACCESS read-only
        STATUS     current
        DESCRIPTION
            "The statistics of IGMP general query packets received on
             the device."
        ::= { unisIgmpSnoopingStatsObjects 1 }

    unisRecvIGMPSQueryNum OBJECT-TYPE
        SYNTAX     Counter32
        MAX-ACCESS read-only
        STATUS     current
        DESCRIPTION
            "The statistics of IGMP specific query packets received on
             the device."
        ::= { unisIgmpSnoopingStatsObjects 2 }

    unisRecvIGMPV1ReportNum OBJECT-TYPE
        SYNTAX     Counter32
        MAX-ACCESS read-only
        STATUS     current
        DESCRIPTION
            "The statistics of IGMP V1 report packets received on
             the device."
        ::= { unisIgmpSnoopingStatsObjects 3 }

    unisRecvIGMPV2ReportNum OBJECT-TYPE
        SYNTAX     Counter32
        MAX-ACCESS read-only
        STATUS     current
        DESCRIPTION
            "The statistics of IGMP V2 report packets received on
             the device."
        ::= { unisIgmpSnoopingStatsObjects 4 }

    unisRecvIGMPLeaveNum OBJECT-TYPE
        SYNTAX     Counter32
        MAX-ACCESS read-only
        STATUS     current
        DESCRIPTION
            "The statistics of IGMP leave packets received on
             the device."
        ::= { unisIgmpSnoopingStatsObjects 5 }

    unisRecvErrorIGMPPacketNum OBJECT-TYPE
        SYNTAX     Counter32
        MAX-ACCESS read-only
        STATUS     current
        DESCRIPTION
            "The statistics of error IGMP packets received on
             the device."
        ::= { unisIgmpSnoopingStatsObjects 6 }

    unisSentIGMPSQueryNum OBJECT-TYPE
        SYNTAX     Counter32
        MAX-ACCESS read-only
        STATUS     current
        DESCRIPTION
            "The statistics of IGMP specific query packets sent from
             the device."
        ::= { unisIgmpSnoopingStatsObjects 7 }

    unisIgmpSnoopingClearStats  OBJECT-TYPE
        SYNTAX     INTEGER { clear(1),
                             counting(2)
                           }
        MAX-ACCESS read-write
        STATUS     current
        DESCRIPTION
            "The configuration to clear the statistics of IGMP packets."
        DEFVAL  { counting }
        ::= { unisIgmpSnoopingStatsObjects 8 }

        
END
