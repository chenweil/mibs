-- ==========================================================================
-- Copyright (c) 2020 Unisyue Technologies Co., Ltd.  All rights reserved.
--
-- Description: The purpose of this MIB file is to provide the object definition
--              of the SNMP (Simple Network Management Protocol) extended
--              information.
-- Reference:
-- Version: V1.7
-- History:
-- V1.0 2009-04-07  Initial version, created by Lisong
-- V1.1 2010-03-12  Added unisSnmpExtReadCommunitySingle and
--                  unisSnmpExtWriteCommunitySingle by SongHao
-- V1.2 2011-08-11  Added unisSnmpCommunityExTable by duyanbing
-- V1.3 2013-04-08  Changed MAX-ACCESS of unisSnmpCommunityExName by duyanbing
-- V1.4 2013-05-16  Added unisSnmpExtMaxContextNum and
--                  unisSnmpExtContextTable by gaoyanping
-- V1.5 2014-08-12  Added unisSnmpExtCommunityIPv6AclNum and unisSnmpExtVersion,
--                  modified description of unisSnmpExtCommunityAclNum by SongHao.
--      2015-01-20  Added unisSnmpExtTrapSource and unisSnmpExtInformSource by gaoyanping.
-- V1.6 2016-04-13  Added unisSnmpExtPrivProtocols by gaoyanping.
--      2016-08-08  Modify unisSnmpExtCommunityAclNum, unisSnmpExtCommunityIPv6AclNum
--                  of the range by zhangbaohong
-- V1.7 2019-04-16  Added unisSnmpExtAclNum, unisSnmpExtIPv6AclNum by zhangzichao.
-- ==========================================================================
UNIS-SNMP-EXT-MIB DEFINITIONS ::= BEGIN

IMPORTS
        TruthValue, RowStatus
    FROM SNMPv2-TC
        OBJECT-TYPE, MODULE-IDENTITY, Integer32, OBJECT-IDENTITY
    FROM SNMPv2-SMI
        SnmpAdminString, SnmpSecurityModel
    FROM SNMP-FRAMEWORK-MIB
        unisCommon
    FROM UNIS-OID-MIB;

unisSnmpExt MODULE-IDENTITY
    LAST-UPDATED "201904160000Z"
    ORGANIZATION
        "Unisyue Technologies Co., Ltd."
    CONTACT-INFO
        ""
    DESCRIPTION
        "This MIB file is to provide the object definition of the SNMP extended
         information."
    REVISION "201904160000Z"
    DESCRIPTION
        "Added unisSnmpExtAclNum, unisSnmpExtAclName, unisSnmpExtIPv6AclNum, unisSnmpExtIPv6AclName."
    REVISION "201608080000Z"
    DESCRIPTION
        "Modify unisSnmpExtCommunityAclNum, unisSnmpExtCommunityIPv6AclNum of the range"
    REVISION "201604130200Z"
    DESCRIPTION
        "Added unisSnmpExtPrivProtocols."
    REVISION "201501200900Z"
    DESCRIPTION
        "Added unisSnmpExtTrapSource and unisSnmpExtInformSource."
    REVISION "201408120303Z"
    DESCRIPTION
        "Added unisSnmpExtCommunityIPv6AclNum and unisSnmpExtVersion,
        modified description of unisSnmpExtCommunityAclNum."
    REVISION "201305160000Z"
    DESCRIPTION
        "Added unisSnmpExtMaxContextNum and unisSnmpExtContextTable."
    REVISION "201304080000Z"
    DESCRIPTION
        "Changed MAX-ACCESS of unisSnmpCommunityExName."
    REVISION "201108110000Z"
    DESCRIPTION
        "Added unisSnmpCommunityExTable."
    REVISION "201003120000Z"
    DESCRIPTION
        "Added unisSnmpExtReadCommunitySingle and unisSnmpExtWriteCommunitySingle."
    REVISION "200904071700Z"
    DESCRIPTION
        "The initial version of this MIB file."
    ::= { unisCommon 104 }
--
-- Object definitions
--
unisSnmpExtScalarObjects OBJECT IDENTIFIER ::= { unisSnmpExt 1 }

unisSnmpExtTables        OBJECT IDENTIFIER ::= { unisSnmpExt 2 }

unisSnmpExtNotifications OBJECT IDENTIFIER ::= { unisSnmpExt 3 }

unisSnmpExtPrivProtocols OBJECT IDENTIFIER ::= { unisSnmpExt 4 }

--
-- Scalar Objects
--
    unisSnmpExtSnmpChannel OBJECT-TYPE
        SYNTAX          Integer32(1..65535)
        MAX-ACCESS      read-write
        STATUS current
        DESCRIPTION
            "The channel number used by SNMP."
        DEFVAL { 161 }
        ::= { unisSnmpExtScalarObjects 1 }

    unisSnmpExtReadCommunitySingle OBJECT-TYPE
        SYNTAX          SnmpAdminString (SIZE(1..32))
        MAX-ACCESS      read-write
        STATUS          current
        DESCRIPTION     "The first read community."
        ::= { unisSnmpExtScalarObjects 2 }

    unisSnmpExtWriteCommunitySingle OBJECT-TYPE
        SYNTAX          SnmpAdminString (SIZE(1..32))
        MAX-ACCESS      read-write
        STATUS          current
        DESCRIPTION     "The first write community."
        ::= { unisSnmpExtScalarObjects 3 }

    unisSnmpExtMaxContextNum OBJECT-TYPE
        SYNTAX          Integer32(1..65535)
        MAX-ACCESS      read-only
        STATUS          current
        DESCRIPTION     "The maximum number of contexts."
        ::= { unisSnmpExtScalarObjects 4 }

    unisSnmpExtVersion OBJECT-TYPE
        SYNTAX          BITS {snmpV1(0), snmpV2c(1), snmpV3(2)}
        MAX-ACCESS      read-write
        STATUS          current
        DESCRIPTION     "The valid version of SNMP agent."
        ::= { unisSnmpExtScalarObjects 5 }

    unisSnmpExtTrapSource OBJECT-TYPE
        SYNTAX          SnmpAdminString (SIZE(0..255))
        MAX-ACCESS      read-only
        STATUS          current
        DESCRIPTION     "The specified interface, the SNMP agent used the
                        primary IP address of which as the source IP address
                        in all its traps."
        ::= { unisSnmpExtScalarObjects 6 }

    unisSnmpExtInformSource OBJECT-TYPE
        SYNTAX          SnmpAdminString (SIZE(0..255))
        MAX-ACCESS      read-only
        STATUS          current
        DESCRIPTION     "The specified interface, the SNMP agent used the
                        primary IP address of which as the source IP address
                        in all its informs."
        ::= { unisSnmpExtScalarObjects 7 }
    unisSnmpExtAclNum OBJECT-TYPE
        SYNTAX          Integer32 (0 | 2000..3999)
        MAX-ACCESS      read-write
        STATUS          current
        DESCRIPTION     "The number of global ACL.  It mutually exclusive with unisSnmpExtAclName."
        ::= { unisSnmpExtScalarObjects 8 }
    unisSnmpExtAclName OBJECT-TYPE
        SYNTAX          OCTET STRING(SIZE(0..63))
        MAX-ACCESS      read-write
        STATUS          current
        DESCRIPTION     "The name of global ACL.  It mutually exclusive with unisSnmpExtAclNum."
        ::= { unisSnmpExtScalarObjects 9 }
    unisSnmpExtIPv6AclNum OBJECT-TYPE
        SYNTAX          Integer32 (0 | 2000..3999)
        MAX-ACCESS      read-write
        STATUS          current
        DESCRIPTION     "The number of global IPv6 ACL.
                         It mutually exclusive with unisSnmpExtIPv6AclName."
        ::= { unisSnmpExtScalarObjects 10 }
    unisSnmpExtIPv6AclName OBJECT-TYPE
        SYNTAX          OCTET STRING(SIZE(0..63))
        MAX-ACCESS      read-write
        STATUS          current
        DESCRIPTION     "The name of global IPv6 ACL.  It mutually exclusive with unisSnmpExtIPv6AclNum."
        ::= { unisSnmpExtScalarObjects 11 }
--
-- Table Objects
--
    unisSnmpExtCommunityTable OBJECT-TYPE
        SYNTAX SEQUENCE OF UnisSnmpExtCommunityEntry
        MAX-ACCESS      not-accessible
        STATUS          current
        DESCRIPTION     "Modify the extended properties of SNMP community or
                         user."
        ::= { unisSnmpExtTables 1 }

    unisSnmpExtCommunityEntry OBJECT-TYPE
        SYNTAX          UnisSnmpExtCommunityEntry
        MAX-ACCESS      not-accessible
        STATUS          current
        DESCRIPTION     "The entry of unisSnmpExtCommunityTable."
        INDEX {
                unisSnmpExtCommunitySecurityLevel,
                unisSnmpExtCommunitySecurityName
              }
        ::= { unisSnmpExtCommunityTable 1 }

    UnisSnmpExtCommunityEntry ::= SEQUENCE {
        unisSnmpExtCommunitySecurityLevel   SnmpSecurityModel,
        unisSnmpExtCommunitySecurityName    SnmpAdminString,
        unisSnmpExtCommunityName            OCTET STRING,
        unisSnmpExtCommunityAclNum          Integer32,
        unisSnmpExtCommunityIPv6AclNum      Integer32
    }

    unisSnmpExtCommunitySecurityLevel OBJECT-TYPE
        SYNTAX          SnmpSecurityModel
        MAX-ACCESS      not-accessible
        STATUS          current
        DESCRIPTION     "The security model of the specified community or user.
                         This object may not take the 'any' (0) value."
        ::= { unisSnmpExtCommunityEntry 1 }

    unisSnmpExtCommunitySecurityName OBJECT-TYPE
        SYNTAX          SnmpAdminString (SIZE(1..32))
        MAX-ACCESS      not-accessible
        STATUS          current
        DESCRIPTION     "The security name of the specified community or user."
        ::= { unisSnmpExtCommunityEntry 2 }

    unisSnmpExtCommunityName OBJECT-TYPE
        SYNTAX          OCTET STRING(SIZE(1..32))
        MAX-ACCESS      read-only
        STATUS          current
        DESCRIPTION     "The name of the group to which the security name belongs."
        ::= { unisSnmpExtCommunityEntry 3 }

    unisSnmpExtCommunityAclNum OBJECT-TYPE
        SYNTAX          Integer32 (0 | 2000..3999)
        MAX-ACCESS      read-write
        STATUS          current
        DESCRIPTION     "The specified IPv4 ACL (Access Control List) number
                        used by the community or the user.
                        Basic ACL type: 2000..2999
                        Advanced ACL type: 3000..3999
                        "
        DEFVAL          { 0 }
        ::= { unisSnmpExtCommunityEntry 4 }

    unisSnmpExtCommunityIPv6AclNum OBJECT-TYPE
        SYNTAX          Integer32 (0 | 2000..3999)
        MAX-ACCESS      read-write
        STATUS          current
        DESCRIPTION     "The specified IPv6 Access Control List (ACL) number
                        used by the community or the user.
                        Basic ACL type: 2000..2999
                        Advanced ACL type: 3000..3999
                        "
        DEFVAL          { 0 }
        ::= { unisSnmpExtCommunityEntry 5 }

    unisSnmpCommunityExTable OBJECT-TYPE
        SYNTAX SEQUENCE OF UnisSnmpCommunityExEntry
        MAX-ACCESS      not-accessible
        STATUS          current
        DESCRIPTION     "Modify the extended properties of SNMP community."
        ::= { unisSnmpExtTables 2 }

    unisSnmpCommunityExEntry OBJECT-TYPE
        SYNTAX          UnisSnmpCommunityExEntry
        MAX-ACCESS      not-accessible
        STATUS          current
        DESCRIPTION     "The entry of unisSnmpCommunityExTable."
        INDEX {
                 unisSnmpCommunityExName
              }
        ::= { unisSnmpCommunityExTable 1 }

    UnisSnmpCommunityExEntry ::= SEQUENCE {
        unisSnmpCommunityExName
            OCTET STRING,
        unisSnmpCommunityExWrite
            TruthValue,
        unisSnmpCommunityExViewName
            OCTET STRING,
        unisSnmpCommunityExAclNum
            Integer32,
        unisSnmpCommunityExRowStatus
            RowStatus
    }

    unisSnmpCommunityExName OBJECT-TYPE
        SYNTAX          OCTET STRING(SIZE(1..32))
        MAX-ACCESS      read-only
        STATUS          current
        DESCRIPTION     "The specified community name."
        ::= { unisSnmpCommunityExEntry 1 }

    unisSnmpCommunityExWrite OBJECT-TYPE
        SYNTAX          TruthValue
        MAX-ACCESS      read-create
        STATUS          current
        DESCRIPTION
        "Represents the community can write or not.
        'true' : the community can write.
        'false': the community can read only."
        DEFVAL      { false }
        ::= { unisSnmpCommunityExEntry 2 }

    unisSnmpCommunityExViewName OBJECT-TYPE
        SYNTAX          OCTET STRING(SIZE(1..32))
        MAX-ACCESS      read-create
        STATUS          current
        DESCRIPTION     "A family of view subtrees that the Community can operate."
        ::= { unisSnmpCommunityExEntry 3 }

    unisSnmpCommunityExAclNum OBJECT-TYPE
        SYNTAX          Integer32 (0|2000..2999)
        MAX-ACCESS      read-create
        STATUS          current
        DESCRIPTION     "The specified ACL (Access Control List) number used by the community."
        DEFVAL          {0}
        ::= { unisSnmpCommunityExEntry 4 }

    unisSnmpCommunityExRowStatus OBJECT-TYPE
        SYNTAX          RowStatus
        MAX-ACCESS      read-create
        STATUS          current
        DESCRIPTION     "The status of this table entry."
        ::= { unisSnmpCommunityExEntry 5 }

    unisSnmpExtContextTable OBJECT-TYPE
        SYNTAX SEQUENCE OF UnisSnmpExtContextEntry
        MAX-ACCESS      not-accessible
        STATUS          current
        DESCRIPTION     "Modify the extended properties of SNMP context."
        ::= { unisSnmpExtTables 3 }

    unisSnmpExtContextEntry OBJECT-TYPE
        SYNTAX          UnisSnmpExtContextEntry
        MAX-ACCESS      not-accessible
        STATUS          current
        DESCRIPTION     "The entry of unisSnmpExtContextTable."
        INDEX {
                unisSnmpExtContextName
              }
        ::= { unisSnmpExtContextTable 1 }

    UnisSnmpExtContextEntry ::= SEQUENCE {
        unisSnmpExtContextName
            SnmpAdminString,
        unisSnmpExtContextRowStatus
            RowStatus
     }

    unisSnmpExtContextName OBJECT-TYPE
        SYNTAX          SnmpAdminString (SIZE(1..32))
        MAX-ACCESS      not-accessible
        STATUS          current
        DESCRIPTION     "The specified context name."
        ::= { unisSnmpExtContextEntry 1 }

    unisSnmpExtContextRowStatus OBJECT-TYPE
        SYNTAX          RowStatus
        MAX-ACCESS      read-create
        STATUS          current
        DESCRIPTION     "The status of this table entry."
        ::= { unisSnmpExtContextEntry 2 }

--
-- Notification Objects
--

--
-- PrivProtocols
--
    unisSnmpExtAESCfb192PrivProtocol OBJECT-IDENTITY
    STATUS        current
    DESCRIPTION  "The CFB192-AES-192 privacy protocol."
    REFERENCE    "- Specification for the ADVANCED ENCRYPTION
                    STANDARD .

                  - Use 192 bit key size AES.
                 "
    ::= { unisSnmpExtPrivProtocols 1 }

    unisSnmpExtAESCfb256PrivProtocol OBJECT-IDENTITY
    STATUS        current
    DESCRIPTION  "The CFB256-AES-256 privacy protocol."
    REFERENCE    "- Specification for the ADVANCED ENCRYPTION
                    STANDARD.

                  - Use 256 bit key size AES.
                 "
    ::= { unisSnmpExtPrivProtocols 2 }

END
