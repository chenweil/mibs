-- ============================================================================
-- Copyright (c) 2020 Unisyue Technologies Co., Ltd.  All rights reserved.
--
-- Description: This MIB is used for configuration of SECP (security policies).
-- Reference:
-- Version: V1.0
-- History:
-- V1.0 created by xuedeng.
-- ============================================================================
UNIS-SECP-MIB DEFINITIONS ::= BEGIN

IMPORTS
    unisCommon
        FROM  UNIS-OID-MIB
    OBJECT-TYPE, MODULE-IDENTITY,
    Unsigned32, Counter64
        FROM SNMPv2-SMI;

--
-- Node definitions
--

unisSecp MODULE-IDENTITY
    LAST-UPDATED "201612191605Z"        -- Dec 19, 2016 at 16:05 GMT
    ORGANIZATION
        "Unisyue Technologies Co., Ltd."
    CONTACT-INFO
        ""
    DESCRIPTION
        "Security policies management information base for managing devices
        that support security policies.
        "
    REVISION "201612191605Z"            -- Dec 19, 2016 at 16:05 GMT
    DESCRIPTION
        "The initial revision of this MIB module."
    ::= { unisCommon 166 }

--
-- Nodes of unisSecpObjects
--
unisSecpObjects OBJECT IDENTIFIER ::= { unisSecp 1 }

--
-- Nodes of unisSecpRunningInfoTable
--
unisSecpRunningInfoTable OBJECT-TYPE
    SYNTAX SEQUENCE OF UnisSecpRunningInfoEntry
    MAX-ACCESS not-accessible
    STATUS current
    DESCRIPTION
        "Security policies running information base."
    ::= { unisSecpObjects 1 }

unisSecpRunningInfoEntry OBJECT-TYPE
    SYNTAX UnisSecpRunningInfoEntry
    MAX-ACCESS not-accessible
    STATUS current
    DESCRIPTION
        "Security policies running information entry."
    INDEX
    {
        unisSecpIPVersion,
        unisSecpRuleID
    }
    ::= { unisSecpRunningInfoTable 1 }

UnisSecpRunningInfoEntry ::=
    SEQUENCE
    {
        unisSecpIPVersion
            INTEGER,
        unisSecpRuleID
            Unsigned32,
        unisSecpMatchPacketCount
            Counter64,
        unisSecpLastMatchTime
            Unsigned32
    }

unisSecpIPVersion OBJECT-TYPE
    SYNTAX INTEGER
    {
        ipv4(1),
        ipv6(2)
    }
    MAX-ACCESS not-accessible
    STATUS current
    DESCRIPTION
        "IP protocol version."
    ::= { unisSecpRunningInfoEntry 1 }

unisSecpRuleID OBJECT-TYPE
    SYNTAX Unsigned32 (0..65534)
    MAX-ACCESS not-accessible
    STATUS current
    DESCRIPTION
        "Rule ID of security policies."
    ::= { unisSecpRunningInfoEntry 2 }

unisSecpMatchPacketCount OBJECT-TYPE
    SYNTAX Counter64
    MAX-ACCESS read-only
    STATUS current
    DESCRIPTION
        "Number of packets matching the rule."
    ::= { unisSecpRunningInfoEntry 3 }

unisSecpLastMatchTime OBJECT-TYPE
    SYNTAX Unsigned32
    MAX-ACCESS read-only
    STATUS current
    DESCRIPTION
        "Interval in seconds between the last match and 1970/1/1 00:00:00."
    ::= { unisSecpRunningInfoEntry 4 }

END
