-- ==========================================================================
-- Copyright (c) 2020 Unisyue Technologies Co., Ltd.  All rights reserved.
--
-- Description: The purpose of this MIB file is to provide the define of
--              POS MIB of serial router.
-- Reference:
-- Version: V1.1
-- History:
-- V1.0  The initial version, created by wangshijin 2004-07-02
-- V1.1  Refined this MIB which is completely conform with SMIv2.
--       Make the following changes:
--       1. Add MODULE-IDENTITY 
--       2. Remove default value for unisposAppHostIP, unisposAppSourceIp, unisposAppRecvPacCounter 
--       	unisposAppErrPacCouter, unisposAppDistrErrCounter, unisposAppBuffedCounter,
--       	unisposAppDiscardedCounter, unisposPosRecvPacCounter, unisposPosErrPacCounter,
--       	unisposPosMapErrCounter, unisposPosBuffedCounter, unisposPosDiscardedCounter                                                                                   
--       	unisposFCMConnectFailCounter and unisposFCMTimeoutCounter because their syntax is Counter32                                 
--       3. Modify unisposPosIfIndex, unisposAsyAppIfIndex, unisposFCMIfIndex, unisposPadIfIndex of INTEGER range
--       4. Modify unisposPosId of INTEGER range 
--       5. Add a new column object unisposPosInterType under unisposInterTable table	by caizibin  2004-10-11
--       6. Add an enumeration called pad(3) under the unisposAppConnectMode  by caizibin  2004-10-11
--       7. Add a new column object unisposAppX121Addr under unisposAppTable table	by caizibin  2004-10-11
--	 	 8. Add new object unisposPadWaitTime, unisposPadIdleTimeout, unisposPadPacType, unisposPadEnable, 
--	    unisposPadCheckSChar by caizibin  2004-10-11
--       9.Refine some object's descrption to make them more readable 
--	     10.Add unisposPadTable table 
-- ==========================================================================
UNIS-POS-MIB    DEFINITIONS ::= BEGIN

IMPORTS
	RowStatus  
        FROM SNMPv2-TC  
    OBJECT-TYPE, NOTIFICATION-TYPE, MODULE-IDENTITY, IpAddress, Counter32
        FROM SNMPv2-SMI
    unismlsr
		FROM UNIS-OID-MIB;

unispos     MODULE-IDENTITY 
        LAST-UPDATED "200410150000Z"
        ORGANIZATION
            "Unisyue Technologies Co., Ltd."
        CONTACT-INFO
            ""
        DESCRIPTION 
                "The POS MIB module is used to manage 
                 POS-Access. " 
        REVISION	"200410120000Z"
        DESCRIPTION 
                "The lastest version of this MIB module."  
        REVISION	"200407020000Z"
        DESCRIPTION 
                "The initial version of this MIB module."         

		::= { unismlsr 8 }   


unisposAppTable   OBJECT-TYPE
   SYNTAX    	SEQUENCE OF UnisPOSAppEntry
   MAX-ACCESS   not-accessible
   STATUS    	current
   DESCRIPTION
             "The table to get and set the application informatin."
   ::= { unispos 1 }

unisposAppEntry   OBJECT-TYPE
   SYNTAX    	UnisPOSAppEntry
   MAX-ACCESS   not-accessible
   STATUS    	current
   DESCRIPTION
             "The content of unisposAppTable."
   INDEX     { unisposAppId }
   ::= { unisposAppTable 1 }


UnisPOSAppEntry ::= SEQUENCE {
   unisposAppId
        INTEGER,
   unisposAppConnectMode
        INTEGER,
   unisposAppState
        INTEGER,     
   unisposAppIfIndex
        INTEGER,     
   unisposAppHostIP
        IpAddress,
   unisposAppPort
        INTEGER,
   unisposAppSourceIp
        IpAddress,  
   unisposAppRecvPacCounter     
        Counter32,
   unisposAppErrPacCounter
        Counter32,
   unisposAppDistrErrCounter
        Counter32,
   unisposAppBuffedCounter
        Counter32,
   unisposAppDiscardedCounter
        Counter32,
   unisposAppDebug
        INTEGER,
   unisposAppRowStatus
        RowStatus,     		
   unisposAppX121Addr
   	OCTET STRING
   }

unisposAppId   OBJECT-TYPE
   SYNTAX    	INTEGER(0..31)
   MAX-ACCESS   read-only
   STATUS    	current
   DESCRIPTION
             "The ID of application."
   ::= { unisposAppEntry 1 }

unisposAppConnectMode   OBJECT-TYPE
   SYNTAX    	INTEGER{
                        tcp(1),
                        flow(2),
                        pad(3)                        
                }
   MAX-ACCESS   read-create
   STATUS    	current
   DESCRIPTION
             "The connect mode of application.
             
             If the router and unix are connected by TCP protocol,
             the connect mode of application is tcp.
             
             If the router and unix are connected by async interface, 
             the connect mode of application is flow.
             
             If the router is used as POSPAD device, the connect mode of application 
             is pad."
   ::= { unisposAppEntry 2 }

unisposAppState   OBJECT-TYPE
   SYNTAX    	INTEGER{
                	noset(1),
                	down(2),
                	up(3),
                	ok(4),
                	kept(5),
                	linking(6),
                	linked(7) 
             	}
   MAX-ACCESS   read-only
   STATUS    	current
   DESCRIPTION
             "The state of application."
   DEFVAL  {1}          
   ::= { unisposAppEntry 3 }

unisposAppIfIndex   OBJECT-TYPE             
   SYNTAX    	INTEGER(0..2147483647)
   MAX-ACCESS   read-create
   STATUS    	current
   DESCRIPTION
             "The interface index of the application 
             whose connect mode is flow or pad."  
   REFERENCE  "ifIndex"          
   ::= { unisposAppEntry 4 }

unisposAppHostIP   OBJECT-TYPE
   SYNTAX    	IpAddress
   MAX-ACCESS   read-create
   STATUS    	current
   DESCRIPTION
             "The destination IP Address of application.
             Used for the application whose connect mode is tcp."
   ::= { unisposAppEntry 5 }

unisposAppPort   OBJECT-TYPE
   SYNTAX    	INTEGER(0..65535)
   MAX-ACCESS   read-create
   STATUS    	current
   DESCRIPTION
             "The destination port of application.
             Used for the application whose connect mode is tcp."
   ::= { unisposAppEntry 6 }

unisposAppSourceIp   OBJECT-TYPE
   SYNTAX    	IpAddress
   MAX-ACCESS   read-create
   STATUS    	current
   DESCRIPTION
             "The source IP Address of application.
             Used for the application whose connect mode is tcp."
   ::= { unisposAppEntry 7 }

unisposAppRecvPacCounter   OBJECT-TYPE
   SYNTAX    	Counter32
   MAX-ACCESS   read-only
   STATUS    	current
   DESCRIPTION
             "The number of packets received by the application."
   DEFVAL  {0}          
   ::= { unisposAppEntry 8 }

unisposAppErrPacCounter   OBJECT-TYPE
   SYNTAX    	Counter32
   MAX-ACCESS   read-only
   STATUS    	current
   DESCRIPTION
             "The number of error packets received by the application."
   DEFVAL  {0}          
   ::= { unisposAppEntry 9 }

unisposAppDistrErrCounter   OBJECT-TYPE
   SYNTAX    	Counter32
   MAX-ACCESS   read-only
   STATUS    	current
   DESCRIPTION
             "The number of packets that could not be sent to POS."
   DEFVAL  {0}          
   ::= { unisposAppEntry 10 }

unisposAppBuffedCounter   OBJECT-TYPE
   SYNTAX    	Counter32
   MAX-ACCESS   read-only
   STATUS    	current
   DESCRIPTION
             "The number of packets stored in the buffer of application."
   DEFVAL  {0}          
   ::= { unisposAppEntry 11 }

unisposAppDiscardedCounter   OBJECT-TYPE
   SYNTAX    	Counter32
   MAX-ACCESS   read-only
   STATUS    	current
   DESCRIPTION
             "The number of packets discarded by the application."
   DEFVAL  {0}          
   ::= { unisposAppEntry 12 }

unisposAppDebug   OBJECT-TYPE
   SYNTAX    	INTEGER{
                        close(1),
                        open(2)
                }
   MAX-ACCESS   read-create
   STATUS    	current
   DESCRIPTION
             "The debugging switch of application."
   ::= { unisposAppEntry 13 }

unisposAppRowStatus   OBJECT-TYPE
   SYNTAX    	RowStatus
   MAX-ACCESS   read-create
   STATUS    	current
   DESCRIPTION
             "The status of row. Only support active, CreateAndGo and destroy."
   ::= { unisposAppEntry 14 } 
   
unisposAppX121Addr OBJECT-TYPE
   SYNTAX    	OCTET STRING (SIZE(1..15))
   MAX-ACCESS   read-create
   STATUS    	current
   DESCRIPTION             
             "The destination X121 Address of application which is
             an octet string made up of numeric.
             Used for the application whose connect mode is pad."
   ::= { unisposAppEntry 15 }  

unisposInterTable   OBJECT-TYPE
   SYNTAX    	SEQUENCE OF UnisPOSInterEntry
   MAX-ACCESS   not-accessible
   STATUS    	current
   DESCRIPTION
             "The table to get and set the POS-Interface informatin."
   ::= { unispos 2 }

unisposInterEntry   OBJECT-TYPE
   SYNTAX    	UnisPOSInterEntry
   MAX-ACCESS   not-accessible
   STATUS    	current
   DESCRIPTION
             "The content of unisposInterTable."
   INDEX     { unisposPosId }
   ::= { unisposInterTable 1 }


UnisPOSInterEntry ::= SEQUENCE {
   unisposPosId
        INTEGER,
   unisposPosIfIndex
        INTEGER,
   unisposPosConnectState
        INTEGER,     
   unisposPosRecvPacCounter
        Counter32,     
   unisposPosErrPacCounter
        Counter32,
   unisposPosMapErrCounter
        Counter32,
   unisposPosBuffedCounter
        Counter32,  
   unisposPosDiscardedCounter     
        Counter32,
   unisposPosInterDebug
        INTEGER,
   unisposPosInterRowStatus
        RowStatus,
   unisposPosInterType
   	INTEGER  
   }

unisposPosId   OBJECT-TYPE
   SYNTAX    	INTEGER(0..255)
   MAX-ACCESS   read-only
   STATUS    	current
   DESCRIPTION
             "The ID of the POS-Interface."
   ::= { unisposInterEntry 1 }

unisposPosIfIndex   OBJECT-TYPE
   SYNTAX    	INTEGER(1..2147483647)
   MAX-ACCESS   read-create
   STATUS    	current
   DESCRIPTION
             "The interface index of the POS-Interface whose type is fcm, asy or pad-client."  
   REFERENCE  "ifIndex"
   ::= { unisposInterEntry 2 }

unisposPosConnectState   OBJECT-TYPE
   SYNTAX    	INTEGER{
                        noset(1),
                        down(2),
                        up(3),
                        ok(4)
                }
   MAX-ACCESS   read-only
   STATUS    	current
   DESCRIPTION
             "The state of the POS-Interface."
   DEFVAL  {1}          
   ::= { unisposInterEntry 3 }

unisposPosRecvPacCounter   OBJECT-TYPE
   SYNTAX    	Counter32
   MAX-ACCESS   read-only
   STATUS    	current
   DESCRIPTION
             "The number of packets received by the POS-Interface."
   DEFVAL  {0}          
   ::= { unisposInterEntry 4 }

unisposPosErrPacCounter   OBJECT-TYPE
   SYNTAX    	Counter32
   MAX-ACCESS   read-only
   STATUS    	current
   DESCRIPTION
             "The number of error packets received by the POS-Interface."
   DEFVAL  {0}          
   ::= { unisposInterEntry 5 }

unisposPosMapErrCounter   OBJECT-TYPE
   SYNTAX    	Counter32
   MAX-ACCESS   read-only
   STATUS    	current
   DESCRIPTION
             "The number of packets that could not be sent to application."
   DEFVAL  {0}          
   ::= { unisposInterEntry 6 }

unisposPosBuffedCounter   OBJECT-TYPE
   SYNTAX    	Counter32
   MAX-ACCESS   read-only
   STATUS    	current
   DESCRIPTION
             "The number of packets stored in the buffer of the POS-Interface."
   DEFVAL  {0}          
   ::= { unisposInterEntry 7 }

unisposPosDiscardedCounter   OBJECT-TYPE
   SYNTAX    	Counter32
   MAX-ACCESS   read-only
   STATUS    	current
   DESCRIPTION
             "The number of packets discarded by the POS-Interface."
   DEFVAL  {0}          
   ::= { unisposInterEntry 8 }

unisposPosInterDebug   OBJECT-TYPE
   SYNTAX    	INTEGER{
                        close(1),
                        open(2)
                }
   MAX-ACCESS   read-create
   STATUS    	current
   DESCRIPTION
             "The debugging switch of the POS-Interface."
   ::= { unisposInterEntry 9 }   

unisposPosInterRowStatus   OBJECT-TYPE
   SYNTAX    	RowStatus
   MAX-ACCESS   read-create
   STATUS    	current
   DESCRIPTION
             "The status of row. Only support active, CreateAndGo and destroy."
   ::= { unisposInterEntry 10 }   

unisposPosInterType   OBJECT-TYPE
   SYNTAX    	INTEGER{
                        fcm(1),
                        asy(2),
                        pad-client(3),
                        pad-server(4)
                }
   MAX-ACCESS   read-create
   STATUS    	current
   DESCRIPTION
             "The type of interface.
             
             The POS-Access mode has four types: FCM-Access, ASYNC-Access, 
             simulating POSPAD device, POSPAD-Access. 
             
             FCM-Access mode means POS and router are connected through PSTN.
             In this case, unisposPosInterType should be set to fcm.
             
             ASYNC-Access mode means POS and router are connected by asynchronous cable.
             In this case, unisposPosInterType should be set to asy.
             
             Simulating POSPAD device means router connects POS through asynchronous cable
             and connects another router whose connect mode is pad-server through X.25 network. 
             In this case, unisposPosInterType should be set to pad-client.  
              
             POSPAD-Access mode means router connects POSPAD device through X.25 network.
             In this case, unisposPosInterType is pad-server. The unisposPosInterType
             can't be set to pad-server. It is autogenerated when POSPAD device initiates
             a connection to the router.  
             "
   DEFVAL  {1}
   ::= { unisposInterEntry 11 }
   
unisposMapTable   OBJECT-TYPE            
   SYNTAX    	SEQUENCE OF UnisPOSMapEntry
   MAX-ACCESS   not-accessible
   STATUS    	current
   DESCRIPTION
		"The table to get and set the informatin of mapping relation of destination and application."
   ::= { unispos 3 }

unisposMapEntry   OBJECT-TYPE
   SYNTAX    	UnisPOSMapEntry
   MAX-ACCESS   not-accessible
   STATUS    	current
   DESCRIPTION
             "The content of unisposMapTable."
   INDEX     { unisposMapDes }
   ::= { unisposMapTable 1 }


UnisPOSMapEntry ::= SEQUENCE {
   unisposMapDes
        INTEGER,
   unisposMapAppNumber
        INTEGER,
   unisposMapRowStatus
        RowStatus
   }

unisposMapDes   OBJECT-TYPE
   SYNTAX    	INTEGER(-1..65535)
   MAX-ACCESS   read-create
   STATUS    	current
   DESCRIPTION
             "The destination code of the mapping item.
             If the value is -1, it is the default item of mapping relation."
   ::= { unisposMapEntry 1 }

unisposMapAppNumber   OBJECT-TYPE
   SYNTAX    	INTEGER(0..31)
   MAX-ACCESS   read-create
   STATUS    	current
   DESCRIPTION
             "The application index of the mapping item."

   ::= { unisposMapEntry 2 }

unisposMapRowStatus   OBJECT-TYPE
   SYNTAX    	RowStatus
   MAX-ACCESS   read-create
   STATUS    	current
   DESCRIPTION
             "The status of row. Only support active, CreateAndGo and destroy."
   ::= { unisposMapEntry 3 } 
   
unisposAsyAppTable   OBJECT-TYPE
   SYNTAX    	SEQUENCE OF UnisPOSAsyAppEntry
   MAX-ACCESS   not-accessible
   STATUS    	current
   DESCRIPTION
             "The table to get and set the asynchronous-application interface information."
   ::= { unispos 4 }

unisposAsyAppEntry   OBJECT-TYPE
   SYNTAX    	UnisPOSAsyAppEntry
   MAX-ACCESS   not-accessible
   STATUS    	current
   DESCRIPTION
             "The content of unisposAsyAppTable."
   INDEX     { unisposAsyAppIfIndex }
   ::= { unisposAsyAppTable 1 }

UnisPOSAsyAppEntry ::= SEQUENCE {
   unisposAsyAppIfIndex
        INTEGER,
   unisposAsyAppRowStatus
        RowStatus
   }

unisposAsyAppIfIndex   OBJECT-TYPE
   SYNTAX    	INTEGER(0..2147483647)
   MAX-ACCESS   read-only
   STATUS    	current
   DESCRIPTION
             "The interface index of asynchronous-application."
   REFERENCE  "ifIndex"
   ::= { unisposAsyAppEntry 1 }

unisposAsyAppRowStatus   OBJECT-TYPE
   SYNTAX    	RowStatus
   MAX-ACCESS   read-create
   STATUS    	current
   DESCRIPTION
             "The status of row. Only support active, CreateAndGo and destroy."
   ::= { unisposAsyAppEntry 2 }
      
   

unisposFCMTable   OBJECT-TYPE
   SYNTAX    	SEQUENCE OF UnisPOSFCMEntry
   MAX-ACCESS   not-accessible
   STATUS    	current
   DESCRIPTION
             "The table to get the information of FCM interface."
   ::= { unispos 5 }

unisposFCMEntry   OBJECT-TYPE
   SYNTAX    	UnisPOSFCMEntry
   MAX-ACCESS   not-accessible
   STATUS    	current
   DESCRIPTION
             "The content of unisposFCMTable."
   INDEX     { unisposFCMIfIndex }
   ::= { unisposFCMTable 1 }


UnisPOSFCMEntry ::= SEQUENCE {
   unisposFCMIfIndex
        INTEGER,
   unisposFCMTimeoutCounter
        Counter32,
   unisposFCMConnectFailCounter
        Counter32
   }

unisposFCMIfIndex   OBJECT-TYPE
   SYNTAX    	INTEGER(0..2147483647)
   MAX-ACCESS   read-only
   STATUS    	current
   DESCRIPTION
             "The index of FCM interface." 
   REFERENCE  "ifIndex"
   ::= { unisposFCMEntry 1 }

unisposFCMTimeoutCounter   OBJECT-TYPE
   SYNTAX    	Counter32
   MAX-ACCESS   read-only
   STATUS    	current
   DESCRIPTION
             "The number that modem was hung up for timeout."
   DEFVAL  {0}          
   ::= { unisposFCMEntry 3 }

unisposFCMConnectFailCounter   OBJECT-TYPE
   SYNTAX    	Counter32
   MAX-ACCESS   read-only
   STATUS    	current
   DESCRIPTION
             "The number that modem could not handshake successfully."
   DEFVAL  {0}          
   ::= { unisposFCMEntry 4 }
   
   

unisposAppSum   OBJECT-TYPE
   SYNTAX    	INTEGER(0..32)
   MAX-ACCESS   read-only
   STATUS    	current   
   DESCRIPTION
             "The total of configued applications."
   DEFVAL  {0}          
   ::= { unispos 6 }



unisposInterSum   OBJECT-TYPE
   SYNTAX    	INTEGER(0..256)
   MAX-ACCESS   read-only
   STATUS    	current   
   DESCRIPTION
             "The total of configued POS-Interfaces."
   DEFVAL  {0}          
   ::= { unispos 7 }



unisposEnable   OBJECT-TYPE
   SYNTAX    	INTEGER{
                        disable(1),
                        enable(2)
                }
   MAX-ACCESS   read-write
   STATUS    	current   
   DESCRIPTION
             "To enable or diable pos-server."
   DEFVAL  {1}          
   ::= { unispos 8 }



unisposAppDebugAll   OBJECT-TYPE
   SYNTAX    	INTEGER{
                        close(1),
                        open(2)
                }
   MAX-ACCESS   read-write
   STATUS    	current   
   DESCRIPTION
             "To open or close the debugging switch of all applications."
   DEFVAL  {1}          
   ::= { unispos 9 }



unisposPosDebugAll   OBJECT-TYPE
   SYNTAX    	INTEGER{
                        close(1),
                        open(2)
                }
   MAX-ACCESS   read-write
   STATUS    	current   
   DESCRIPTION
             "To open or close the debugging switch of all POS-Interfaces."
   DEFVAL  {1}          
   ::= { unispos 10 }



unisposClearPacCounter   OBJECT-TYPE
   SYNTAX    	INTEGER{
                        clear(1),
                        counting(2)
                }
   MAX-ACCESS   read-write
   STATUS    	current   
   DESCRIPTION
             "To reset all packet counters of all applicaions and POS-Interfaces."
   DEFVAL  {2}          
   ::= { unispos 11 } 
   
unisposClearFCMCounter   OBJECT-TYPE
   SYNTAX    	INTEGER{
                        clear(1),
                        counting(2)
                }
   MAX-ACCESS   read-write
   STATUS    	current   
   DESCRIPTION
             "To clear all counters of all FCM interfaces."
   DEFVAL  {2}          
   ::= { unispos 12 }



unisposEnableTrap   OBJECT-TYPE
   SYNTAX    	INTEGER{
                        disable(1),
                        enable(2)
                }
   MAX-ACCESS   read-write
   STATUS    	current   
   DESCRIPTION
             "To enable or disable trap switch."
   DEFVAL  {1}          
   ::= { unispos 13 }

unisposFCMAnswerTime   OBJECT-TYPE
   SYNTAX    	INTEGER(500..2000)
   MAX-ACCESS   read-write
   STATUS    	current   
   DESCRIPTION
             "FCM answer time, unit:ms."
   DEFVAL  {500}      
      ::= { unispos 14 } 
      
unisposFCMTradeTime   OBJECT-TYPE
   SYNTAX    	INTEGER(30000..1200000)
   MAX-ACCESS   read-write
   STATUS    	current   
   DESCRIPTION
             "FCM trade time, unit:ms."
   DEFVAL  {60000}          
   ::= { unispos 15 }

unisposFCMPacketInterval   OBJECT-TYPE
   SYNTAX    	INTEGER(3500..10000)
   MAX-ACCESS   read-write
   STATUS    	current   
   DESCRIPTION
             "FCM packet interval time, unit:ms."
   DEFVAL  {5000}          
   ::= { unispos 16 }

unisposPadWaitTime  OBJECT-TYPE 	
   SYNTAX        INTEGER (100..10000)
   MAX-ACCESS    read-write
   STATUS        current
   DESCRIPTION
	    "The time that POS-Interface needs to wait to receive another packet, unit:ms.
	    It may be configured when router is used as POSPAD device. In other cases,
	    It is useless."
   ::= { unispos 18 }

unisposPadIdleTimeout OBJECT-TYPE 	
   SYNTAX          INTEGER (0..600)
   MAX-ACCESS      read-write
   STATUS          current
   DESCRIPTION
		"If these is no packet transmitting through the time, 
		the connection of POSPAD device and router whose connect mode 
		is pad-server will be cut off. Unit:s."
   ::= { unispos 19 }

unisposPadPacType	 OBJECT-TYPE	
    SYNTAX        INTEGER { 
    				       syn(1),
    				       asy(2)
                         }
    MAX-ACCESS    read-write
    STATUS        current
    DESCRIPTION
	  	"The type of packet.Between POSPAD device and router whose connect mode 
		is pad-server, there are two types of packet. One is synchronous, 
		the other is asynchronous."
    DEFVAL  {1}
    ::= { unispos 20 }

unisposPadCheckSChar  OBJECT-TYPE
   SYNTAX    	INTEGER {
                    disable(1),
                    enable(2)                   
		        }
   MAX-ACCESS   read-write
   STATUS    	current   
   DESCRIPTION
             "To enable or disable the checking of 10 04 characters in packet.
             It is used for the router which is used as POSPAD device.
             
             When the value is disable, it will check packet that just includes 10 04 charaters.
             If there are 10 04 packet, the router which is used as POSPAD device
             will disconnect from POSPAD-access router.
             
             When the value is enable, it will check 10 04 characters in packet. 
             If there are 10 04 characters in packet, the router which is used as POSPAD 
             device will disconnect from POSPAD-access router."
   DEFVAL  {2}          
   ::= { unispos 21 }

unisposPadTable   OBJECT-TYPE            
   SYNTAX    	SEQUENCE OF UnisPOSPadEntry
   MAX-ACCESS   not-accessible
   STATUS    	current
   DESCRIPTION
		"The table to enable or disable POSPAD-Access function under serial interface."
   ::= { unispos 22 }

unisposPadEntry   OBJECT-TYPE
   SYNTAX    	UnisPOSPadEntry
   MAX-ACCESS   not-accessible
   STATUS    	current
   DESCRIPTION
             "The content of unisposPadTable."
   INDEX     { unisposPadIfIndex }
   ::= { unisposPadTable 1 }


UnisPOSPadEntry ::= SEQUENCE {
   unisposPadIfIndex
        INTEGER,
   unisposPadRowStatus
        RowStatus
   }

unisposPadIfIndex   OBJECT-TYPE
   SYNTAX    	INTEGER(1..2147483647)
   MAX-ACCESS   not-accessible
   STATUS    	current
   DESCRIPTION
             "The index of serial interface."  
   REFERENCE  "ifIndex"
   ::= { unisposPadEntry 1 }

unisposPadRowStatus   OBJECT-TYPE
   SYNTAX    	RowStatus
   MAX-ACCESS   read-create
   STATUS    	current
   DESCRIPTION
             "The status of row. Only support active, CreateAndGo and destroy."
   ::= { unisposPadEntry 2 }  

unisposTrap        OBJECT IDENTIFIER ::= { unispos 17 }

unisposAppNotReadyTrap NOTIFICATION-TYPE
   OBJECTS 	{ unisposAppId }
   STATUS  	current
   DESCRIPTION
             "The agent will send a trap when the application whose state is linked
             isn't ready to send or receive data.
             Only used for the application whose connect mode is tcp."
   ::= { unisposTrap 1 }



unisposAppConnectFailTrap NOTIFICATION-TYPE
   OBJECTS 	{ unisposAppId }
   STATUS  	current
   DESCRIPTION
             "The agent will send a trap if router can not connect to the application."
   ::= { unisposTrap 2 }
   


unisposAppStateChangeTrap NOTIFICATION-TYPE
   OBJECTS 	{ unisposAppId, unisposAppState }
   STATUS  	current
   DESCRIPTION
             "The agent will send a trap when the state of the application is changed to down or kept."
   ::= { unisposTrap 3 }
   


unisposAppNotConfigedTrap NOTIFICATION-TYPE
   OBJECTS 	{ unisposAppId }
   STATUS  	current
   DESCRIPTION
             "The agent will send a trap if the application isn't configured."
   ::= { unisposTrap 4 }
   


unisposAppBuffOverFlowTrap NOTIFICATION-TYPE
   OBJECTS 	{ unisposAppId }
   STATUS  	current
   DESCRIPTION
             "The agent will send a trap if the application buffer is overflowed."
   ::= { unisposTrap 5 }
   


unisposAppDebugOpenTrap NOTIFICATION-TYPE
   OBJECTS 	{ unisposAppId }
   STATUS  	current
   DESCRIPTION
             "The agent will send a trap if the debugging switch of application is open."
   ::= { unisposTrap 6 }
   


unisposAppDebugAllOpenTrap NOTIFICATION-TYPE
   STATUS  	current
   DESCRIPTION
             "The agent will send a trap if the all debugging switches of application are open."
   ::= { unisposTrap 7 }



unisposInterBuffOverFlowTrap NOTIFICATION-TYPE
   STATUS  	current
   DESCRIPTION
             "The agent will send a trap if the distributing buffer is overflowed."
   ::= { unisposTrap 8 }
   


unisposInterStateChangeTrap NOTIFICATION-TYPE
   OBJECTS 	{ unisposPosId, unisposPosConnectState }
   STATUS  	current
   DESCRIPTION
             "The agent will send a trap if the state of POS-Interface is changed to down."
   ::= { unisposTrap 9 }
   


unisposInterDebugOpenTrap NOTIFICATION-TYPE
   OBJECTS 	{ unisposPosId }
   STATUS  	current
   DESCRIPTION
             "The agent will send a trap if the debug of POS-Interface is open."
   ::= { unisposTrap 10 }
   


unisposInterDebugAllOpenTrap NOTIFICATION-TYPE
   STATUS  	current
   DESCRIPTION
             "The agent will send a trap if the all debugs of POS-Interface are open."
   ::= { unisposTrap 11 }



unisposFCMTimeoutTrap NOTIFICATION-TYPE
   OBJECTS 	{ unisposFCMIfIndex }
   STATUS  	current
   DESCRIPTION
             "The agent will send a trap if the modem is hung up for timeout."
   ::= { unisposTrap 12 }
   


unisposFCMConnectFailTrap NOTIFICATION-TYPE
   OBJECTS 	{ unisposFCMIfIndex }
   STATUS  	current
   DESCRIPTION
             "The agent will send a trap if the handshaking of modems is not successful."
   ::= { unisposTrap 13 }
   
   
   
unisposClearPacketCounter NOTIFICATION-TYPE
   STATUS  	current
   DESCRIPTION
             "The agent will send a trap when the packet counter of 
             the POS application and interface is cleared."
   ::= { unisposTrap 14 }



unisposClearFcmCounter NOTIFICATION-TYPE
   STATUS  	current
   DESCRIPTION
             "The agent will send a trap when the FCM counter is cleared."
   ::= { unisposTrap 15 }
   
END
