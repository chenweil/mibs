-- =================================================================
-- Copyright (c) 2020 Unisyue Technologies Co., Ltd.  All rights reserved.
--
-- Description:protocol vlan mib
-- Reference:IEEE 802.1v clause 8.6.4
-- Version: V1.4
-- History:
--     V1.0 Initial version 2004-08-18
--     V1.1 Updated version 2004-08-31
--     V1.2 2004-10-12 updated by gaolong
--          Change value of UnisvProtocolVlanProtocolType from underscores to hyphens.
--          Remove unisProtocolVlanVlanId, unisProtocolVlanProtocolIndex from unisProtocolVlanProtocolGroup
--          because they are not-accessible objects.
--          Remove unisProtocolVlanPortIndex, unisProtocolVlanPortVlanId, unisProtocolVlanPortProtocolId
--          from unisProtocolVlanPortGroup because they are not-accessible objects.
--     V1.3 2005-08-31 updated by jiangjun
--          Add unisDifferentProtocolNumAllPort object to support the maximum
--          number of different protocols that can be applied on all ports.
--          Add enum value (ipv6) to UnisvProtocolVlanProtocolType.
--          Update file format by gaolong.
--     V1.4 2013-04-23 updated by yangxiaoren
--          Add unisProtocolVlanPortStatus object to support the protocol VLAN
--          status of port applied.
--          Add enum value notConfigured(201) to unisvProtocolVlanProtocolType.
-- =================================================================
UNIS-PROTOCOL-VLAN-MIB DEFINITIONS ::= BEGIN

    IMPORTS
        unisCommon
            FROM UNIS-OID-MIB
        OBJECT-GROUP, MODULE-COMPLIANCE
            FROM SNMPv2-CONF
        Integer32, OBJECT-TYPE, MODULE-IDENTITY
            FROM SNMPv2-SMI
        RowStatus, TEXTUAL-CONVENTION
            FROM SNMPv2-TC;


    unisProtocolVlan MODULE-IDENTITY
        LAST-UPDATED "200408311800Z"
        ORGANIZATION
            "Unisyue Technologies Co., Ltd."
        CONTACT-INFO
            ""
        DESCRIPTION
            "This MIB contains the objects for managing the protocol-based
             VLAN configurations."
        REVISION "200408311938Z"        -- August 31, 2004 at 19:38 GMT
        DESCRIPTION
            "The initial revision of this MIB module ."
        ::= { unisCommon 16 }

--
-- Textual conventions
--

    UnisvProtocolVlanProtocolType ::= TEXTUAL-CONVENTION
        STATUS current
        DESCRIPTION
            "
            Contains protocols both for Layer 3 and Layer 2.
            "
        SYNTAX INTEGER
        {
            -- Layer 3 protocols
            ip(1),
            ipx(2),
            at(3),
            ipv6(4),

            -- Layer 2 protocols
            mode-llc(101),
            mode-snap(102),
            mode-ethernetii(103),

            -- Protocol no configure
            notConfigure(201)
        }

    UnisvProtocolVlanProtocolSubType ::= TEXTUAL-CONVENTION
        STATUS current
        DESCRIPTION
            "
            combine with UnisvProtocolVlanProtocolType.

            ethernetii(2), llc(3), raw(4), snap(5) are used when the value
            of UnisvProtocolVlanProtocolType is for Layer 3 protocols.
            etype(6) is used when the value of UnisvProtocolVlanProtocolType
            is for Layer 2 protocols.
            For detailed information, see the DESCRIPTION part of
            unisProtocolVlanProtocolTypeValue.
            "
        SYNTAX INTEGER
        {
            notused(1),        -- this value indicates the object is not used.

            ethernetii(2),
            llc(3),
            raw(4),
            snap(5),

            etype(6)
        }

--
-- Node definitions
--

    unisProtocolVlanOperate OBJECT IDENTIFIER ::= { unisProtocolVlan 1 }


    unisProtocolNumAllVlan OBJECT-TYPE
        SYNTAX Integer32
        MAX-ACCESS read-only
        STATUS current
        DESCRIPTION
            "The maximum number of protocols that can be configured on all VLANs.
            This number may vary with products."
        ::= { unisProtocolVlanOperate 1 }

    unisProtocolNumPerVlan OBJECT-TYPE
        SYNTAX Integer32
        MAX-ACCESS read-only
        STATUS current
        DESCRIPTION
            "The maximum number of protocols that can be configured per VLAN.
            This number may vary with products."

        ::= { unisProtocolVlanOperate 2 }

    unisProtocolNumAllPort OBJECT-TYPE
        SYNTAX Integer32
        MAX-ACCESS read-only
        STATUS current
        DESCRIPTION
            "The maximum number of protocols that can be applied on all ports.
            This number may vary with products."
        ::= { unisProtocolVlanOperate 3 }

    unisProtocolNumPerPort OBJECT-TYPE
        SYNTAX Integer32
        MAX-ACCESS read-only
        STATUS current
        DESCRIPTION
            "The maximum number of protocols that can be applied to each port.
            This number may vary with products."
        ::= { unisProtocolVlanOperate 4 }

    unisProtocolVlanTable OBJECT-TYPE
        SYNTAX SEQUENCE OF UnisProtocolVlanEntry
        MAX-ACCESS not-accessible
        STATUS current
        DESCRIPTION
            "Protocol-based VLAN configuration table."
        ::= { unisProtocolVlanOperate 5 }

    unisProtocolVlanEntry OBJECT-TYPE
        SYNTAX UnisProtocolVlanEntry
        MAX-ACCESS not-accessible
        STATUS current
        DESCRIPTION
            "Protocol-based VLAN configuration entry."
        INDEX { unisProtocolVlanVlanId, unisProtocolVlanProtocolIndex }
        ::= { unisProtocolVlanTable 1 }

    UnisProtocolVlanEntry ::=
        SEQUENCE {
            unisProtocolVlanVlanId
                Integer32,
            unisProtocolVlanProtocolIndex
                Integer32,
            unisProtocolVlanProtocolType
                UnisvProtocolVlanProtocolType,
            unisProtocolVlanProtocolSubType
                UnisvProtocolVlanProtocolSubType,
            unisProtocolVlanProtocolTypeValue
                OCTET STRING,
            unisProtocolVlanRowStatus
                RowStatus
         }

    unisProtocolVlanVlanId OBJECT-TYPE
        SYNTAX Integer32
        MAX-ACCESS not-accessible
        STATUS current
        DESCRIPTION
            "Vlan ID."
        ::= { unisProtocolVlanEntry 1 }

    unisProtocolVlanProtocolIndex OBJECT-TYPE
        SYNTAX Integer32
        MAX-ACCESS not-accessible
        STATUS current
        DESCRIPTION
            "The protocol index value of a row in this table is in the range
            of [0..unisProtocolNumPerVlan-1].
            This object may not be provided during creation. In this case,
            a number is assigned by system automatically."
        ::= { unisProtocolVlanEntry 2 }

    unisProtocolVlanProtocolType OBJECT-TYPE
        SYNTAX UnisvProtocolVlanProtocolType
        MAX-ACCESS read-create
        STATUS current
        DESCRIPTION
            "
            Specify protocol types supported by a protocol-based VLAN.
            Now protocols supported on Layer 3 include ip, ipx, at, ipv6, etc.
            Now protocols supported on Layer 2 include llc, snap, ethernetii, etc.

            For detailed information, see description of
            unisProtocolVlanProtocolTypeValue.
            "
        ::= { unisProtocolVlanEntry 3 }

    unisProtocolVlanProtocolSubType OBJECT-TYPE
        SYNTAX UnisvProtocolVlanProtocolSubType
        MAX-ACCESS read-create
        STATUS current
        DESCRIPTION
            "
            See description of unisProtocolVlanProtocolTypeValue.
            "
        ::= { unisProtocolVlanEntry 4 }

    unisProtocolVlanProtocolTypeValue OBJECT-TYPE
        SYNTAX OCTET STRING(SIZE(0..255))
        MAX-ACCESS read-create
        STATUS current
        DESCRIPTION
            "
            The value of the configured protocol type.
            By default, semicolon(;) is used as a separator between different
            parts in the content of the object.

            The relationship among unisProtocolVlanProtocolType, unisProtocolVlanProtocolSubType
            and unisProtocolVlanProtocolTypeValue is as follows:

            |----------------------------------------------------------------------------------------------|
            | unisProtocolVlan- | unisProtocolVlan- | unisProtocolVlanProtocolTypeValue                    |
            | ProtocolType      | ProtocolSubType   |                                                      |
            |-------------------|-------------------|------------------------------------------------------|
            | ip                | notused           | notused for create operation                         |
            |-------------------|-------------------|------------------------------------------------------|
            | ipv6              | notused           | notused for create operation                         |
            |-------------------|-------------------|------------------------------------------------------|
            | at                | notused           | notused for create operation                         |
            |-------------------|-------------------|------------------------------------------------------|
            | ipx               | ethernetii        | notused for create operation
            |                   | llc               |                                                      |
            |                   | raw               |                                                      |
            |                   | snap              |                                                      |
            |-------------------|-------------------|------------------------------------------------------|
            | mode-snap         | etype             | hex string like '600', which means 0x0600.           |
            |                   |                   | The range is [0x600..0xffff]                         |
            |-------------------|-------------------|------------------------------------------------------|
            | mode-ethernetii   | etype             | hex string like '600', which means 0x0600.           |
            |                   |                   | The range is [0x600..0xffff]                         |
            |-------------------|-------------------|------------------------------------------------------|
            | mode-llc          | notused           | the sequence of different parts is as follows.       |
            |                   |                   | [dsap value][;ssap value][dsap value;ssap value]     |
            |                   |                   | Both range is [0x00..0xff]                           |
            |                   |                   |                                                      |
            |                   |                   | For example. Suppose value of dsap and ssap are 0x09 |
            |                   |                   | and 0x0a.                                            |
            |                   |                   | If neither dsap or ssap, the string length is zero.  |
            |                   |                   | If dsap provided, the string is '09;' or '09'        |
            |                   |                   | If ssap provided, the value is ';0a'                 |
            |                   |                   | If dsap and ssap provided, the value is '09;0a'      |
            |-------------------|-------------------|------------------------------------------------------|
            "
        ::= { unisProtocolVlanEntry 5 }

    unisProtocolVlanRowStatus OBJECT-TYPE
        SYNTAX RowStatus
        MAX-ACCESS read-create
        STATUS current
        DESCRIPTION
            "The row status of this table."
        ::= { unisProtocolVlanEntry 6 }

    unisProtocolVlanPortTable OBJECT-TYPE
        SYNTAX SEQUENCE OF UnisProtocolVlanPortEntry
        MAX-ACCESS not-accessible
        STATUS current
        DESCRIPTION
            "Protocol-based VLAN port information table."
        ::= { unisProtocolVlanOperate 6 }

    unisProtocolVlanPortEntry OBJECT-TYPE
        SYNTAX UnisProtocolVlanPortEntry
        MAX-ACCESS not-accessible
        STATUS current
        DESCRIPTION
            "Protocol-based VLAN port information entry."
        INDEX { unisProtocolVlanPortIndex, unisProtocolVlanPortVlanId,
                unisProtocolVlanPortProtocolId }
        ::= { unisProtocolVlanPortTable 1 }

    UnisProtocolVlanPortEntry ::=
        SEQUENCE {
            unisProtocolVlanPortIndex
                Integer32,
            unisProtocolVlanPortVlanId
                Integer32,
            unisProtocolVlanPortProtocolId
                Integer32,
            unisProtocolVlanPortProtocolType
                UnisvProtocolVlanProtocolType,
            unisProtocolVlanPortProtocolSubType
                UnisvProtocolVlanProtocolSubType,
            unisProtocolVlanPortTypeValue
                OCTET STRING,
            unisProtocolVlanPortRowStatus
                RowStatus,
            unisProtocolVlanPortStatus
                INTEGER
         }

    unisProtocolVlanPortIndex OBJECT-TYPE
        SYNTAX Integer32
        MAX-ACCESS not-accessible
        STATUS current
        DESCRIPTION
            "
            The maximum number is the total number of ports supported by device.
            "
        REFERENCE
            "unisLswPortIndex in UNIS-LSW-DEV-ADM-MIB"
        ::= { unisProtocolVlanPortEntry 1 }

    unisProtocolVlanPortVlanId OBJECT-TYPE
        SYNTAX Integer32
        MAX-ACCESS not-accessible
        STATUS current
        DESCRIPTION
            "The protocol-based VLAN ID."
        ::= { unisProtocolVlanPortEntry 2 }

    unisProtocolVlanPortProtocolId OBJECT-TYPE
        SYNTAX Integer32
        MAX-ACCESS not-accessible
        STATUS current
        DESCRIPTION
            "The protocol index."
        ::= { unisProtocolVlanPortEntry 3 }

    unisProtocolVlanPortProtocolType OBJECT-TYPE
        SYNTAX UnisvProtocolVlanProtocolType
        MAX-ACCESS read-only
        STATUS current
        DESCRIPTION
            "See the description of unisProtocolVlanProtocolType."
        ::= { unisProtocolVlanPortEntry 4 }

    unisProtocolVlanPortProtocolSubType OBJECT-TYPE
        SYNTAX UnisvProtocolVlanProtocolSubType
        MAX-ACCESS read-only
        STATUS current
        DESCRIPTION
            "See the description of unisProtocolVlanProtocolSubType."
        ::= { unisProtocolVlanPortEntry 5 }

    unisProtocolVlanPortTypeValue OBJECT-TYPE
        SYNTAX OCTET STRING
        MAX-ACCESS read-only
        STATUS current
        DESCRIPTION
            "See the description of unisProtocolVlanProtocolTypeValue."
        ::= { unisProtocolVlanPortEntry 6 }

    unisProtocolVlanPortRowStatus OBJECT-TYPE
        SYNTAX RowStatus
        MAX-ACCESS read-create
        STATUS current
        DESCRIPTION
            "The row status of this table."
        ::= { unisProtocolVlanPortEntry 7 }

    unisProtocolVlanPortStatus OBJECT-TYPE
        SYNTAX  INTEGER
        {
            active   (1),
            inactive (2)
        }
        MAX-ACCESS read-only
        STATUS current
        DESCRIPTION
            "The protocol VLAN status on the port.  The value is active only
            when unisProtocolVlanPortProtocolId has the corresponding entry in
            unisProtocolVlanTable, the port link type is hybrid, and the VLAN is
            allowed by the port.

            active:   protocol VLAN has been applied on the port.
            inactive: protocol VLAN is not applied on the port."
        ::= { unisProtocolVlanPortEntry 8 }

    unisDifferentProtocolNumAllPort OBJECT-TYPE
        SYNTAX Integer32
        MAX-ACCESS read-only
        STATUS current
        DESCRIPTION
            "The maximum number of different protocols that can be applied to all ports."
        ::= { unisProtocolVlanOperate 7 }

    unisProtocolVlanConformance OBJECT IDENTIFIER ::= { unisProtocolVlan 2 }


    unisProtocolVlanCompliances OBJECT IDENTIFIER ::= { unisProtocolVlanConformance 1 }


    unisProtocolVlanCompliance MODULE-COMPLIANCE
        STATUS current
        DESCRIPTION
            "The compliance statement for protocol VLAN MIB."
        MODULE -- this module
        MANDATORY-GROUPS {  unisProtocolVlanOperateGroup,
                            unisProtocolVlanProtocolGroup,
                            unisProtocolVlanPortGroup
                         }
        ::= { unisProtocolVlanCompliances 1 }


    unisProtocolVlanGroups OBJECT IDENTIFIER ::= { unisProtocolVlanConformance 2 }

    unisProtocolVlanOperateGroup OBJECT-GROUP
        OBJECTS { unisProtocolNumAllVlan, unisProtocolNumPerVlan,
                  unisProtocolNumAllPort, unisProtocolNumPerPort,
                  unisDifferentProtocolNumAllPort
                }
        STATUS current
        DESCRIPTION
            "A group of scalar objects describing the maximum number."
        ::= { unisProtocolVlanGroups 1 }

    unisProtocolVlanProtocolGroup OBJECT-GROUP
        OBJECTS { unisProtocolVlanProtocolType, unisProtocolVlanProtocolSubType,
                  unisProtocolVlanProtocolTypeValue, unisProtocolVlanRowStatus
                }
        STATUS current
        DESCRIPTION
            "A group of protocol VLAN protocol."
        ::= { unisProtocolVlanGroups 2 }

    unisProtocolVlanPortGroup OBJECT-GROUP
        OBJECTS { unisProtocolVlanPortProtocolType, unisProtocolVlanPortProtocolSubType,
                  unisProtocolVlanPortTypeValue, unisProtocolVlanPortRowStatus
                }
        STATUS current
        DESCRIPTION
            "A group of protocol VLAN port."
        ::= { unisProtocolVlanGroups 3 }

END
