-- ==================================================================
-- Copyright (c) 2020 Unisyue Technologies Co., Ltd.  All rights reserved.
--
-- Description: This MIB file is used for management of Balance Group
--              information.
-- Reference:
-- Version: V1.0
-- History:
--   V1.0 2009-09-15 Created by xupengfei02152
-- ==================================================================
UNIS-BLG-MIB DEFINITIONS ::= BEGIN

IMPORTS
    unisCommon
        FROM UNIS-OID-MIB
    Integer32, Counter64, OBJECT-TYPE, MODULE-IDENTITY
        FROM SNMPv2-SMI
    TEXTUAL-CONVENTION
        FROM SNMPv2-TC;

unisBlg MODULE-IDENTITY
    LAST-UPDATED "200909151111Z"
    ORGANIZATION
        "Unisyue Technologies Co., Ltd."
    CONTACT-INFO
        ""
    DESCRIPTION
        "This MIB module defines a set of basic objects for
        configuring switches and routers to set/get balance
        group information."
    REVISION
        "200909151111Z"
    DESCRIPTION
        "The initial version of this MIB."

   ::= { unisCommon 108 }

CounterClear ::= TEXTUAL-CONVENTION
    STATUS  current
    DESCRIPTION
        "Cleared: reset the value of the group's counter.
         Nouse: 'nouse' will be returned when getting."
    SYNTAX INTEGER
    {
        cleared(1),
        nouse(2)
    }

unisBlgObjects OBJECT IDENTIFIER  ::= { unisBlg 1 }

unisBlgStatsTable  OBJECT-TYPE
    SYNTAX SEQUENCE OF UnisBlgStatsEntry
    MAX-ACCESS not-accessible
    STATUS current
    DESCRIPTION
        "This table contains the statistics information
        about balance groups."
    ::= { unisBlgObjects 1 }

unisBlgStatsEntry OBJECT-TYPE
    SYNTAX UnisBlgStatsEntry
    MAX-ACCESS not-accessible
    STATUS current
    DESCRIPTION
        "This list contains statistics information."
    INDEX { unisBlgIndex }
    ::= { unisBlgStatsTable 1 }

UnisBlgStatsEntry ::=
   SEQUENCE
   {
       unisBlgIndex
           Integer32,
       unisBlgGroupTxPacketCount
           Counter64,
       unisBlgGroupRxPacketCount
           Counter64,
       unisBlgGroupTxByteCount
           Counter64,
       unisBlgGroupRxByteCount
           Counter64,
       unisBlgGroupCountClear
           CounterClear
   }

unisBlgIndex OBJECT-TYPE
    SYNTAX      Integer32 (1..2147483647)
    MAX-ACCESS  not-accessible
    STATUS      current
    DESCRIPTION
        "The index of the balance group."
    ::= { unisBlgStatsEntry 1 }

unisBlgGroupTxPacketCount OBJECT-TYPE
    SYNTAX      Counter64
    MAX-ACCESS  read-only
    STATUS      current
    DESCRIPTION
        "When retrieved, this object returns the count of
        packets the balance group has sent."
    ::= { unisBlgStatsEntry 2 }

unisBlgGroupRxPacketCount OBJECT-TYPE
    SYNTAX      Counter64
    MAX-ACCESS  read-only
    STATUS      current
    DESCRIPTION
        "When retrieved, this object returns the count of
        packets the balance group has received."
    ::= { unisBlgStatsEntry 3 }

unisBlgGroupTxByteCount OBJECT-TYPE
    SYNTAX      Counter64
    MAX-ACCESS  read-only
    STATUS      current
    DESCRIPTION
        "When retrieved, this object returns the count of
        bytes the balance group has sent."
    ::= { unisBlgStatsEntry 4 }

unisBlgGroupRxByteCount OBJECT-TYPE
    SYNTAX      Counter64
    MAX-ACCESS  read-only
    STATUS      current
    DESCRIPTION
        "When retrieved, this object returns the count of
        bytes the balance group has received."
    ::= { unisBlgStatsEntry 5 }

unisBlgGroupCountClear OBJECT-TYPE
    SYNTAX CounterClear
    MAX-ACCESS read-write
    STATUS current
    DESCRIPTION
        "This object is used to reset the counter of the balance group.
        Read operation is meaningless."
    ::= { unisBlgStatsEntry 6 }

END
