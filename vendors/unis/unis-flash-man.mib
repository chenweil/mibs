-- =================================================================
-- Copyright (c) 2020 Unisyue Technologies Co., Ltd.  All rights reserved.
--
-- Description: flash management mib
-- Reference:
-- Version: V3.3
-- History:
--     V1.0 initial version 2002-12-20
--     V1.1 2004-6-15 add delete(4) to unisFlhOperType
--     V1.2 2004-7-15 add some UnisFlashOperationStatus types:
--          opAuthFail(17),
--          opTimeout(18),
--          opDeleteFileOpenError(20),
--          opDeleteInvalidDevice(21),
--          opDeleteInvalidFunction(22),
--          opDeleteOperationError(23),
--          opDeleteInvalidFileName(24),
--          opDeleteDeviceBusy(25),
--          opDeleteParaError(26),
--          opDeleteInvalidPath(27)
--     V1.21 2004-8-19 modify the DESCRIPTION of unisFlhMinPartitionSize
--         by fanxiaoxun
--     V2.0 2004-10-12 updated by gaolong
--         Fix unisFlhMIBCompliance MODULE name to UNIS-FLASH-MAN-MIB
--     V2.1 2004-11-22 modify the SYNTAX of unisFlhSupportNum and unisFlhIndex
--         by wangpengju
--     V2.2 2005-01-11 updated by gaolong and weixinzhe
--         File description updated
--     V2.3 2005-01-11 add 'rename' operation type for unisFlhOperType,
--         by wangpengju
--     V2.4 2005-06-06 add enum value in SYNTAX of unisFlhOperProtocol
--         by jinyongfeng. Adjust file format by gaolong
--     V2.5 2005-08-18 change the value range of unisFlhFileIndex
--         from (1..32) to (1..2147483647), by wangpengju
--     V2.6 2006-03-03 updated by yangjianfeng
--         correct some error words which are obvious clerical error.
--     V2.7 2009-05-05 Add unisFlhOperServerPort by jinyi
--     V2.8 2010-06-05 add unisFlhOperFailReason by shuaixiaojuan
--                     add unisFlhKbyteSize by jinyi
--     V2.9 2010-10-30 Deprecated unisFlhOperServerAddress,
--                     added enum in UnisFlashOperationStatus,
--                     added unisFlhOperSrvAddrType, unisFlhOperSrvAddrRev and
--                     unisFlhOperSrvVPNName by songhao.
--     V3.0 2011-10-13 Modify syntax of unisFlhName and unisFlhPartName
--                     by shuaixiaojuan.
--     V3.1 2012-06-26 Add unisFlhPartBootable and unisFlhPartPathForGlobalOpt
--                     by lisong.
--     V3.2 2013-05-23 Add unisFlhHCSize, unisFlhPartHCSpace,
--                     unisFlhPartHCSpaceFree and unisFlhFileHCSize to replace
--                     unisFlhSize, unisFlhPartSpace, unisFlhPartSpaceFree
--                     and unisFlhFileSize by lisong.
--     V3.3 2014-08-11 Added mkdir(6), rmdir(7) to unisFlhOperType, added unisFlhFileType
--                     to unisFlhFileEntry, modified description of
--                     unisFlhFileName, unisFlhOperProtocol, unisFlhOperSourceFile
--                     and UnisFlashOperationStatus to support directory operation
--                     by SongHao.
--          2015-01-20 Added copy(8) to unisFlhOperType by SongHao.
-- =================================================================
UNIS-FLASH-MAN-MIB DEFINITIONS ::= BEGIN

IMPORTS
    PhysicalIndex
        FROM ENTITY-MIB
    unisCommon
        FROM UNIS-OID-MIB
    OBJECT-GROUP, MODULE-COMPLIANCE, NOTIFICATION-GROUP
        FROM SNMPv2-CONF
    TimeTicks, IpAddress, Integer32, Gauge32, Counter32,
    OBJECT-TYPE, MODULE-IDENTITY, NOTIFICATION-TYPE
        FROM SNMPv2-SMI
    InetAddressType, InetAddress
        FROM INET-ADDRESS-MIB
    DisplayString, TimeStamp, TruthValue, RowStatus, TEXTUAL-CONVENTION
        FROM SNMPv2-TC
    CounterBasedGauge64
        FROM HCNUM-TC;


unisFlash MODULE-IDENTITY
    LAST-UPDATED "201501200808Z"
    ORGANIZATION
        "Unisyue Technologies Co., Ltd."
    CONTACT-INFO
        ""
    DESCRIPTION
        "This MIB contains objects to manage flash cards and flash
        card operations.
        There are no constraints on this MIB."
    REVISION "201501200808Z"
    DESCRIPTION
        "Added copy(8) to unisFlhOperType."
    REVISION "201408110303Z"
    DESCRIPTION
        "Added mkdir(6), rmdir(7) to unisFlhOperType, added unisFlhFileType
        to unisFlhFileEntry, modified description of
        unisFlhFileName, unisFlhOperProtocol, unisFlhOperSourceFile
        and UnisFlashOperationStatus to support directory operation."
    REVISION "201305230000Z"
    DESCRIPTION
        "Add unisFlhHCSize, unisFlhPartHCSpace, unisFlhPartHCSpaceFree and
        unisFlhFileHCSize to replace unisFlhSize, unisFlhPartSpace,
        unisFlhPartSpaceFree and unisFlhFileSize."
    REVISION "201206260000Z"
    DESCRIPTION
        "Add unisFlhPartBootable and unisFlhPartPathForGlobalOpt."
    REVISION "201110130000Z"
    DESCRIPTION
        "Modify syntax of unisFlhName and unisFlhPartName."
    REVISION "201010300000Z"
    DESCRIPTION
        "Deprecated unisFlhOperServerAddress, added enum in
        UnisFlashOperationStatus, added unisFlhOperSrvAddrType,
        unisFlhOperSrvAddrRev and unisFlhOperSrvVPNName."
    REVISION "201006050000Z"
    DESCRIPTION
        "Add unisFlhOperFailReason and unisFlhKbyteSize."
    REVISION "200905050000Z"
    DESCRIPTION
        "Add unisFlhOperServerPort."
    REVISION "200603030000Z"
    DESCRIPTION
        "Correct some error words which are obvious clerical error."
    REVISION "200508180000Z"
    DESCRIPTION
        "Change the value range of unisFlhFileIndex from (1..32)
        to (1..2147483647)."
    REVISION "200506060000Z"
    DESCRIPTION
        "Add enum value in SYNTAX of unisFlhOperProtocol.
         Adjust file format."
    REVISION "200501110800Z"
    DESCRIPTION
        "Add 'rename' operation type for unisFlhOperType."
    REVISION "200501110000Z"
    DESCRIPTION
        "File description updated."
    REVISION "200411220000Z"
    DESCRIPTION
        "Modify the SYNTAX of unisFlhSupportNum and unisFlhIndex."
    REVISION "200410120000Z"
    DESCRIPTION
        "Fix unisFlhMIBCompliance MODULE name to UNIS-FLASH-MAN-MIB."
    REVISION "200408190000Z"
    DESCRIPTION
        "Modify the DESCRIPTION of unisFlhMinPartitionSize."
    REVISION "200407150000Z"
    DESCRIPTION
        "Add some UnisFlashOperationStatus types:
        opAuthFail(17),
        opTimeout(18),
        opDeleteFileOpenError(20),
        opDeleteInvalidDevice(21),
        opDeleteInvalidFunction(22),
        opDeleteOperationError(23),
        opDeleteInvalidFileName(24),
        opDeleteDeviceBusy(25),
        opDeleteParaError(26),
        opDeleteInvalidPath(27)"
    REVISION "200406150000Z"
    DESCRIPTION
        "add delete(4) to unisFlhOperType."
    REVISION "200212200000Z"
    DESCRIPTION
        "Initial version."
    ::= { unisCommon 5 }


--
-- Textual conventions
--

UnisFlashOperationStatus ::= TEXTUAL-CONVENTION
    STATUS current
    DESCRIPTION
        "The status of the specified operation can be one of
        the following.

        opInProgress : The operation is in process.
        opSuccess : The operation has been completed successfully.
        opInvalid : The command is invalid or command-protocol-device
                    combination is unsupported by the system.
        opInvalidProtocol : Invalid protocol is specified.
        opInvalidSourceName : Invalid source name is specified.
        opInvalidDestName : Invalid target name is specified.
        opInvalidServerAddress : Invalid server address is specified.
        opDeviceBusy : The device is in use and locked by another process.
        opDeviceOpenError : Invalid device name is specified.
        opDeviceError : Device read, write or erase error.
        opDeviceNotProgrammable : Device is read-only but a write or
                                  erase operation was specified.
        opDeviceFull : Device is filled to capacity.
        opFileOpenError : Invalid file/directory name,
                          file/directory not found in partition.
        opFileTransferError : File transfer was unsuccessful.
        opFileChecksumError : File checksum in Flash is invalid.
        opNoMemory : System is running in low on memory.
        opUnknownFailure : Failure which is unknown.
        opDeleteFileOpenError : File/Directory is in used by another process.
        opDeleteInvalidDevice : Invalid device name is specified.
        opDeleteInvalidFunction : Deleted operation is unsupported
                                  by the device.
        opDeleteOperationError : Operation is in a low error.
        opDeleteInvalidFileName : Invalid name is specified.
        opDeleteDeviceBusy : The device is in use and locked
                            by another process.
        opDeleteParaError : The parameters are invalid.
        opDeleteInvalidPath : The path is invalid.
        opDeleteFileNotExistInSlave : Failed to delete file, because the file
                                      does not exist in the slave.
        opDeleteFileFailedInSlave : Operation failed when deleting file in the slave.
        opSlaveFull : Operation failed because the slave doesn't have enough space.
        opCopyToSlaveFailure : Operation failed when copying file to the slave.
        "
    SYNTAX INTEGER
        {
            opInProgress(1),
            opSuccess(2),
            opInvalid(3),
            opInvalidProtocol(4),
            opInvalidSourceName(5),
            opInvalidDestName(6),
            opInvalidServerAddress(7),
            opDeviceBusy(8),
            opDeviceOpenError(9),
            opDeviceError(10),
            opDeviceNotProgrammable(11),
            opDeviceFull(12),
            opFileOpenError(13),
            opFileTransferError(14),
            opFileChecksumError(15),
            opNoMemory(16),
            opAuthFail(17),
            opTimeout(18),
            opUnknownFailure(19),
            opDeleteFileOpenError(20),
            opDeleteInvalidDevice(21),
            opDeleteInvalidFunction(22),
            opDeleteOperationError(23),
            opDeleteInvalidFileName(24),
            opDeleteDeviceBusy(25),
            opDeleteParaError(26),
            opDeleteInvalidPath(27),
            opDeleteFileNotExistInSlave(28),
            opDeleteFileFailedInSlave(29),
            opSlaveFull(30),
            opCopyToSlaveFailure(31)
        }

UnisFlashPartitionUpgradeMode ::= TEXTUAL-CONVENTION
    STATUS current
    DESCRIPTION
        "
        Flash partition upgrade method, i.e., method by which
        new files can be downloaded into the partition.
        FLH stands for Flash Load Helper, a feature provided
        on run-from-Flash systems for upgrading Flash.  This
        feature uses the bootstrap code in ROMs to help in
        automatic download.
        This object should be retrieved if the partition
        status is runFromFlash(2).
        If the partition status is readOnly(1), the upgrade
        method would depend on the reason for the readOnly
        status.  For example, it may simply be a matter of installing
        the programming jumper, or it may require execution of a
        later version of software that supports the Flash chips.

        unknown      -  the current system image does not know
                how Flash can be programmed.  A possible
                method would be to reload the ROM image
                and perform the upgrade manually.
        rxbootFLH    -  the Flash Load Helper is available to
                download files to Flash.  A copy-to-flash
                command can be used and this system image
                will automatically reload the Rxboot image
                in ROM and direct it to carry out the
                download request.
        direct       -  will be done directly by this image.
        "
    SYNTAX INTEGER
        {
            unknown(1),
            rxbootFLH(2),
            direct(3)
        }

UnisFlashPartitionStatus ::= TEXTUAL-CONVENTION
    STATUS current
    DESCRIPTION
        "If device is not programmable the value of it will be
        'readOnly'; If the current image is running from
        this partition the value of it will be 'runFromFlash'
        If device is programmable the value of it will be 'readWrite'.
        "
    SYNTAX INTEGER
        {
            readOnly(1),
            runFromFlash(2),
            readWrite(3)
        }


--
-- Node definitions
--
unisFlashManMIBObjects OBJECT IDENTIFIER ::= { unisFlash 1 }


-- The flash device information.
unisFlashDevice OBJECT IDENTIFIER ::= { unisFlashManMIBObjects 1 }


unisFlhSupportNum OBJECT-TYPE
    SYNTAX Integer32
    MAX-ACCESS read-only
    STATUS current
    DESCRIPTION
        "
        Specifies the total number of flash which the
        system supported.

        The MIB should not be loaded if there is no flash
        in the system and so the value here will be a
        minimum of 1.
        "
    ::= { unisFlashDevice 1 }


unisFlashTable OBJECT-TYPE
    SYNTAX SEQUENCE OF UnisFlashEntry
    MAX-ACCESS not-accessible
    STATUS current
    DESCRIPTION
        "
        This table gives the properties of all the flashes on
        the system.
        "
    ::= { unisFlashDevice 2 }


unisFlashEntry OBJECT-TYPE
    SYNTAX UnisFlashEntry
    MAX-ACCESS not-accessible
    STATUS current
    DESCRIPTION
        "The entry of unisFlashTable."
    INDEX { unisFlhIndex }
    ::= { unisFlashTable 1 }


UnisFlashEntry ::=
    SEQUENCE {
        unisFlhIndex                 Integer32,
        unisFlhSize                  Integer32,
        unisFlhPos                   PhysicalIndex,
        unisFlhName                  DisplayString,
        unisFlhChipNum               Integer32,
        unisFlhDescr                 DisplayString,
        unisFlhInitTime              TimeStamp,
        unisFlhRemovable             TruthValue,
        unisFlhPartitionBool         TruthValue,
        unisFlhMinPartitionSize      Integer32,
        unisFlhMaxPartitions         Integer32,
        unisFlhPartitionNum          Integer32,
        unisFlhKbyteSize             Integer32,
        unisFlhHCSize                CounterBasedGauge64
     }

unisFlhIndex OBJECT-TYPE
    SYNTAX Integer32 (1..2147483647)
    MAX-ACCESS read-only
    STATUS current
    DESCRIPTION
        "
        The index of unisFlashTable.  There are two parts for this index
        depicted as follows:
        31                  15                  0
        +++++++++++++++++++++++++++++++++++++++++
        +   entity index    +    random index   +
        +   ( bit 16..31 )       ( bit 0..15 )  +
        +++++++++++++++++++++++++++++++++++++++++

        From bit0 to bit15 (two bytes), it has a minimum value of 1, and
        maximum value of the same as the value of unisFlhSupportNum.

        From bit16 to bit31 (two bytes), it is the physical index the same as the
        entPhysicalIndex specified in ENTITY-MIB.
        "
    ::= { unisFlashEntry 1 }


unisFlhSize OBJECT-TYPE
    SYNTAX Integer32
    UNITS "bytes"
    MAX-ACCESS read-only
    STATUS deprecated
    DESCRIPTION
        "
        Specifies the total size of the flash indexed by unisFlhIndex.
        The value should be zero if the flash is removed for a removable
        device.
        If the total size of the flash exceeds 2,147,483,647 bytes,
        unisFlhHCSize specifies the actual size.
        "
    ::= { unisFlashEntry 2 }


unisFlhPos OBJECT-TYPE
    SYNTAX PhysicalIndex
    MAX-ACCESS read-only
    STATUS current
    DESCRIPTION
        "
        The position of the flash device in system.  This object is
        an index of entPhysicalTable in ENTITY-MIB.
        If the value of this object is 0,
        the main processor is indicated.
        "
    ::= { unisFlashEntry 3 }


unisFlhName OBJECT-TYPE
    SYNTAX DisplayString (SIZE (0..255))
    MAX-ACCESS read-only
    STATUS current
    DESCRIPTION
        "The flash name within the system."
    ::= { unisFlashEntry 4 }


unisFlhChipNum OBJECT-TYPE
    SYNTAX Integer32 (1..64)
    MAX-ACCESS read-only
    STATUS current
    DESCRIPTION
        "The chip numbers in the flash."
    ::= { unisFlashEntry 5 }


unisFlhDescr OBJECT-TYPE
    SYNTAX DisplayString (SIZE (0..64))
    MAX-ACCESS read-only
    STATUS current
    DESCRIPTION
        "Description of the purpose of the flash in the system."
    ::= { unisFlashEntry 6 }


unisFlhInitTime OBJECT-TYPE
    SYNTAX TimeStamp
    MAX-ACCESS read-only
    STATUS current
    DESCRIPTION
        "
        The initialization time for the flash component or partition,
        recorded using the system time.  This will be the boot time for
        a fixed device.  For a removable component or a partition,
        it will be the initialization time.
        "
    ::= { unisFlashEntry 8 }


unisFlhRemovable OBJECT-TYPE
    SYNTAX TruthValue
    MAX-ACCESS read-only
    STATUS current
    DESCRIPTION
        "
        The value indicates whether the flash indexed can be removed
        or not.
        The true(1) value indicates the flash device CAN be removed.
        "
    ::= { unisFlashEntry 9 }


unisFlhPartitionBool OBJECT-TYPE
    SYNTAX TruthValue
    MAX-ACCESS read-write
    STATUS current
    DESCRIPTION
        "
        The value indicates whether the flash indexed can be partitioned
        or not.
        The true(1) value indicates the flash CAN be partitioned.
        "
    ::= { unisFlashEntry 11 }


unisFlhMinPartitionSize OBJECT-TYPE
    SYNTAX Integer32
    UNITS "bytes"
    MAX-ACCESS read-only
    STATUS current
    DESCRIPTION
        "
        Minimum partition size supported.
        If unisFlhDevicePartitionBool is false, the value
        of this object is the same as unisFlhSize.
        "
    ::= { unisFlashEntry 12 }


unisFlhMaxPartitions OBJECT-TYPE
    SYNTAX Integer32 (1..8)
    MAX-ACCESS read-only
    STATUS current
    DESCRIPTION
        "
        The maximum count of partitions which the system supports
        for this flash.  If unisFlhPartitionBool is false,
        the object value is 1.
        "
    ::= { unisFlashEntry 13 }


unisFlhPartitionNum OBJECT-TYPE
    SYNTAX Integer32
    MAX-ACCESS read-only
    STATUS current
    DESCRIPTION
        "
        The actual number of partitions supported by the system for
        this flash.  If unisFlhPartitionBool is false, this value is 1.
        "
    ::= { unisFlashEntry 14 }

unisFlhKbyteSize OBJECT-TYPE
    SYNTAX Integer32
    UNITS "kbytes"
    MAX-ACCESS read-only
    STATUS current
    DESCRIPTION
        "
        Specifies the total size of the flash device indexed
        by unisFlhIndex.  The value should be zero if the flash is
        removed for a removable device.
        "
    ::= { unisFlashEntry 15 }

unisFlhHCSize OBJECT-TYPE
    SYNTAX CounterBasedGauge64
    UNITS "bytes"
    MAX-ACCESS read-only
    STATUS current
    DESCRIPTION
        "
        Specifies the total size of the flash indexed by unisFlhIndex.
        This node is a 64-bit substitute for unisFlhSize.
        "
    ::= { unisFlashEntry 16 }

unisFlashChips OBJECT IDENTIFIER ::= { unisFlashDevice 3 }


unisFlhChipTable OBJECT-TYPE
    SYNTAX SEQUENCE OF UnisFlhChipEntry
    MAX-ACCESS not-accessible
    STATUS current
    DESCRIPTION
        "
        Table of properties for all flash chips.
        Used mainly for diagnostics.
        "
    ::= { unisFlashChips 1 }


unisFlhChipEntry OBJECT-TYPE
    SYNTAX UnisFlhChipEntry
    MAX-ACCESS not-accessible
    STATUS current
    DESCRIPTION
        "The entry of unisFlhChipTable"
    INDEX { unisFlhIndex, unisFlhChipSerialNo }
    ::= { unisFlhChipTable 1 }


UnisFlhChipEntry ::=
    SEQUENCE {
        unisFlhChipSerialNo              Integer32,
        unisFlhChipID                    DisplayString,
        unisFlhChipDescr                 DisplayString,
        unisFlhChipWriteTimesLimit       Integer32,
        unisFlhChipWriteTimes            Counter32,
        unisFlhChipEraseTimesLimit       Integer32,
        unisFlhChipEraseTimes            Counter32
     }

unisFlhChipSerialNo OBJECT-TYPE
    SYNTAX Integer32 (1..64)
    MAX-ACCESS not-accessible
    STATUS current
    DESCRIPTION
        "Index of unisFlhChipTable."
    ::= { unisFlhChipEntry 1 }


unisFlhChipID OBJECT-TYPE
    SYNTAX DisplayString (SIZE (0..5))
    MAX-ACCESS read-only
    STATUS current
    DESCRIPTION
        "
        The manufacturer code (the upper byte) and
        device code (the lower byte) for a chip.
        Unknown chip code is presented as 00:00.
        "
    ::= { unisFlhChipEntry 2 }


unisFlhChipDescr OBJECT-TYPE
    SYNTAX DisplayString (SIZE (0..32))
    MAX-ACCESS read-only
    STATUS current
    DESCRIPTION
        "
        The description of the flash chip.
        "
    ::= { unisFlhChipEntry 3 }


unisFlhChipWriteTimesLimit OBJECT-TYPE
    SYNTAX Integer32
    MAX-ACCESS read-only
    STATUS current
    DESCRIPTION
        "
        The limit for the number of write times (retries)
        for a flash chip.  If the limit
        is exceeded an error should be reported by the management
        station.
        "
    ::= { unisFlhChipEntry 4 }


unisFlhChipWriteTimes OBJECT-TYPE
    SYNTAX Counter32
    MAX-ACCESS read-only
    STATUS current
    DESCRIPTION
        "
        A count of write times (retries) for the flash chip since
        initialization.
        A count of 25 or more for a single chip indicates a write error.
        Management stations should note the value of this MIB before and
        after a write operation,
        and report any errors accordingly.
        "
    ::= { unisFlhChipEntry 5 }


unisFlhChipEraseTimesLimit OBJECT-TYPE
    SYNTAX Integer32
    MAX-ACCESS read-only
    STATUS current
    DESCRIPTION
        "
        The limit for the number of erase times (retries) for a flash
        chip.
        If the limit is exceeded an error should be reported by the
        management station.
        "
    ::= { unisFlhChipEntry 6 }


unisFlhChipEraseTimes OBJECT-TYPE
    SYNTAX Counter32
    MAX-ACCESS read-only
    STATUS current
    DESCRIPTION
        "
        A count of erase times (retries) for the flash chip since
        initialization.
        A count of 2000 or more for a single chip indicates a write
        error.
        Management stations should note the value of this MIB before and
        after an erase operation, and report any errors accordingly.
        "
    ::= { unisFlhChipEntry 7 }


unisFlashPartitions OBJECT IDENTIFIER ::= { unisFlashDevice 4 }


unisFlhPartitionTable OBJECT-TYPE
    SYNTAX SEQUENCE OF UnisFlhPartitionEntry
    MAX-ACCESS not-accessible
    STATUS current
    DESCRIPTION
        "
        Properties for the flash partitions.  Minimum of one entry in
        this table.
        "
    ::= { unisFlashPartitions 1 }


unisFlhPartitionEntry OBJECT-TYPE
    SYNTAX UnisFlhPartitionEntry
    MAX-ACCESS not-accessible
    STATUS current
    DESCRIPTION
        "
        An entry of the unisFlhPartitionTable.Indexed by flash
        number and partition number.
        "
    INDEX { unisFlhIndex, unisFlhPartIndex }
    ::= { unisFlhPartitionTable 1 }


UnisFlhPartitionEntry ::=
SEQUENCE {
    unisFlhPartIndex                 Integer32,
    unisFlhPartFirstChip             Integer32,
    unisFlhPartLastChip              Integer32,
    unisFlhPartSpace                 Integer32,
    unisFlhPartSpaceFree             Gauge32,
    unisFlhPartFileNum               Integer32,
    unisFlhPartChecksumMethod        INTEGER,
    unisFlhPartStatus                UnisFlashPartitionStatus,
    unisFlhPartUpgradeMode           UnisFlashPartitionUpgradeMode,
    unisFlhPartName                  DisplayString,
    unisFlhPartRequireErase          TruthValue,
    unisFlhPartFileNameLen           Integer32,
    unisFlhPartBootable              TruthValue,
    unisFlhPartPathForGlobalOpt      TruthValue,
    unisFlhPartHCSpace               CounterBasedGauge64,
    unisFlhPartHCSpaceFree           CounterBasedGauge64
 }

unisFlhPartIndex OBJECT-TYPE
    SYNTAX Integer32 (1..8)
    MAX-ACCESS not-accessible
    STATUS current
    DESCRIPTION
        "
        An index which specifies a sequenced partition in the system.
        "
    ::= { unisFlhPartitionEntry 1 }


unisFlhPartFirstChip OBJECT-TYPE
    SYNTAX Integer32 (1..64)
    MAX-ACCESS read-only
    STATUS current
    DESCRIPTION
        "
        The first chip's sequence number in the
        partition, by which a chip can be indexed in
        chip table.
        "
    ::= { unisFlhPartitionEntry 2 }


unisFlhPartLastChip OBJECT-TYPE
    SYNTAX Integer32 (1..64)
    MAX-ACCESS read-only
    STATUS current
    DESCRIPTION
        "
        The last chip's sequence number in the
        partition, by which a chip can be indexed in
        chip table.
        "
    ::= { unisFlhPartitionEntry 3 }


unisFlhPartSpace OBJECT-TYPE
    SYNTAX Integer32
    UNITS "bytes"
    MAX-ACCESS read-only
    STATUS deprecated
    DESCRIPTION
        "
        The total space of the flash partition.
        The following should be satisfied:
        unisFlhPartSpace = n*unisFlhMinPartitionSize
        If the total size of the flash partition exceeds 2,147,483,647 bytes,
        unisFlhPartHCSpace specifies the actual size.
        "
    ::= { unisFlhPartitionEntry 4 }


unisFlhPartSpaceFree OBJECT-TYPE
    SYNTAX Gauge32
    UNITS "bytes"
    MAX-ACCESS read-only
    STATUS deprecated
    DESCRIPTION
        "
        The flash partition's free space.
        If the free space of the flash partition exceeds 2,147,483,647 bytes,
        unisFlhPartHCSpaceFree specifies the actual free space.
        "
    ::= { unisFlhPartitionEntry 5 }


unisFlhPartFileNum OBJECT-TYPE
    SYNTAX Integer32
    MAX-ACCESS read-only
    STATUS current
    DESCRIPTION
        "The number of all the files in the flash partition."
    ::= { unisFlhPartitionEntry 6 }


unisFlhPartChecksumMethod OBJECT-TYPE
    SYNTAX INTEGER
        {
            simpleChecksum(1),
            undefined(2),
            simpleCRC(3)
        }
    MAX-ACCESS read-only
    STATUS current
    DESCRIPTION
        "The Checksum method which the file system uses."
    ::= { unisFlhPartitionEntry 7 }


unisFlhPartStatus OBJECT-TYPE
    SYNTAX UnisFlashPartitionStatus
    MAX-ACCESS read-only
    STATUS current
    DESCRIPTION
        "The flash partition status."
    ::= { unisFlhPartitionEntry 8 }


unisFlhPartUpgradeMode OBJECT-TYPE
    SYNTAX UnisFlashPartitionUpgradeMode
    MAX-ACCESS read-only
    STATUS current
    DESCRIPTION
        "The upgrade mode of the Flash partition"
    ::= { unisFlhPartitionEntry 9 }


unisFlhPartName OBJECT-TYPE
    SYNTAX DisplayString (SIZE (0..255))
    MAX-ACCESS read-only
    STATUS current
    DESCRIPTION
        "The name of the flash partition given by the system."
    ::= { unisFlhPartitionEntry 10 }


unisFlhPartRequireErase OBJECT-TYPE
    SYNTAX TruthValue
    MAX-ACCESS read-only
    STATUS current
    DESCRIPTION
        "
        Shows whether a write operation is conditional on partition
        erase.
        "
    ::= { unisFlhPartitionEntry 11 }


unisFlhPartFileNameLen OBJECT-TYPE
    SYNTAX Integer32 (1..256)
    MAX-ACCESS read-only
    STATUS current
    DESCRIPTION
        "The maximum length of file name supported in the system."
    ::= { unisFlhPartitionEntry 12 }

unisFlhPartBootable OBJECT-TYPE
    SYNTAX TruthValue
    MAX-ACCESS read-only
    STATUS current
    DESCRIPTION
        "The value indicates whether the partition is a bootable partition.
         The true(1) value indicates a bootable partition.
        "
    ::= { unisFlhPartitionEntry 13 }

unisFlhPartPathForGlobalOpt OBJECT-TYPE
    SYNTAX TruthValue
    MAX-ACCESS read-write
    STATUS current
    DESCRIPTION
        "The value indicates whether the partition is used in a global file
         operation.  The true(1) value indicates that in one global file
         operation files will be copied to or deleted from this partition.
         When unisFlhPartPathForGlobalOpt in one entry is set to true(1),
         unisFlhPartPathForGlobalOpt in other entries with the same entity
         index will be set to false(0).
        "
    ::= { unisFlhPartitionEntry 14 }

unisFlhPartHCSpace OBJECT-TYPE
    SYNTAX CounterBasedGauge64
    UNITS "bytes"
    MAX-ACCESS read-only
    STATUS current
    DESCRIPTION
        "
        The total space of the flash partition.
        This node is a 64-bit substitute for unisFlhPartSpace.
        "
    ::= { unisFlhPartitionEntry 15 }


unisFlhPartHCSpaceFree OBJECT-TYPE
    SYNTAX CounterBasedGauge64
    UNITS "bytes"
    MAX-ACCESS read-only
    STATUS current
    DESCRIPTION
        "
        The flash partition's free space.
        This node is a 64-bit substitue for unisFlhPartSpace.
        "
    ::= { unisFlhPartitionEntry 16 }



unisFlhFiles OBJECT IDENTIFIER ::= { unisFlashPartitions 2 }


unisFlhFileTable OBJECT-TYPE
    SYNTAX SEQUENCE OF UnisFlhFileEntry
    MAX-ACCESS not-accessible
    STATUS current
    DESCRIPTION
        "Table of file information."
    ::= { unisFlhFiles 1 }


unisFlhFileEntry OBJECT-TYPE
    SYNTAX UnisFlhFileEntry
    MAX-ACCESS not-accessible
    STATUS current
    DESCRIPTION
        "
        An entry representing a file.  Indexed using flash number,
        partition number, and file number.
        "
    INDEX { unisFlhIndex, unisFlhPartIndex, unisFlhFileIndex }
    ::= { unisFlhFileTable 1 }


UnisFlhFileEntry ::=
    SEQUENCE {
        unisFlhFileIndex         Integer32,
        unisFlhFileName          DisplayString,
        unisFlhFileSize          Integer32,
        unisFlhFileStatus        INTEGER,
        unisFlhFileChecksum      OCTET STRING,
        unisFlhFileHCSize        CounterBasedGauge64,
        unisFlhFileType          INTEGER
        }

unisFlhFileIndex OBJECT-TYPE
    SYNTAX Integer32 (1..2147483647)
    MAX-ACCESS not-accessible
    STATUS current
    DESCRIPTION
        "Index of the table, whose range is from 1 to 2147483647"
    ::= { unisFlhFileEntry 1 }


unisFlhFileName OBJECT-TYPE
    SYNTAX DisplayString (SIZE (1..255))
    MAX-ACCESS read-only
    STATUS current
    DESCRIPTION
        "A valid file/directory name supported by the file system."
    ::= { unisFlhFileEntry 2 }


unisFlhFileSize OBJECT-TYPE
    SYNTAX Integer32
    MAX-ACCESS read-only
    STATUS deprecated
    DESCRIPTION
        "
        The file size in bytes excluding the file
        header of file system.  The value should be greater than zero.
        If the file size exceeds 2,147,483,647 bytes, unisFlhFileHCSize
        specifies the actual size.
        "
    ::= { unisFlhFileEntry 3 }


unisFlhFileStatus OBJECT-TYPE
    SYNTAX INTEGER
        {
            deleted(1),
            invalidChecksum(2),
            valid(3)
        }
    MAX-ACCESS read-only
    STATUS current
    DESCRIPTION
        "
        The status should be as follows:
        deleted(1):  The file is in recycle bin.
        invalidChecksum(2):  The checksum of file is invalid;
        valid(3):  A valid file.
        "
    ::= { unisFlhFileEntry 4 }


unisFlhFileChecksum OBJECT-TYPE
    SYNTAX OCTET STRING
    MAX-ACCESS read-only
    STATUS current
    DESCRIPTION
        "The file checksum in the header of file."
    ::= { unisFlhFileEntry 5 }


unisFlhFileHCSize OBJECT-TYPE
    SYNTAX CounterBasedGauge64
    UNITS "bytes"
    MAX-ACCESS read-only
    STATUS current
    DESCRIPTION
        "
        The file size in bytes.
        This node is a 64-bit substitue for unisFlhFileSize.
        "
    ::= { unisFlhFileEntry 6 }

unisFlhFileType OBJECT-TYPE
    SYNTAX INTEGER
        {
            file(1),
            directory(2)
        }
    MAX-ACCESS read-only
    STATUS current
    DESCRIPTION
        "This object indicates whether it is a file or directory."
    ::= { unisFlhFileEntry 7 }


-- The operation on the flash.
unisFlashOperate OBJECT IDENTIFIER ::= { unisFlashManMIBObjects 2 }


unisFlhOpTable OBJECT-TYPE
    SYNTAX SEQUENCE OF UnisFlhOpEntry
    MAX-ACCESS not-accessible
    STATUS current
    DESCRIPTION
        "Table used to operate flash."
    ::= { unisFlashOperate 1 }


unisFlhOpEntry OBJECT-TYPE
    SYNTAX UnisFlhOpEntry
    MAX-ACCESS not-accessible
    STATUS current
    DESCRIPTION
        "
        Note an operation cannot be stopped until it is finished.

        If notification is configured, NMS will receive a notification
        at the end of the operation.

        Entries in the table will be removed automatically in 5 minutes.
        It can also be deleted by NMS directly.
        "
    INDEX { unisFlhOperIndex }
    ::= { unisFlhOpTable 1 }


UnisFlhOpEntry ::=
    SEQUENCE {
        unisFlhOperIndex                 Integer32,
        unisFlhOperType                  INTEGER,
        unisFlhOperProtocol              INTEGER,
        unisFlhOperServerAddress         IpAddress,
        unisFlhOperServerUser            DisplayString,
        unisFlhOperPassword              DisplayString,
        unisFlhOperSourceFile            DisplayString,
        unisFlhOperDestinationFile       DisplayString,
        unisFlhOperStatus                UnisFlashOperationStatus,
        unisFlhOperEndNotification       TruthValue,
        unisFlhOperProgress              TimeTicks,
        unisFlhOperRowStatus             RowStatus,
        unisFlhOperServerPort            Integer32,
        unisFlhOperFailReason            DisplayString,
        unisFlhOperSrvAddrType           InetAddressType,
        unisFlhOperSrvAddrRev            InetAddress,
        unisFlhOperSrvVPNName            DisplayString
        }

unisFlhOperIndex OBJECT-TYPE
    SYNTAX Integer32 (1..2147483647)
    MAX-ACCESS not-accessible
    STATUS current
    DESCRIPTION
        "
        Specifies the index of an entry.  It is a
        random value when creating an entry.
        "
    ::= { unisFlhOpEntry 1 }


unisFlhOperType OBJECT-TYPE
    SYNTAX INTEGER
        {
            net2FlashWithErase(1),
            net2FlashWithoutErase(2),
            flash2Net(3),
            delete(4),
            rename(5),
            mkdir(6),
            rmdir(7),
            copy(8)
        }
    MAX-ACCESS read-create
    STATUS current
    DESCRIPTION
        "
        Specifies the operation to be executed.

        net2FlashWithErase  Copy a file to flash; erase flash beforehand.
        net2FlashWithoutErase   Copy a file to flash; do not erase flash
                                  beforehand.
        flash2Net       Copy a file from flash.
        delete          Delete a file that is specified by
                          unisFlhOperSourceFile.
        rename          Change a file's name.
        mkdir           Create a directory that is specified by
                          unisFlhOperSourceFile.
        rmdir           Delete a directory that is specified by
                          unisFlhOperSourceFile.
        copy            Copy a file.
        "
    ::= { unisFlhOpEntry 2 }


unisFlhOperProtocol OBJECT-TYPE
    SYNTAX INTEGER
        {
            ftp(1),
            tftp(2),
            clusterftp(3),
            clustertftp(4),
            sftp(5)
        }
    MAX-ACCESS read-create
    STATUS current
    DESCRIPTION
        "
        Specifies the protocol used to transfer a file.
        The default protocol is ftp.

        A directory cannot be transferred.

        when 'clusterftp' or 'clustertftp' is selected,
        the unisFlhOperServerAddress needn't be set,
        the server address can be acquired automatically, the value of
        unisFlhOperServerAddress is uncertain during operation.
        Both member switch and commander switch can use them if they
        support HGMP v2.
        "
    DEFVAL { ftp }
    ::= { unisFlhOpEntry 3 }


unisFlhOperServerAddress OBJECT-TYPE
    SYNTAX IpAddress
    MAX-ACCESS read-create
    STATUS deprecated
    DESCRIPTION
        "
        The address of remote host acting as server for operation.

        The default value is 255.255.255.255

        This object is replaced by unisFlhOperSrvAddrRev for it only support IPv4.
        "
    DEFVAL { 'FFFFFFFF'h }
    ::= { unisFlhOpEntry 4 }


unisFlhOperServerUser OBJECT-TYPE
    SYNTAX DisplayString
    MAX-ACCESS read-create
    STATUS current
    DESCRIPTION
        "
        When using ftp to transfer files, the user name must be
        specified through this node.
        "
    ::= { unisFlhOpEntry 5 }


unisFlhOperPassword OBJECT-TYPE
    SYNTAX DisplayString
    MAX-ACCESS read-create
    STATUS current
    DESCRIPTION
        "
        Remote user password for copying via ftp protocol.  Optionally,
        This object may be ignored for protocols other than ftp. "
    ::= { unisFlhOpEntry 6 }


unisFlhOperSourceFile OBJECT-TYPE
    SYNTAX DisplayString (SIZE (1..255))
    MAX-ACCESS read-create
    STATUS current
    DESCRIPTION
        "
        Specifies the source file/directory name for this operation
        that is specified by unisFlhOperType.

        It may be located on flash or remote server.
        It may include the file path if it is applicable.
        It must be specified.
        "
    ::= { unisFlhOpEntry 7 }


unisFlhOperDestinationFile OBJECT-TYPE
    SYNTAX DisplayString
    MAX-ACCESS read-create
    STATUS current
    DESCRIPTION
        "
        Specifies the destination file name.
        It may be located on flash or remote server.
        It may include the file path if it is applicable.
        If it is not specified, the destination file name
        is the same as source file name for application.
        "
    ::= { unisFlhOpEntry 8 }


unisFlhOperStatus OBJECT-TYPE
    SYNTAX UnisFlashOperationStatus
    MAX-ACCESS read-only
    STATUS current
    DESCRIPTION
        "The status of operation."
    ::= { unisFlhOpEntry 9 }


unisFlhOperEndNotification OBJECT-TYPE
    SYNTAX TruthValue
    MAX-ACCESS read-create
    STATUS current
    DESCRIPTION
        "
        If the value of it is specified 'true', a notification
        will be generated at the end of the operation.
        Else no notification will be generated.
        "
    DEFVAL { false }
    ::= { unisFlhOpEntry 10 }


unisFlhOperProgress OBJECT-TYPE
    SYNTAX TimeTicks
    MAX-ACCESS read-only
    STATUS current
    DESCRIPTION
        "The progress described as the time taken for the operation.
        "
    ::= { unisFlhOpEntry 11 }


unisFlhOperRowStatus OBJECT-TYPE
    SYNTAX RowStatus
    MAX-ACCESS read-create
    STATUS current
    DESCRIPTION
        "The row status of this table entry."
    ::= { unisFlhOpEntry 12 }

unisFlhOperServerPort OBJECT-TYPE
    SYNTAX Integer32 (0..65535)
    MAX-ACCESS read-create
    STATUS current
    DESCRIPTION
        "The port of remote host acting as server for operation.
         If the value of this object is not specified, the server
         port is the known protocol port."
    ::= { unisFlhOpEntry 13 }

unisFlhOperFailReason OBJECT-TYPE
    SYNTAX DisplayString
    MAX-ACCESS read-only
    STATUS current
    DESCRIPTION
        "The failure reasons of operation."
    ::= { unisFlhOpEntry 14 }

unisFlhOperSrvAddrType OBJECT-TYPE
    SYNTAX InetAddressType
    MAX-ACCESS read-create
    STATUS current
    DESCRIPTION
        "The type of IP address for unisFlhOperSrvAddrRev."
    ::= { unisFlhOpEntry 15 }

unisFlhOperSrvAddrRev OBJECT-TYPE
    SYNTAX InetAddress
    MAX-ACCESS read-create
    STATUS current
    DESCRIPTION
        "The address of remote host acting as server for operation."
    ::= { unisFlhOpEntry 16 }

unisFlhOperSrvVPNName OBJECT-TYPE
    SYNTAX DisplayString
    MAX-ACCESS read-create
    STATUS current
    DESCRIPTION
        "The VPN instance of this operation uses."
    ::= { unisFlhOpEntry 17 }

unisFlashNotification OBJECT IDENTIFIER ::= { unisFlashManMIBObjects 3 }


unisFlhOperNotification NOTIFICATION-TYPE
    OBJECTS { unisFlhOperStatus }
    STATUS current
    DESCRIPTION
        "
        A unisFlhOperNotification is sent at the completion of a flash
        copy operation if unisFlhOperEndNotification is true.
        "
    ::= { unisFlashNotification 1 }


unisFlashMIBConformance OBJECT IDENTIFIER ::= { unisFlash 2 }


unisFlhMIBCompliances OBJECT IDENTIFIER ::= { unisFlashMIBConformance 1 }


unisFlhMIBCompliance MODULE-COMPLIANCE
    STATUS current
    DESCRIPTION
        "
        The statement of compliance for those implementing this MIB.
        "
    MODULE UNIS-FLASH-MAN-MIB
    MANDATORY-GROUPS { unisFlhGroup, unisFlhPartitionGroup,
      unisFlhFileGroup, unisFlhOperationGroup, unisFlhNotificationGroup
         }
    GROUP unisFlhChipGroup
    DESCRIPTION
        " "
    ::= { unisFlhMIBCompliances 1 }


unisFlashMIBGroups OBJECT IDENTIFIER ::= { unisFlashMIBConformance 2 }


unisFlhGroup OBJECT-GROUP
    OBJECTS { unisFlhSupportNum, unisFlhSize, unisFlhPos, unisFlhName,
        unisFlhChipNum, unisFlhDescr, unisFlhInitTime, unisFlhRemovable,
        unisFlhPartitionBool, unisFlhMinPartitionSize,
        unisFlhMaxPartitions, unisFlhPartitionNum, unisFlhIndex, unisFlhKbyteSize }
    STATUS current
    DESCRIPTION
        "A collection of objects on Flash level information."
    ::= { unisFlashMIBGroups 1 }


unisFlhChipGroup OBJECT-GROUP
    OBJECTS { unisFlhChipID, unisFlhChipDescr, unisFlhChipWriteTimesLimit,
        unisFlhChipWriteTimes, unisFlhChipEraseTimesLimit,
        unisFlhChipEraseTimes }
    STATUS current
    DESCRIPTION
        "A collection of objects on chip level information."
    ::= { unisFlashMIBGroups 3 }


unisFlhPartitionGroup OBJECT-GROUP
    OBJECTS { unisFlhPartFirstChip, unisFlhPartLastChip, unisFlhPartSpace,
        unisFlhPartSpaceFree, unisFlhPartFileNum,
        unisFlhPartChecksumMethod, unisFlhPartStatus,
        unisFlhPartUpgradeMode, unisFlhPartName, unisFlhPartRequireErase,
        unisFlhPartFileNameLen, unisFlhPartBootable,
        unisFlhPartPathForGlobalOpt}
    STATUS current
    DESCRIPTION
        "A collection of objects providing on partition
        level information."
    ::= { unisFlashMIBGroups 4 }


unisFlhFileGroup OBJECT-GROUP
    OBJECTS { unisFlhFileName, unisFlhFileSize, unisFlhFileStatus,
        unisFlhFileChecksum }
    STATUS current
    DESCRIPTION
        "A collection of objects on file level information."
    ::= { unisFlashMIBGroups 5 }


unisFlhOperationGroup OBJECT-GROUP
    OBJECTS { unisFlhOperType, unisFlhOperProtocol,
        unisFlhOperServerAddress, unisFlhOperServerUser,
        unisFlhOperPassword, unisFlhOperSourceFile,
        unisFlhOperDestinationFile, unisFlhOperStatus,
        unisFlhOperEndNotification, unisFlhOperProgress,
        unisFlhOperRowStatus, unisFlhOperServerPort,
        unisFlhOperFailReason }
    STATUS current
    DESCRIPTION
        "A collection of objects of flash operations."
    ::= { unisFlashMIBGroups 6 }


unisFlhNotificationGroup NOTIFICATION-GROUP
    NOTIFICATIONS { unisFlhOperNotification }
    STATUS current
    DESCRIPTION
        "The collection of notifications in the module"
    ::= { unisFlashMIBGroups 7 }

END
