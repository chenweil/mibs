-- ===========================================================
-- Copyright (c) 2020 Unisyue Technologies Co., Ltd.  All rights reserved.
-- Description:
-- Reference:
-- Version: V2.8
-- History:
-- V1.0 created by liyue.
--     Define MODULE-IDENTITY for unisEpon
-- V1.1 2005-12-21 Adjusted the structure of some tables and the value of
--        some objects by liuhongxu
--        Redefined the scope of some objects
-- V1.2 2006-01-09 Updated file by liuhongxu and zoudian.
--        Added unisEponOnuTypeManTable, unisOltPortAlarmRegExcessEnabled,
--        unisOnuBindType, unisOnuPCBVersion, unisOnuRtt, unisOnuEEPROMVersion,
--        unisOnuRegType, unisOnuHostType, unisEponOnuRegExcessTrap,
--        unisEponOnuRegExcessRecoverTrap, unisOnuSlaBandWidthStepVal.
--        Changed the description of unisOnuSlaMaxBandWidth and unisOnuSlaMinBandWidth.
--        Adjusted the format.
-- V1.3 2006-01-16 Updated file by lichunyan.
--        Added unisOnuPacketManTable, unisOnuProtocolTable, unisOnuMulticastFilterStatus,
--        unisOnuDot1xTable.
--        Changed the default value of unisOnuSlaMaxBandWidth.
--        Adjusted the format of this mib.
-- V1.4 2006-06-08 Updated by chenzhaojie
--        Delete default values of unisOnuSlaMinBandWidth and unisOnuSlaMaxBandWidth
-- V1.5 2006-08-02 Updated by chenzhaojie
--        Add unisOnuSlaDelay, unisOnuDistance, unisOnuPriorityQueueTable,
--        unisOnuCountTable, unisOnuPriorityQueueSizeMinVal, unisOnuPriorityQueueSizeMaxVal,
--        unisEponOnuPowerOffTrap, unisEponOltSwitchoverTrap, unisEponStatTable.
--        Change DESCRIPTION of unisOnuSlaMinBandWidthMinVal, unisOnuSlaMinBandWidthMaxVal.
-- V1.6 2006-09-06 Updated by chenzhaojie
--        Add unisOnuPriorityQueueBandwidthMinVal, unisOnuPriorityQueueBandwidthMaxVal,
--        unisOnuPriorityQueueBurstsizeMinVal, unisOnuPriorityQueueBurstsizeMaxVal.
--        Add unisOnuQueueBandwidthTable.
-- V1.7 2007-05-21 Updated by chenzhaojie
--        Add unisEponSysScalarGroup
--        Add unisEponSysManTable ,unisEponAutoUpdateTable,unisEponOuiTable.
--        Add unisEponOuiIndexNextTable, unisEponMulticastControlTable.
--        Add unisOltPortAlarmDFEEnabled to unisOltPortAlarmThresholdTable.
--        Add unisOnuDbaReportQueueSetNumber, unisOnuRemoteFecStatus,unisOnuPortBerStatus
--        unisOnuReset, unisOnuMulticastControlMode,unisOnuAccessVlan,unisOnuEncryptKey
--        to unisOnuSysManTable
--        Add unisOnuLlid to unisOnuInfoTable.
--        Add unisOnuIpAddressTable, unisOnuChipSetInfoTable, unisOnuCapabilityTable,
--        unisOnuDbaReportTable.
--        Add unisEponOltDFETrap, unisEponOltDFERecoverTrap
-- V1.8 2007-10-13 Updated by liuhongxu, andapeng, lihaijun
--        Add unisOltMaxRtt to unisOltSysManTable.
--        Add unisOnuUniUpDownTrapStatus, unisOnuDhcpsnooping, unisOnuPppoe,
--        unisOnuIgmpSnoopingHostAgingT, unisOnuIgmpSnoopingMaxRespT,
--        unisOnuIgmpSnoopingRouterAgingT, unisOnuIgmpSnoopingAggReportS,
--        unisOnuIgmpSnoopingAggLeaveS, unisOnuDhcpallocate, unisOnuManageVID,
--        unisOnuManageVlanIntfS.
--        Add unisOnuCosToLocalPrecedenceTable.
--        Add unisOnuFecStatus to unisOnuSysManTable.
--        Add unisOnuIpAddressGateway to unisOnuIpAddressTable.
--        Changed the default value of unisEponMonitorCycle.
-- V1.9 2008-1-15 Updated by fengjian, qinlei, lihaijun
--        Add unisOnuSilentTable.
--        Add unisOltUsingOnuTable.
--        Add unisOnuFirmwareUpdateByTypeTable.
--        Add unisOnuUpdateByTypeNextIndex
--        Add unisOnuUpdateFileName to unisOnuFirmwareUpdateTable.
--        Add unisOnuUpdateResult values.
--        Add unisOnuSlaFixedBandWidth and unisOnuSlaPriorityClass to unisOnuSlaManTable.
--        Add unisEponOnuRegSilentMac.
--        Add unisEponOnuSilenceTrap, unisEponOnuSilenceRecoverTrap.
--        Add unisEponOnuUpdateResultTrap to report onu update result.
-- V2.0 2008-3-17 Updated by zoudian
--        Add unisOnuMcastCtrlHostAgingTime, unisOnuMulticastFastLeaveEnable
--        and unisOnuPortIsolateEnable to unisOnuSysManTable.
--        Add unisOnuIgspFastLeaveSupported and unisOnuMCtrlFastLeaveSupported
--        to unisOnuCapabilityTable.
--        Add unisOnuSlaFixedPacketSize to unisOnuSlaManTable.
-- V2.1 2008-07-25 updated by zhaodan and zoudian.
--        Add unisEponOnuAutoBindTrap and unisEponOperationResult.
--        Add unisOnuFirmwareVersion and unisOnuVendorId to unisOnuInfoTable.
--        Change the description of unisOnuDistance.
-- V2.2 2009-08-18 updated by zhaodan.
--        Add unisEponOnuStpPortTable.
--        Add unisEponOnuPortStpStateTrap to unisEponTrapPrefix.
-- V2.3 2010-02-25 updated by zhaodan.
--        Add unisEponOnuLaserState and unisEponOnuLaserFailedTrap.
--        Add unisOnuOpticalPowerReceivedByOlt to unisOnuInfoTable.
--        Add unisOltOpticalPowerTx and unisOltOpticalPowerRx to unisOltInfoTable.
--        Add unisOnuPhysicalTable and unisOnuSmlkTable.
--        Add unisOnuSmlkSwitchoverTrap to unisEponTrapPrefix.
-- V2.4 2010-12-02 updated by zhaodan.
--        Add unisOnuRS485PropertiesTable, unisOnuRS485SessionSummaryTable,
--            unisOnuRS485SessionTable and unisOnuRS485SessionErrInfoTable.
-- V2.5 2015-05-12 updated by lvhuipeng.
--        Add unisOnuDbaReport2Table.
--        Modify unisEponMonitorCycle, unisOltDbaDiscoveryLength, unisOltDbaDiscovryFrequency
--        Modify unisOnuCosToLocalPrecedenceValue
--        Modify unisEponOnuStpPortTable
-- V2.6 2016-11-29 updated by zhuhaifeng.
--        Add unisOnuSilentLoidTable, unisOnuLoidInfoTable.
--        Modify unisOnuFirmwareUpdateTable, unisOnuFirmwareUpdateByTypeTable.
--        Modify unisOnuBindMacAddrTable, unisEponSysMan, unisOltSysManTable.
--        Modify unisEponErrorInfo, unisEponTrap.
--      2018-02-02 updated by zhuhaifeng.
--        Add unisOnuStatisticsTable, unisOltTransceiverTxPowerTable, unisEponOnuPowerOnTrap.
--        Add unisOnuSlaMaxBandWidthMinVal10G, unisOnuSlaMaxBandWidthMaxVal10G.
--        Add unisOnuSlaMinBandWidthMinVal10G, unisOnuSlaMinBandWidthMaxVal10G.
--        Add unisEponOnuBindOneToOne.
--        Modify unisOltSysManTable, unisOnuSlaManTable, unisOnuCapabilityTable.
--        Modify unisOnuSysManTable, unisOnuDownStreamMaxBandWidth.
-- V2.7 2018-10-12 updated by zhuhaifeng.
--        Add unisOnuServiceSlaTable, unisOnuServiceSlaQueTable.
--        Add unisEponOpticalSignalLosTrap, unisEponOpticalSignalLosRecoverTrap.
--        Add unisEponOnuFiberFailTrap, unisEponOnuFiberFailRecoverTrap.
--      2018-11-28 updated by zhuhaifeng.
--        Add unisOnuInfoMac, unisOnuInfoLoid to unisOnuInfoTable.
--        Add unisOnuPoeTable.
-- V2.8 2019-07-08 updated by yinfengming.
--        Add unisRoltInterfaceTable, unisRoltMemberTable.
--        Modify unisOltUsingOnuTable.
--      2019-07-10 updated by duzhaohui.
--        Add unisEponOnuBlackListMacTable, unisEponOnuBlackListLoidTable.
-- =================================================================
UNIS-EPON-MIB DEFINITIONS ::= BEGIN

IMPORTS
        unisEpon
    FROM UNIS-OID-MIB
        ifIndex, ifDescr
    FROM IF-MIB
        unisLswFrameIndex, unisLswSlotIndex
    FROM UNIS-LSW-DEV-ADM-MIB
        Integer32, Unsigned32, Counter64, IpAddress, OBJECT-TYPE, MODULE-IDENTITY,
        NOTIFICATION-TYPE
    FROM SNMPv2-SMI
        TruthValue, MacAddress, DateAndTime, RowStatus, DisplayString
    FROM SNMPv2-TC
        InetAddress, InetAddressType
    FROM INET-ADDRESS-MIB;

unisEponMibObjects MODULE-IDENTITY
    LAST-UPDATED "201907101038Z"  -- July 10, 2019
    ORGANIZATION
        "Unisyue Technologies Co., Ltd."
    CONTACT-INFO
        ""
    DESCRIPTION
        "
        The objects in this MIB module are used to manage and
        display current configuration of Ethernet Passive Optical
        Network (EPON) port which are based on the Ethernet in
        the First Mile (EFM) Passive Optical Network(PON) as
        defined in IEEE Draft P802.3ah/D3.0 clause 60, 64, 65..
        "
    REVISION    "201907101038Z"  -- July 10, 2019
    DESCRIPTION "Add the objects of unisEponOnuBlackListMacTable, unisEponOnuBlackListLoidTable."
    REVISION    "201907081049Z"  -- July 08, 2019
    DESCRIPTION "Add the objects of unisRoltInterfaceTable, unisRoltMemberTable.
                 Modify unisOltUsingOnuTable."
    REVISION    "201811281049Z"  -- November 28, 2018
    DESCRIPTION "Add the objects of unisOnuServiceSlaTable, unisOnuServiceSlaQueTable,
                 unisEponOpticalSignalLosTrap, unisEponOpticalSignalLosRecoverTrap,
                 unisEponOnuFiberFailTrap, and unisEponOnuFiberFailRecoverTrap.
                 Add unisOnuInfoMac, unisOnuInfoLoid to unisOnuInfoTable.
                 Add unisOnuPoeTable."
    REVISION    "201703061145Z"  -- March 06, 2017
    DESCRIPTION "Add the objects of unisOnuStatisticsTable, and unisOltTransceiverTxPowerTable,
                 update the objects of unisOnuCapabilityTable, and unisOnuSysManTable."
    REVISION    "201702101145Z"  -- February 10, 2017
    DESCRIPTION "Add the objects of unisOnuSilentLoidTable, and unisOnuLoidInfoTable,
                 update the objects of unisOnuFirmwareUpdateTable,
                 unisOnuFirmwareUpdateByTypeTable, unisOnuBindMacAddrTable, unisEponSysMan,
                 unisOltSysManTable, unisEponErrorInfo, and unisEponTrap."
    REVISION    "201508041145Z"  -- August 4, 2015
    DESCRIPTION "Add the objects of unisOnuDbaReport2Table, update the
                 objects of unisEponMonitorCycle, unisOltDbaDiscoveryLength,
                 unisOltDbaDiscovryFrequency, and unisEponOnuStpPortTable."
    ::= { unisEpon 1 }

unisEponSysMan OBJECT IDENTIFIER ::= { unisEponMibObjects 1 }

unisEponAutoAuthorize OBJECT-TYPE
    SYNTAX      TruthValue
    MAX-ACCESS  read-write
    STATUS      current
    DESCRIPTION
        "
        This value determines whether software performs
        self-authorization for each Optical Network Unit(ONU)
        registering to the network.  Setting it to false
        means for every ONU registering, software requires
        external authorization, and until it's done the
        ONU is not authenticated.  True value means software
        authorizes each ONU registering to the network
        automatically.
        true  - ONUs are always authorized.
        false - If 802.1x authorization is enable,
        the ONUs have to be authorized by
        the protocol.
        - If 802.1x authorization is disable,
        ONUs are always authorized.
        "
    DEFVAL { false }
    ::= { unisEponSysMan 1 }


unisEponMonitorCycle OBJECT-TYPE
    SYNTAX      Integer32(1..3600)
    MAX-ACCESS  read-write
    STATUS      current
    DESCRIPTION
        "
        The cycle of alarm thresholds checking.
        Applying to the following types:
        Bit Error Rate(BER) alarm, Frame Error Rate(FER),
        Logical Link Identity(LLID) mismatch alarm and so on.
        The unit is second.
        "
    DEFVAL { 80 }
    ::= { unisEponSysMan 2 }

unisEponMsgTimeOut OBJECT-TYPE
    SYNTAX      Integer32
    MAX-ACCESS  read-write
    STATUS      current
    DESCRIPTION
        "
        Timeout waiting for a response from Optical Line Terminal(OLT)
        firmware after sending it a message.
        The unit is millisecond.
        "
    DEFVAL { 600 }
    ::= { unisEponSysMan 3 }

unisEponMsgLoseNum OBJECT-TYPE
    SYNTAX      Integer32
    MAX-ACCESS  read-write
    STATUS      current
    DESCRIPTION
        "
        The times of messages sending timeouts, after
        which OLT will reset (applying to every OLT).
        "
    DEFVAL { 20 }
    ::= { unisEponSysMan 4 }

unisEponSysHasEPONBoard OBJECT-TYPE
    SYNTAX      TruthValue
    MAX-ACCESS  read-only
    STATUS      current
    DESCRIPTION
        "
        true(1)  - At least an EPON board exists.
        false(2) - No EPON board exists.
        "
    ::= { unisEponSysMan 5 }

unisEponMonitorCycleEnable OBJECT-TYPE
    SYNTAX      TruthValue
    MAX-ACCESS  read-write
    STATUS      current
    DESCRIPTION
        "
        Stop or continue monitoring.
        true(1)  - Continue monitoring.
        false(2) - Stop monitoring.
        "
    DEFVAL { true }
    ::= { unisEponSysMan 6 }

unisEponOltSoftwareErrAlmEnable OBJECT-TYPE
    SYNTAX      TruthValue
    MAX-ACCESS  read-write
    STATUS      current
    DESCRIPTION
        "
        Software error alarm behavior of all active OLTs.
        true(1)  - alarm enable.
        false(2) - alarm disable.
        "
    DEFVAL { true }
    ::= { unisEponSysMan 7 }

unisEponPortLoopBackAlmEnable OBJECT-TYPE
    SYNTAX      TruthValue
    MAX-ACCESS  read-write
    STATUS      current
    DESCRIPTION
        "
        LoopBack alarm behavior of EPON ports.
        true(1)  - alarm enable.
        false(2) - alarm disable.
        "
    DEFVAL { true }
    ::= { unisEponSysMan 8 }

unisEponMonitorCycleMinVal OBJECT-TYPE
    SYNTAX      Integer32
    MAX-ACCESS  read-only
    STATUS      current
    DESCRIPTION
        "
        The lower limit of cycle which be confined to the
        unisEponMonitorCycle.
        "
    ::= { unisEponSysMan 9 }

unisEponMonitorCycleMaxVal OBJECT-TYPE
    SYNTAX      Integer32
    MAX-ACCESS  read-only
    STATUS      current
    DESCRIPTION
        "
        The upper limit of cycle which be confined to the
        unisEponMonitorCycle.
        "
    ::= { unisEponSysMan 10 }

unisEponMsgTimeOutMinVal OBJECT-TYPE
    SYNTAX      Integer32
    MAX-ACCESS  read-only
    STATUS      current
    DESCRIPTION
        "
        The lower limit of timeout which be confined to the
        unisEponMsgTimeOut.
        "
    ::= { unisEponSysMan 11 }

unisEponMsgTimeOutMaxVal OBJECT-TYPE
    SYNTAX      Integer32
    MAX-ACCESS  read-only
    STATUS      current
    DESCRIPTION
        "
        The upper limit of timeout which be confined to the
        unisEponMsgTimeOut.
        "
    ::= { unisEponSysMan 12 }

unisEponMsgLoseNumMinVal OBJECT-TYPE
    SYNTAX      Integer32
    MAX-ACCESS  read-only
    STATUS      current
    DESCRIPTION
        "
        The lower limit of time which be confined to the
        unisEponMsgLoseNum.
        "
    ::= { unisEponSysMan 13 }

unisEponMsgLoseNumMaxVal OBJECT-TYPE
    SYNTAX      Integer32
    MAX-ACCESS  read-only
    STATUS      current
    DESCRIPTION
        "
        The upper limit of time which be confined to the
        unisEponMsgLoseNum.
        "
    ::= { unisEponSysMan 14 }

unisEponSysScalarGroup OBJECT IDENTIFIER ::= { unisEponSysMan 15 }

--
-- unisEponSysManTable
--

unisEponSysManTable OBJECT-TYPE
    SYNTAX      SEQUENCE OF UnisEponSysManEntry
    MAX-ACCESS  not-accessible
    STATUS      current
    DESCRIPTION
        "
        This table defines system related parameters.
        "
    ::= { unisEponSysMan 16 }

unisEponSysManEntry OBJECT-TYPE
    SYNTAX      UnisEponSysManEntry
    MAX-ACCESS  not-accessible
    STATUS      current
    DESCRIPTION
        "
        The entry of the table unisEponSysManTable.
        "
    INDEX
        {
            unisEponSlotIndex
        }
    ::= { unisEponSysManTable 1 }

UnisEponSysManEntry ::= SEQUENCE
    {
        unisEponSlotIndex                   Integer32,
        unisEponModeSwitch                  INTEGER,
        unisEponAutomaticMode               INTEGER,
        unisEponOamDiscoveryTimeout         Integer32,
        unisEponEncryptionNoReplyTimeOut    Integer32,
        unisEponEncryptionUpdateTime        Integer32,
        unisEponAutoBindStatus              INTEGER,
        unisEponAutoBindType                BITS
    }

unisEponSlotIndex OBJECT-TYPE
    SYNTAX      Integer32
    MAX-ACCESS  not-accessible
    STATUS      current
    DESCRIPTION
        "
        Slot Index, the index of unisEponSysManTable.
        "
    ::= { unisEponSysManEntry 1 }

unisEponModeSwitch OBJECT-TYPE
    SYNTAX      INTEGER
        {
            cmode(1),
            hmode(2)
        }
    MAX-ACCESS  read-write
    STATUS      current
    DESCRIPTION
        "
        cmode - epon standard mode.
        hmode - private mode.
        "
    DEFVAL { cmode }
    ::= { unisEponSysManEntry 2 }

unisEponAutomaticMode OBJECT-TYPE
    SYNTAX      INTEGER
        {
            enable(1),
            disable(2)
        }
    MAX-ACCESS  read-write
    STATUS      current
    DESCRIPTION
        "
        Automatic mode setting: when enabled - after
        new OLT is added, the OLT stack sets its encryption mode
        to 'triple churning' and configure the OLT to authorize
        ONU MAC addresses according to its table.
        enable  -enable automatic mode.
        disable -disable automatic mode.
        "
    DEFVAL { enable }
    ::= { unisEponSysManEntry 3 }

unisEponOamDiscoveryTimeout OBJECT-TYPE
    SYNTAX      Integer32
    MAX-ACCESS  read-write
    STATUS      current
    DESCRIPTION
        "
        Time out parameter for extended OAM discovery
        process message, ranging from 0 to 2550,
        measured in 100 milliseconds.
        "
    DEFVAL { 30 }
    ::= { unisEponSysManEntry 4 }

unisEponEncryptionNoReplyTimeOut OBJECT-TYPE
    SYNTAX      Integer32
    MAX-ACCESS  read-write
    STATUS      current
    DESCRIPTION
        "
        Encryption response timeout,
        ranging from 1 to 2550,
        measured in 100 milliseconds.
        "
    DEFVAL { 30 }
    ::= { unisEponSysManEntry 5 }

unisEponEncryptionUpdateTime OBJECT-TYPE
    SYNTAX      Integer32
    MAX-ACCESS  read-write
    STATUS      current
    DESCRIPTION
        "
        Encryption key update timer for all ONUs on slot,
        indicated by unisEponSlotIndex,
        ranging from 1 to 255, measured in seconds.
        "
    DEFVAL { 10 }
    ::= { unisEponSysManEntry 6 }

unisEponAutoBindStatus OBJECT-TYPE
    SYNTAX      INTEGER
        {
            enable(1),
            disable(2)
        }
    MAX-ACCESS  read-write
    STATUS      current
    DESCRIPTION
        "
        enable  - auto bind ONU ID when the ONU registered in the EPON system.
        disable - need manual bind ONU ID when the ONU registered in the EPON system.
        "
    DEFVAL { disable }
    ::= { unisEponSysManEntry 7 }

unisEponAutoBindType OBJECT-TYPE
    SYNTAX      BITS
        {
            mac(0),
            loid(1),
            loidPassword(2)
        }
    MAX-ACCESS  read-write
    STATUS      current
    DESCRIPTION
        "
        Set auto binding type, which can be combined.
        If auto binding is disabled, 0 is returned.
        "
    ::= { unisEponSysManEntry 8 }

--
-- unisEponAutoUpdateTable
--
unisEponAutoUpdateTable OBJECT-TYPE
    SYNTAX      SEQUENCE OF UnisEponAutoUpdateEntry
    MAX-ACCESS  not-accessible
    STATUS      current
    DESCRIPTION
        "
        EPON auto update ONU application configuration.
        "
    ::= { unisEponSysMan 17 }

unisEponAutoUpdateEntry OBJECT-TYPE
    SYNTAX      UnisEponAutoUpdateEntry
    MAX-ACCESS  not-accessible
    STATUS      current
    DESCRIPTION
        "
        The entry of the table unisEponAutoUpdateTable.
        "
    INDEX
        {
            unisEponSlotIndex
        }
    ::= { unisEponAutoUpdateTable 1 }

UnisEponAutoUpdateEntry ::= SEQUENCE
    {
        unisEponAutoUpdateFileName          DisplayString,
        unisEponAutoUpdateSchedStatus       INTEGER,
        unisEponAutoUpdateSchedTime         OCTET STRING,
        unisEponAutoUpdateSchedType         INTEGER,
        unisEponAutoUpdateRealTimeStatus    INTEGER
    }
unisEponAutoUpdateFileName OBJECT-TYPE
    SYNTAX      DisplayString(SIZE(0..255))
    MAX-ACCESS  read-write
    STATUS      current
    DESCRIPTION
        "
        The name of ONU application file,  the file name must be valid
        and include the path.  It is a zero length string by default.
        "
    ::= { unisEponAutoUpdateEntry 1 }

unisEponAutoUpdateSchedStatus OBJECT-TYPE
    SYNTAX      INTEGER
        {
            enable(1),
            disable(2)
        }
    MAX-ACCESS  read-write
    STATUS      current
    DESCRIPTION
        "
        The status of schedule update configuration.
        The unisEponAutoUpdateFileName must be set before enable
        unisEponAutoUpdateSchedStatus.
        enable - enable ONU schedule update.
        disable - disable ONU schedule update.
        "
    DEFVAL { disable }
    ::= { unisEponAutoUpdateEntry 2 }

unisEponAutoUpdateSchedTime OBJECT-TYPE
    SYNTAX      OCTET STRING(SIZE(0..255))
    MAX-ACCESS  read-write
    STATUS      current
    DESCRIPTION
        "
        The schedule update timing configuration is related to
        the unisEponAutoUpdateSchedType.
        auto update daily: the string format is hhmm
        auto update weekly: the string format is hhmmw
        'w' means update weekly, it ranges from 0 to 6:
        0 - Sunday.
        1 - Monday.
        2 - Tuesday.
        3 - Wednesday.
        4 - Thursday.
        5 - Friday.
        6 - Saturday.
        auto update in coming date : the string format is hhmmyyyymmdd.
        The configuration will take effect only if unisEponAutoUpdateSchedStatus
        is enabled.
        "
    ::= { unisEponAutoUpdateEntry 3 }

unisEponAutoUpdateSchedType OBJECT-TYPE
    SYNTAX      INTEGER
        {
            daily(1),
            weekly(2),
            comingdate(3)
        }
    MAX-ACCESS  read-write
    STATUS      current
    DESCRIPTION
        "
        The update type of auto updating configuration.
        daily - update ONU application every day.
        weekly - update ONU application every week.
        comingdate - update ONU application on coming date.
        "
    ::= { unisEponAutoUpdateEntry 4 }

unisEponAutoUpdateRealTimeStatus OBJECT-TYPE
    SYNTAX      INTEGER
        {
            enable(1),
            disable(2)
        }
    MAX-ACCESS  read-write
    STATUS      current
    DESCRIPTION
        "
        The status of real time update configuration.
        The unisEponAutoUpdateFileName must be set before enable
        unisEponAutoUpdateRealTimeStatus.
        enable - enable ONU real time update.
        disable - disable ONU real time update.
        "
    DEFVAL { disable }
    ::= { unisEponAutoUpdateEntry 5 }

--
-- unisEponOuiIndexNextTable
--

unisEponOuiIndexNextTable OBJECT-TYPE
    SYNTAX      SEQUENCE OF UnisEponOuiIndexNextEntry
    MAX-ACCESS  not-accessible
    STATUS      current
    DESCRIPTION
        "
        Next OUI index table.
        "
    ::= { unisEponSysMan 18 }

unisEponOuiIndexNextEntry OBJECT-TYPE
    SYNTAX      UnisEponOuiIndexNextEntry
    MAX-ACCESS  not-accessible
    STATUS      current
    DESCRIPTION
        "
        The entry of the table unisEponOuiIndexNextTable.
        "
    INDEX
        {
            unisEponSlotIndex
        }
    ::= { unisEponOuiIndexNextTable 1 }

UnisEponOuiIndexNextEntry ::= SEQUENCE
    {
        unisEponOuiIndexNext    Integer32
    }

unisEponOuiIndexNext OBJECT-TYPE
    SYNTAX      Integer32
    MAX-ACCESS  read-only
    STATUS      current
    DESCRIPTION
        "
        This object contains an appropriate value to be used for
        unisEponOuiIndex when creating rows in the
        unisEponOuiTable.
        "
    ::= { unisEponOuiIndexNextEntry 1 }

--
-- unisEponOuiTable
--

unisEponOuiTable OBJECT-TYPE
    SYNTAX      SEQUENCE OF UnisEponOuiEntry
    MAX-ACCESS  not-accessible
    STATUS      current
    DESCRIPTION
        "
        List of OUI and OAM supported by OLT.
        "
    ::= { unisEponSysMan 19 }

unisEponOuiEntry OBJECT-TYPE
    SYNTAX      UnisEponOuiEntry
    MAX-ACCESS  not-accessible
    STATUS      current
    DESCRIPTION
        "
        The entry of the table unisEponOuiTable.
        "
    INDEX
        {
            unisEponSlotIndex,
            unisEponOuiIndex
        }
    ::= { unisEponOuiTable 1 }

UnisEponOuiEntry ::= SEQUENCE
    {
        unisEponOuiIndex        Integer32,
        unisEponOuiValue        OCTET STRING,
        unisEponOamVersion      OCTET STRING,
        unisEponOuiRowStatus    RowStatus
    }

unisEponOuiIndex OBJECT-TYPE
    SYNTAX      Integer32
    MAX-ACCESS  not-accessible
    STATUS      current
    DESCRIPTION
        "
        The index of this table.
        "
    ::= { unisEponOuiEntry 1 }

unisEponOuiValue OBJECT-TYPE
    SYNTAX      OCTET STRING(SIZE(0..512))
    MAX-ACCESS  read-create
    STATUS      current
    DESCRIPTION
        "
        OUI list supported by the extended OAM discovery process.
        The OUI is composed of six octets.  The first six octets denote the first OUI ,
        the second six octets denote the second OUI, and the like.
        "
    ::= { unisEponOuiEntry 2 }


unisEponOamVersion OBJECT-TYPE
    SYNTAX      OCTET STRING(SIZE(0..255))
    MAX-ACCESS  read-create
    STATUS      current
    DESCRIPTION
        "
        Version of OAM protocol defined by the organization denoted by OUI.
        "
    ::= { unisEponOuiEntry 3 }

unisEponOuiRowStatus OBJECT-TYPE
    SYNTAX      RowStatus
    MAX-ACCESS  read-create
    STATUS      current
    DESCRIPTION
        "
        The status of this table entry.  Only active,
        createAndGo, and destroy are supported.
        "
    ::= { unisEponOuiEntry 4 }

--
-- unisEponMulticastControlTable
--

unisEponMulticastControlTable OBJECT-TYPE
    SYNTAX      SEQUENCE OF UnisEponMulticastControlEntry
    MAX-ACCESS  not-accessible
    STATUS      current
    DESCRIPTION
        "
        Multicast control global configuration.
        "
    ::= { unisEponSysMan 20 }

unisEponMulticastControlEntry OBJECT-TYPE
    SYNTAX      UnisEponMulticastControlEntry
    MAX-ACCESS  not-accessible
    STATUS      current
    DESCRIPTION
        "
        The entry of the table unisEponMulticastControlTable.
        "
    INDEX
        {
            unisEponMulticastVlanId
        }
    ::= { unisEponMulticastControlTable 1 }

UnisEponMulticastControlEntry ::= SEQUENCE
    {
        unisEponMulticastVlanId         Integer32,
        unisEponMulticastAddressList    OCTET STRING,
        unisEponMulticastStatus         RowStatus
    }

unisEponMulticastVlanId OBJECT-TYPE
    SYNTAX      Integer32
    MAX-ACCESS  not-accessible
    STATUS      current
    DESCRIPTION
        "
        The index of this table.
        "
    ::= { unisEponMulticastControlEntry 1 }

unisEponMulticastAddressList OBJECT-TYPE
    SYNTAX      OCTET STRING(SIZE(0..255))
    MAX-ACCESS  read-create
    STATUS      current
    DESCRIPTION
        "
        The multicast address, each four octets represents a multicast address,
        the address section ranging from the first four octets to the second
        four octets, and the like.
        "
    ::= { unisEponMulticastControlEntry 2 }

unisEponMulticastStatus OBJECT-TYPE
    SYNTAX      RowStatus
    MAX-ACCESS  read-create
    STATUS      current
    DESCRIPTION
        "
        The status of this table entry. Only active,
        createAndGo, and destroy are supported.
        "
    ::= { unisEponMulticastControlEntry 3 }

unisEponAuthMode OBJECT-TYPE
    SYNTAX      BITS
        {
            mac(0),
            loid(1),
            loidPassword(2)
        }
    MAX-ACCESS  read-write
    STATUS      current
    DESCRIPTION
        "
        Set global auth mode, which can be combined(loid and loid-password cannot be configured at the same time).
        If no auth mode was set, 0 is returned.
        "
    ::= { unisEponSysMan 21 }

unisEponOnuBindOneToOne OBJECT-TYPE
    SYNTAX      TruthValue
    MAX-ACCESS  read-write
    STATUS      current
    DESCRIPTION
        "
        Enable or disable one-to-one ONU binding feature.
        true(1)  - feature enable.
        false(2) - feature disable.
        "
    ::= { unisEponSysMan 22 }

unisEponOnuBlackListMacTable OBJECT-TYPE
    SYNTAX      SEQUENCE OF UnisEponOnuBlackListMacEntry
    MAX-ACCESS  not-accessible
    STATUS      current
    DESCRIPTION
        "
        The table contains the configurations for managing the ONU MAC blacklist.
        "
    ::= { unisEponSysMan 23 }

unisEponOnuBlackListMacEntry OBJECT-TYPE
    SYNTAX      UnisEponOnuBlackListMacEntry
    MAX-ACCESS  not-accessible
    STATUS      current
    DESCRIPTION
        "
        The entry of the table unisEponOnuBlackListMacTable.
        "
    INDEX
        {
            unisEponOnuBlackListMac
        }
    ::= { unisEponOnuBlackListMacTable 1 }

UnisEponOnuBlackListMacEntry  ::= SEQUENCE
    {
        unisEponOnuBlackListMac             MacAddress,
        unisEponOnuBlackListMacRowStatus    RowStatus
    }

unisEponOnuBlackListMac OBJECT-TYPE
    SYNTAX      MacAddress
    MAX-ACCESS  read-only
    STATUS      current
    DESCRIPTION
        "
        The ONU MAC blacklist value.  This value is used to specify the blacklist MAC
        which is bound by the ONU interface.
        "
    ::= { unisEponOnuBlackListMacEntry 1 }

unisEponOnuBlackListMacRowStatus OBJECT-TYPE
    SYNTAX      RowStatus
    MAX-ACCESS  read-create
    STATUS      current
    DESCRIPTION
        "
        This object is responsible for managing the creation,
        deletion and modification of rows, which supports active
        status and CreatAndGo, destroy operation.
        "
    ::= { unisEponOnuBlackListMacEntry 2 }

unisEponOnuBlackListLoidTable OBJECT-TYPE
    SYNTAX      SEQUENCE OF UnisEponOnuBlackListLoidEntry
    MAX-ACCESS  not-accessible
    STATUS      current
    DESCRIPTION
        "
        The table contains the configurations for managing the ONU LOID blacklist.
        "
    ::= { unisEponSysMan 24 }

unisEponOnuBlackListLoidEntry OBJECT-TYPE
    SYNTAX      UnisEponOnuBlackListLoidEntry
    MAX-ACCESS  not-accessible
    STATUS      current
    DESCRIPTION
        "
        The entry of the table unisEponOnuBlackListLoidTable.
        "
    INDEX
        {
            unisEponOnuBlackListLoid
        }
    ::= { unisEponOnuBlackListLoidTable 1 }

UnisEponOnuBlackListLoidEntry  ::= SEQUENCE
    {
        unisEponOnuBlackListLoid            OCTET STRING,
        unisEponOnuBlackListLoidRowStatus   RowStatus
    }

unisEponOnuBlackListLoid    OBJECT-TYPE
    SYNTAX      OCTET STRING(SIZE(1..24))
    MAX-ACCESS  read-only
    STATUS      current
    DESCRIPTION
        "
        The ONU LOID blacklist value.  This value is used to specify the blacklist LOID
        which is bound by the ONU interface.
        "
    ::= { unisEponOnuBlackListLoidEntry 1 }

unisEponOnuBlackListLoidRowStatus OBJECT-TYPE
    SYNTAX      RowStatus
    MAX-ACCESS  read-create
    STATUS      current
    DESCRIPTION
        "
        This object is responsible for managing the creation,
        deletion and modification of rows, which supports active
        status and CreatAndGo, destroy operation.
        "
    ::= { unisEponOnuBlackListLoidEntry 2 }

unisEponFileName OBJECT IDENTIFIER ::= { unisEponMibObjects 2 }

unisEponDbaUpdateFileName OBJECT-TYPE
    SYNTAX      OCTET STRING(SIZE(0..64))
    MAX-ACCESS  read-write
    STATUS      current
    DESCRIPTION
        "
        The name of a binary file which is loaded to
        the OLT from an external source.  Note that the filename
        must contain the file path.
        "
    ::= { unisEponFileName 1 }

unisEponOnuUpdateFileName OBJECT-TYPE
    SYNTAX      OCTET STRING(SIZE(0..64))
    MAX-ACCESS  read-write
    STATUS      current
    DESCRIPTION
        "
        The filename of the ONU firmware to be updated.
        Note that the filename must contain the file path.
        "
    ::= { unisEponFileName 2 }

unisEponOltMan OBJECT IDENTIFIER ::= { unisEponMibObjects 3 }

--
-- unisOltSysManTable
--

unisOltSysManTable OBJECT-TYPE
    SYNTAX      SEQUENCE OF UnisOltSysManEntry
    MAX-ACCESS  not-accessible
    STATUS      current
    DESCRIPTION
        "
        This table defines several OLT system parameters:
        (1)laser on time
        (2)laser off time
        (3)whether multiple copy broadcast
        (4)whether discard packet
        (5)self test
        (6)self test result
        "
    ::= { unisEponOltMan 1 }

unisOltSysManEntry OBJECT-TYPE
    SYNTAX      UnisOltSysManEntry
    MAX-ACCESS  not-accessible
    STATUS      current
    DESCRIPTION
        "
        The entry of the table unisOltSysManTable.
        "
    INDEX
        {
            ifIndex
        }
    ::= { unisOltSysManTable 1 }

UnisOltSysManEntry ::= SEQUENCE
    {
        unisOltLaserOnTime            Integer32,
        unisOltLaserOffTime           Integer32,
        unisOltMultiCopyBrdCast       TruthValue,
        unisOltEnableDiscardPacket    TruthValue,
        unisOltSelfTest               INTEGER,
        unisOltSelfTestResult         INTEGER,
        unisOltMaxRtt                 Unsigned32,
        unisOltAuthMode               BITS,
        unisOltOnuBindOneToOne        TruthValue
    }

unisOltLaserOnTime OBJECT-TYPE
    SYNTAX      Integer32
    MAX-ACCESS  read-write
    STATUS      current
    DESCRIPTION
        "
        The laser on time of the ONUs during the
        discovery process, measured in Time Quanta(TQ).
        "
    DEFVAL { 96 }
    ::= { unisOltSysManEntry 1 }

unisOltLaserOffTime OBJECT-TYPE
    SYNTAX      Integer32
    MAX-ACCESS  read-write
    STATUS      current
    DESCRIPTION
        "
        The laser off time of the ONUs during the
        discovery process, measured in TQ.
        "
    DEFVAL { 96 }
    ::= { unisOltSysManEntry 2 }

unisOltMultiCopyBrdCast OBJECT-TYPE
    SYNTAX      TruthValue
    MAX-ACCESS  read-write
    STATUS      current
    DESCRIPTION
        "
        true/false filtering of tagged  multicast frames.
        The software avert tagged downstream frames with
        multicast or broadcast DA to the PON and not to the
        CPU, except for special multicast frames
        (link-constraint, IGMP control and ARP) that are
        passed to the CPU regardless of this feature.
        "
    DEFVAL { false }
    ::= { unisOltSysManEntry 3 }

unisOltEnableDiscardPacket OBJECT-TYPE
    SYNTAX      TruthValue
    MAX-ACCESS  read-write
    STATUS      current
    DESCRIPTION
        "
        Forward(false)/discard(true) any frames received from
        unlearned source address when the inside address
        table of the original ONU entry reach to the limit.
        "
    DEFVAL { false }
    ::= { unisOltSysManEntry 4 }

unisOltSelfTest OBJECT-TYPE
    SYNTAX      INTEGER
        {
            selftest(1)
        }
    MAX-ACCESS  read-write
    STATUS      current
    DESCRIPTION
        "
        selftest(1): Test OLT to check whether it's OK.
        "
    ::= { unisOltSysManEntry 5 }

unisOltSelfTestResult OBJECT-TYPE
    SYNTAX      INTEGER
        {
            other(1),
            ok(2),
            fail(3)
        }
    MAX-ACCESS  read-only
    STATUS      current
    DESCRIPTION
        "
        The self test result of the specific OLT.
        other(1): The self test result is another reason.
        ok(2):    The self test result is OK.
        fail(3):  The self test result is fail.
        "
    ::= { unisOltSysManEntry 6 }

unisOltMaxRtt OBJECT-TYPE
    SYNTAX      Unsigned32
    MAX-ACCESS  read-write
    STATUS      current
    DESCRIPTION
        "
        Set the max Round Trip Time of this OLT.
        "
    ::= { unisOltSysManEntry 7 }

unisOltAuthMode OBJECT-TYPE
    SYNTAX      BITS
        {
            mac(0),
            loid(1),
            loidPassword(2)
        }
    MAX-ACCESS  read-write
    STATUS      current
    DESCRIPTION
        "
        Set the auth mode of this OLT, which can be combined(loid and loid-password cannot be configured at the same time).
        If no auth mode was set, 0 is returned.
        "
    ::= { unisOltSysManEntry 8 }

unisOltOnuBindOneToOne OBJECT-TYPE
    SYNTAX      TruthValue
    MAX-ACCESS  read-write
    STATUS      current
    DESCRIPTION
        "
        Enable or disable one-to-one ONU binding feature.
        true(1)  - feature enable.
        false(2) - feature disable.
        "
    ::= { unisOltSysManEntry 9 }
--
-- unisOltInfoTable
--
unisOltInfoTable OBJECT-TYPE
    SYNTAX      SEQUENCE OF UnisOltInfoEntry
    MAX-ACCESS  not-accessible
    STATUS      current
    DESCRIPTION
        "
        Primary status of the specified OLT.
        There will be one row in this table for each
        information in the system.
        (1)Software and hardware versions of the specified OLT
        (unisOltFirmMajorVersion, unisOltFirmMinorVersion,
        unisOltHardMajorVersion, unisOltHardMinorVersion)
        (2)Several physical capabilities of an OLT device.
        (unisOltAgcLockTime, unisOltAgcCdrTime)
        (3)The operation(activation) status of an OLT.
        (unisOltMacAddress, unisOltWorkMode)
        "
    ::= { unisEponOltMan 2 }

unisOltInfoEntry OBJECT-TYPE
    SYNTAX      UnisOltInfoEntry
    MAX-ACCESS  not-accessible
    STATUS      current
    DESCRIPTION
        "
        The entry of the table unisOltInfoTable.
        "
    INDEX
        {
            ifIndex
        }
    ::= { unisOltInfoTable 1 }

UnisOltInfoEntry ::= SEQUENCE
    {
        unisOltFirmMajorVersion    OCTET STRING,
        unisOltFirmMinorVersion    OCTET STRING,
        unisOltHardMajorVersion    OCTET STRING,
        unisOltHardMinorVersion    OCTET STRING,
        unisOltAgcLockTime         Integer32,
        unisOltAgcCdrTime          Integer32,
        unisOltMacAddress          MacAddress,
        unisOltWorkMode            INTEGER,
        unisOltOpticalPowerTx      Integer32,
        unisOltOpticalPowerRx      Integer32
    }

unisOltFirmMajorVersion OBJECT-TYPE
    SYNTAX      OCTET STRING
    MAX-ACCESS  read-only
    STATUS      current
    DESCRIPTION
        "
        OLT firmware major version.  If the object length is
        zero, it means the version is unknown.
        "
    ::= { unisOltInfoEntry 1 }

unisOltFirmMinorVersion OBJECT-TYPE
    SYNTAX      OCTET STRING
    MAX-ACCESS  read-only
    STATUS      current
    DESCRIPTION
        "
        OLT firmware minor version.  If the object length is
        zero, it means the version is unknown.
        "
    ::= { unisOltInfoEntry 2 }

unisOltHardMajorVersion OBJECT-TYPE
    SYNTAX      OCTET STRING
    MAX-ACCESS  read-only
    STATUS      current
    DESCRIPTION
        "
        OLT hardware major version.  If the object length is
        zero, it means the version is unknown.
        "
    ::= { unisOltInfoEntry 3 }

unisOltHardMinorVersion OBJECT-TYPE
    SYNTAX      OCTET STRING
    MAX-ACCESS  read-only
    STATUS      current
    DESCRIPTION
        "
        OLT hardware minor version.  If the object length is
        zero, it means the version is unknown.
        "
    ::= { unisOltInfoEntry 4 }

unisOltAgcLockTime OBJECT-TYPE
    SYNTAX      Integer32
    MAX-ACCESS  read-only
    STATUS      current
    DESCRIPTION
        "
        PON upstream data Automatic Gain Control(AGC) lock time,
        measured in TQ,
        range: 1 - 2^15.
        0x7FFFFFFF: unknown value.
        "
    ::= { unisOltInfoEntry 5 }

unisOltAgcCdrTime OBJECT-TYPE
    SYNTAX      Integer32
    MAX-ACCESS  read-only
    STATUS      current
    DESCRIPTION
        "
        PON RX signal synchronization time,
        measured in TQ,
        range: 1 - 2^15.
        0x7FFFFFFF: unknown value
        "
    ::= { unisOltInfoEntry 6 }

unisOltMacAddress OBJECT-TYPE
    SYNTAX      MacAddress
    MAX-ACCESS  read-only
    STATUS      current
    DESCRIPTION
        "
        OLT MAC address.
        "
    ::= { unisOltInfoEntry 7 }

unisOltWorkMode OBJECT-TYPE
    SYNTAX      INTEGER
        {
            other(1),
            open(2),
            reset(3),
            closed(4)
        }
    MAX-ACCESS  read-only
    STATUS      current
    DESCRIPTION
        "
        The operation(activation) modes of an OLT.
        other(1)  - The OLT is in another mode.
        open(2)   - The OLT is open.
        reset(3)  - The OLT is reset.
        closed(4) - The OLT is closed.
        "
    ::= { unisOltInfoEntry 8 }

unisOltOpticalPowerTx OBJECT-TYPE
    SYNTAX      Integer32
    MAX-ACCESS  read-only
    STATUS      current
    DESCRIPTION
        "
        The optical power transmitted by this OLT.
        It measured in 0.01 dBm unit.
        "
    ::= { unisOltInfoEntry 9 }

unisOltOpticalPowerRx OBJECT-TYPE
    SYNTAX      Integer32
    MAX-ACCESS  read-only
    STATUS      current
    DESCRIPTION
        "
        The burst optical power received by this OLT.
        It measured in 0.01 dBm unit.
        "
    ::= { unisOltInfoEntry 10 }

--
-- unisOltDbaManTable
--
unisOltDbaManTable OBJECT-TYPE
    SYNTAX      SEQUENCE OF UnisOltDbaManEntry
    MAX-ACCESS  not-accessible
    STATUS      current
    DESCRIPTION
        "
        This table defines the primary parameters of the
        Dynamic Bandwidth Allocation(DBA) algorithm applying to the OLT.
        "
    ::= { unisEponOltMan 3 }

unisOltDbaManEntry OBJECT-TYPE
    SYNTAX      UnisOltDbaManEntry
    MAX-ACCESS  not-accessible
    STATUS      current
    DESCRIPTION
        "
        The entry of the table unisOltDbaManTable.
        "
    INDEX
        {
            ifIndex
        }
    ::= { unisOltDbaManTable 1 }

UnisOltDbaManEntry ::= SEQUENCE
    {
        unisOltDbaEnabledType          INTEGER,
        unisOltDbaDiscoveryLength      Integer32,
        unisOltDbaDiscovryFrequency    Integer32,
        unisOltDbaCycleLength          Integer32,
        unisOltDbaVersion              OCTET STRING,
        unisOltDbaUpdate               INTEGER,
        unisOltDbaUpdateResult         INTEGER
    }

unisOltDbaEnabledType OBJECT-TYPE
    SYNTAX      INTEGER
        {
            internal(1),
            external(2)
        }
    MAX-ACCESS  read-write
    STATUS      current
    DESCRIPTION
        "
        Enable different types of the DBA algorithm.
        Start upstream dynamic bandwidth allocation algorithm,
        replacing former bandwidth allocation mechanism.
        internal(1) - OLT internal Service Level Agreement(SLA) based
        algorithm, always being activated.
        external(2) - DBA algorithm in a binary file which is loaded to
        the OLT from an external source.
        "
    DEFVAL { internal }
    ::= { unisOltDbaManEntry 1 }

unisOltDbaDiscoveryLength OBJECT-TYPE
    SYNTAX      Integer32
    MAX-ACCESS  read-write
    STATUS      current
    DESCRIPTION
        "
        Discovery length in TQ units.
        "
    ::= { unisOltDbaManEntry 2 }

unisOltDbaDiscovryFrequency OBJECT-TYPE
    SYNTAX      Integer32
    MAX-ACCESS  read-write
    STATUS      current
    DESCRIPTION
        "
        How often should the OLT send discovery frames to
        the ONUs, measured in grant cycles.
        "
    ::= { unisOltDbaManEntry 3 }

unisOltDbaCycleLength OBJECT-TYPE
    SYNTAX      Integer32
    MAX-ACCESS  read-write
    STATUS      current
    DESCRIPTION
        "
        The grant cycle length in TQ units.
        "
    DEFVAL { 65535 }
    ::= { unisOltDbaManEntry 4 }

unisOltDbaVersion OBJECT-TYPE
    SYNTAX      OCTET STRING
    MAX-ACCESS  read-only
    STATUS      current
    DESCRIPTION
        "
        DBA version of the OLT.
        "
    ::= { unisOltDbaManEntry 5 }

unisOltDbaUpdate OBJECT-TYPE
    SYNTAX      INTEGER
        {
            update(1)
        }
    MAX-ACCESS  read-write
    STATUS      current
    DESCRIPTION
        "
        Update(1): Update the DBA algorithm with a binary
        file which is loaded to the OLT from an external source(flash).
        Config the MIB object module unisEponDbaUpdateFileName.
        "
    ::= { unisOltDbaManEntry 6 }

unisOltDbaUpdateResult OBJECT-TYPE
    SYNTAX      INTEGER
        {
            other(1),
            ok(2),
            fail(3),
            fileNotExist(4),
            notSetFilename(5)
        }
    MAX-ACCESS  read-only
    STATUS      current
    DESCRIPTION
        "
        The latest DBA update result.
        other: The DBA update result is another reason.
        ok:    The DBA update result is OK.
        fail:  The DBA update result is fail.
        fileNotExist: The DBA update failed because the file
        does not exist.
        notSetFilename: The DBA filename is not set.
        "
    ::= { unisOltDbaManEntry 7 }

--
-- unisOltPortAlarmThresholdTable
--

unisOltPortAlarmThresholdTable OBJECT-TYPE
    SYNTAX      SEQUENCE OF UnisOltPortAlarmThresholdEntry
    MAX-ACCESS  not-accessible
    STATUS      current
    DESCRIPTION
        "
        The table defines the alarm threshold of OLT.
        "
    ::= { unisEponOltMan 4 }

unisOltPortAlarmThresholdEntry OBJECT-TYPE
    SYNTAX      UnisOltPortAlarmThresholdEntry
    MAX-ACCESS  not-accessible
    STATUS      current
    DESCRIPTION
        "
        The entry of the table unisOltPortAlarmThresholdTable.
        "
    INDEX
        {
            ifIndex
        }
    ::= { unisOltPortAlarmThresholdTable 1 }

UnisOltPortAlarmThresholdEntry ::= SEQUENCE
    {
        unisOltPortAlarmBerEnabled                 TruthValue,
        unisOltPortAlarmBerDirect                  INTEGER,
        unisOltPortAlarmBerThreshold               Integer32,
        unisOltPortAlarmFerEnabled                 TruthValue,
        unisOltPortAlarmFerDirect                  INTEGER,
        unisOltPortAlarmFerThreshold               Integer32,
        unisOltPortAlarmLlidMismatchEnabled        TruthValue,
        unisOltPortAlarmLlidMismatchThreshold      Integer32,
        unisOltPortAlarmRemoteStableEnabled        TruthValue,
        unisOltPortAlarmLocalStableEnabled         TruthValue,
        unisOltPortAlarmRegistrationEnabled        TruthValue,
        unisOltPortAlarmOamDisconnectionEnabled    TruthValue,
        unisOltPortAlarmEncryptionKeyEnabled       TruthValue,
        unisOltPortAlarmVendorSpecificEnabled      TruthValue,
        unisOltPortAlarmRegExcessEnabled           TruthValue,
        unisOltPortAlarmDFEEnabled                 TruthValue
    }

unisOltPortAlarmBerEnabled OBJECT-TYPE
    SYNTAX      TruthValue
    MAX-ACCESS  read-write
    STATUS      current
    DESCRIPTION
        "
        Behavior of BER alarm.
        true(1)  - alarm enable.
        false(2) - alarm disable.
        "
    DEFVAL { true }
    ::= { unisOltPortAlarmThresholdEntry 1 }

unisOltPortAlarmBerDirect OBJECT-TYPE
    SYNTAX      INTEGER
        {
            berUplink(1),
            berDownlink(2),
            berAll(3)
        }
    MAX-ACCESS  read-write
    STATUS      current
    DESCRIPTION
        "
        Traffic direction to monitor for BER alarm.
        "
    DEFVAL { berAll }
    ::= { unisOltPortAlarmThresholdEntry 2 }

unisOltPortAlarmBerThreshold OBJECT-TYPE
    SYNTAX      Integer32
    MAX-ACCESS  read-write
    STATUS      current
    DESCRIPTION
        "
        BER threshold exceed which the alarm is raised.
        "
    DEFVAL { 10 }
    ::= { unisOltPortAlarmThresholdEntry 3 }

unisOltPortAlarmFerEnabled OBJECT-TYPE
    SYNTAX      TruthValue
    MAX-ACCESS  read-write
    STATUS      current
    DESCRIPTION
        "
        Behavior of FER alarm.
        true(1)  - alarm enable.
        false(2) - alarm disable.
        "
    DEFVAL { true }
    ::= { unisOltPortAlarmThresholdEntry 4 }

unisOltPortAlarmFerDirect OBJECT-TYPE
    SYNTAX      INTEGER
        {
            ferUplink(1),
            ferDownlink(2),
            ferAll(3)
        }
    MAX-ACCESS  read-write
    STATUS      current
    DESCRIPTION
        "
        Traffic direction to monitor for FER alarm.
        "
    DEFVAL { ferAll }
    ::= { unisOltPortAlarmThresholdEntry 5 }

unisOltPortAlarmFerThreshold OBJECT-TYPE
    SYNTAX      Integer32
    MAX-ACCESS  read-write
    STATUS      current
    DESCRIPTION
        "
        Frame error rate exceed threshold then the alarm is raised.
        "
    DEFVAL { 1 }
    ::= { unisOltPortAlarmThresholdEntry 6 }

unisOltPortAlarmLlidMismatchEnabled OBJECT-TYPE
    SYNTAX      TruthValue
    MAX-ACCESS  read-write
    STATUS      current
    DESCRIPTION
        "
        Behavior of LLID mismatch alarm.
        true(1)  - alarm enable.
        false(2) - alarm disable.
        "
    DEFVAL { false }
    ::= { unisOltPortAlarmThresholdEntry 7 }

unisOltPortAlarmLlidMismatchThreshold OBJECT-TYPE
    SYNTAX      Integer32
    MAX-ACCESS  read-write
    STATUS      current
    DESCRIPTION
        "
        The minimal number of mismatched frames exceed threshold then
        LLID mismatch alarm is raised.
        "
    DEFVAL { 5000 }
    ::= { unisOltPortAlarmThresholdEntry 8 }

unisOltPortAlarmRemoteStableEnabled OBJECT-TYPE
    SYNTAX      TruthValue
    MAX-ACCESS  read-write
    STATUS      current
    DESCRIPTION
        "
        Behavior of remote stable alarm.
        true(1)  - alarm enable.
        false(2) - alarm disable.
        "
    DEFVAL { true }
    ::= { unisOltPortAlarmThresholdEntry 9 }

unisOltPortAlarmLocalStableEnabled OBJECT-TYPE
    SYNTAX      TruthValue
    MAX-ACCESS  read-write
    STATUS      current
    DESCRIPTION
        "
        Behavior of local stable alarm.
        true(1)  - alarm enable.
        false(2) - alarm disable.
        "
    DEFVAL { true }
    ::= { unisOltPortAlarmThresholdEntry 10 }

unisOltPortAlarmRegistrationEnabled OBJECT-TYPE
    SYNTAX      TruthValue
    MAX-ACCESS  read-write
    STATUS      current
    DESCRIPTION
        "
        Behavior of registration alarm.
        true(1)  - alarm enable.
        false(2) - alarm disable.
        "
    DEFVAL { true }
    ::= { unisOltPortAlarmThresholdEntry 11 }

unisOltPortAlarmOamDisconnectionEnabled OBJECT-TYPE
    SYNTAX      TruthValue
    MAX-ACCESS  read-write
    STATUS      current
    DESCRIPTION
        "
        Behavior of Operations Administration and Maintenance(OAM)
        disconnection alarm.
        true(1)  - alarm enable.
        false(2) - alarm disable.
        "
    DEFVAL { true }
    ::= { unisOltPortAlarmThresholdEntry 12 }

unisOltPortAlarmEncryptionKeyEnabled OBJECT-TYPE
    SYNTAX      TruthValue
    MAX-ACCESS  read-write
    STATUS      current
    DESCRIPTION
        "
        Behavior of encryption bad key alarm.
        true(1)  - alarm enable.
        false(2) - alarm disable.
        "
    DEFVAL { true }
    ::= { unisOltPortAlarmThresholdEntry 13 }

unisOltPortAlarmVendorSpecificEnabled OBJECT-TYPE
    SYNTAX      TruthValue
    MAX-ACCESS  read-write
    STATUS      current
    DESCRIPTION
        "
        Behavior of vendor specific alarm.
        true(1)  - alarm enable.
        false(2) - alarm disable.
        "
    DEFVAL { true }
    ::= { unisOltPortAlarmThresholdEntry 14 }

unisOltPortAlarmRegExcessEnabled OBJECT-TYPE
    SYNTAX      TruthValue
    MAX-ACCESS  read-write
    STATUS      current
    DESCRIPTION
        "
        Behavior of ONU registering over limitation alarm.
        true(1)  - alarm enable.
        false(2) - alarm disable.
        "
    DEFVAL { true }
    ::= { unisOltPortAlarmThresholdEntry 15 }

unisOltPortAlarmDFEEnabled OBJECT-TYPE
    SYNTAX      TruthValue
    MAX-ACCESS  read-write
    STATUS      current
    DESCRIPTION
        "
        Behavior of device fatal error alarm.
        true  - alarm enable.
        false - alarm disable.
        "
    DEFVAL { true }
    ::= { unisOltPortAlarmThresholdEntry 16 }

unisOltLaserOnTimeMinVal OBJECT-TYPE
    SYNTAX      Integer32
    MAX-ACCESS  read-only
    STATUS      current
    DESCRIPTION
        "
        The lower limit of time which is confined to
        unisOltLaserOnTime.
        "
    ::= { unisEponOltMan 5 }

unisOltLaserOnTimeMaxVal OBJECT-TYPE
    SYNTAX      Integer32
    MAX-ACCESS  read-only
    STATUS      current
    DESCRIPTION
        "
        The upper limit of time which is confined to
        unisOltLaserOnTime.
        "
    ::= { unisEponOltMan 6 }

unisOltLaserOffTimeMinVal OBJECT-TYPE
    SYNTAX      Integer32
    MAX-ACCESS  read-only
    STATUS      current
    DESCRIPTION
        "
        The lower limit of time which is confined to
        unisOltLaserOffTime.
        "
    ::= { unisEponOltMan 7 }

unisOltLaserOffTimeMaxVal OBJECT-TYPE
    SYNTAX      Integer32
    MAX-ACCESS  read-only
    STATUS      current
    DESCRIPTION
        "
        The upper limit of time which is confined to
        unisOltLaserOffTime.
        "
    ::= { unisEponOltMan 8 }

unisOltDbaDiscoveryLengthMinVal OBJECT-TYPE
    SYNTAX      Integer32
    MAX-ACCESS  read-only
    STATUS      current
    DESCRIPTION
        "
        The lower limit of the discovery length which is confined to
        unisOltDbaDiscoveryLength.
        "
    ::= { unisEponOltMan 9 }

unisOltDbaDiscoveryLengthMaxVal OBJECT-TYPE
    SYNTAX      Integer32
    MAX-ACCESS  read-only
    STATUS      current
    DESCRIPTION
        "
        The upper limit of the discovery length which is confined to
        unisOltDbaDiscoveryLength.
        "
    ::= { unisEponOltMan 10 }

unisOltDbaDiscovryFrequencyMinVal OBJECT-TYPE
    SYNTAX      Integer32
    MAX-ACCESS  read-only
    STATUS      current
    DESCRIPTION
        "
        The lower limit of the discovery length which is confined to
        unisOltDbaDiscovryFrequency.
        "
    ::= { unisEponOltMan 11 }

unisOltDbaDiscovryFrequencyMaxVal OBJECT-TYPE
    SYNTAX      Integer32
    MAX-ACCESS  read-only
    STATUS      current
    DESCRIPTION
        "
        The upper limit of the discovery length which is confined to
        unisOltDbaDiscovryFrequency.
        "
    ::= { unisEponOltMan 12 }

unisOltDbaCycleLengthMinVal OBJECT-TYPE
    SYNTAX      Integer32
    MAX-ACCESS  read-only
    STATUS      current
    DESCRIPTION
        "
        The lower limit of the frames which is confined to
        unisOltDbaCycleLength.
        "
    ::= { unisEponOltMan 13 }

unisOltDbaCycleLengthMaxVal OBJECT-TYPE
    SYNTAX      Integer32
    MAX-ACCESS  read-only
    STATUS      current
    DESCRIPTION
        "
        The upper limit of the frames which is confined to
        unisOltDbaCycleLength.
        "
    ::= { unisEponOltMan 14 }

unisOltPortAlarmLlidMisMinVal OBJECT-TYPE
    SYNTAX      Integer32
    MAX-ACCESS  read-only
    STATUS      current
    DESCRIPTION
        "
        The lower limit of the frames which is confined to
        unisOltPortAlarmLlidMismatchThreshold.
        "
    ::= { unisEponOltMan 15 }

unisOltPortAlarmLlidMisMaxVal OBJECT-TYPE
    SYNTAX      Integer32
    MAX-ACCESS  read-only
    STATUS      current
    DESCRIPTION
        "
        The upper limit of the frames which is confined to
        unisOltPortAlarmLlidMismatchThreshold.
        "
    ::= { unisEponOltMan 16 }

unisOltPortAlarmBerMinVal OBJECT-TYPE
    SYNTAX      Integer32
    MAX-ACCESS  read-only
    STATUS      current
    DESCRIPTION
        "
        The lower limit of threshold which is confined to
        unisOltPortAlarmBerThreshold.
        "
    ::= { unisEponOltMan 17 }

unisOltPortAlarmBerMaxVal OBJECT-TYPE
    SYNTAX      Integer32
    MAX-ACCESS  read-only
    STATUS      current
    DESCRIPTION
        "
        The upper limit of threshold which is confined to
        unisOltPortAlarmBerThreshold.
        "
    ::= { unisEponOltMan 18 }

unisOltPortAlarmFerMinVal OBJECT-TYPE
    SYNTAX      Integer32
    MAX-ACCESS  read-only
    STATUS      current
    DESCRIPTION
        "
        The lower limit of threshold which is confined to
        unisOltPortAlarmFerThreshold.
        "
    ::= { unisEponOltMan 19 }

unisOltPortAlarmFerMaxVal OBJECT-TYPE
    SYNTAX      Integer32
    MAX-ACCESS  read-only
    STATUS      current
    DESCRIPTION
        "
        The upper limit of threshold which is confined to
        unisOltPortAlarmFerThreshold.
        "
    ::= { unisEponOltMan 20 }

--
-- unisOnuSilentTable
--

unisOnuSilentTable OBJECT-TYPE
    SYNTAX      SEQUENCE OF UnisOnuSilentEntry
    MAX-ACCESS  not-accessible
    STATUS      current
    DESCRIPTION
        "
        This table is used for getting silent ONU information of OLT.
        "
    ::= { unisEponOltMan 21 }

unisOnuSilentEntry OBJECT-TYPE
    SYNTAX      UnisOnuSilentEntry
    MAX-ACCESS  not-accessible
    STATUS      current
    DESCRIPTION
        "
        The entry of the table unisOnuSilentTable.
        "
    INDEX
        {
            ifIndex,
            unisOnuSilentMacAddr
        }
    ::= { unisOnuSilentTable 1 }

UnisOnuSilentEntry ::= SEQUENCE
    {
        unisOnuSilentMacAddr    MacAddress,
        unisOnuSilentTime       Integer32
    }

unisOnuSilentMacAddr OBJECT-TYPE
    SYNTAX      MacAddress
    MAX-ACCESS  not-accessible
    STATUS      current
    DESCRIPTION
        "
        The MAC address of silent ONUs in OLT.
        "
    ::= { unisOnuSilentEntry 1 }

unisOnuSilentTime OBJECT-TYPE
    SYNTAX      Integer32
    MAX-ACCESS  read-only
    STATUS      current
    DESCRIPTION
        "
        The aging time of a silent ONU.
        "
    ::= { unisOnuSilentEntry 2 }

--
-- unisOltUsingOnuTable
--

unisOltUsingOnuTable OBJECT-TYPE
    SYNTAX      SEQUENCE OF UnisOltUsingOnuEntry
    MAX-ACCESS  not-accessible
    STATUS      current
    DESCRIPTION
        "
        The table containing configurations to manage ONU interface(s)
        based on OLT interface.
        "
    ::= { unisEponOltMan 22 }

unisOltUsingOnuEntry OBJECT-TYPE
    SYNTAX      UnisOltUsingOnuEntry
    MAX-ACCESS  not-accessible
    STATUS      current
    DESCRIPTION
        "
        The entry of the table unisOltUsingOnuTable.
        "
    INDEX
        {
            ifIndex,
            unisOltUsingOnuNum
        }
    ::= { unisOltUsingOnuTable 1 }

UnisOltUsingOnuEntry  ::= SEQUENCE
    {
        unisOltUsingOnuNum          Integer32,
        unisOltUsingOnuIfIndex      Integer32,
        unisOltUsingOnuRowStatus    RowStatus
    }

unisOltUsingOnuNum OBJECT-TYPE
    SYNTAX      Integer32(1..128)
    MAX-ACCESS  not-accessible
    STATUS      current
    DESCRIPTION
        "
        The ONU interface number.  This value is used to specify the ONU interface
        which the user wants to configure for an OLT interface.
        "
    ::= { unisOltUsingOnuEntry 1 }

unisOltUsingOnuIfIndex OBJECT-TYPE
    SYNTAX      Integer32
    MAX-ACCESS  read-only
    STATUS      current
    DESCRIPTION
        "
        The ifIndex of the ONU interface.
        "
    ::= { unisOltUsingOnuEntry 2 }

unisOltUsingOnuRowStatus OBJECT-TYPE
    SYNTAX      RowStatus
    MAX-ACCESS  read-create
    STATUS      current
    DESCRIPTION
        "
        This object is responsible for managing the creation,
        deletion and modification of rows, which supports active
        status and CreatAndGo, destroy operation.
        "
    ::= { unisOltUsingOnuEntry 3 }

--
-- unisOnuSilentLoidTable
--

unisOnuSilentLoidTable OBJECT-TYPE
    SYNTAX      SEQUENCE OF UnisOnuSilentLoidEntry
    MAX-ACCESS  not-accessible
    STATUS      current
    DESCRIPTION
        "
        This table is used for getting silent ONU's LOID information of an OLT.
        "
    ::= { unisEponOltMan 23 }

unisOnuSilentLoidEntry OBJECT-TYPE
    SYNTAX      UnisOnuSilentLoidEntry
    MAX-ACCESS  not-accessible
    STATUS      current
    DESCRIPTION
        "
        The entry of the table unisOnuSilentLoidTable.
        "
    INDEX
        {
            ifIndex,
            unisOnuSilentLoid
        }
    ::= { unisOnuSilentLoidTable 1 }

UnisOnuSilentLoidEntry ::= SEQUENCE
    {
        unisOnuSilentLoid       OCTET STRING,
        unisOnuSilentLoidTime   Integer32
    }

unisOnuSilentLoid OBJECT-TYPE
    SYNTAX      OCTET STRING(SIZE(1..24))
    MAX-ACCESS  not-accessible
    STATUS      current
    DESCRIPTION
        "
        The LOID of a silent ONU in an OLT.
        "
    ::= { unisOnuSilentLoidEntry 1 }

unisOnuSilentLoidTime OBJECT-TYPE
    SYNTAX      Integer32
    MAX-ACCESS  read-only
    STATUS      current
    DESCRIPTION
        "
        The aging time of a silent ONU.
        "
    ::= { unisOnuSilentLoidEntry 2 }

--
-- unisOltTransceiverTxPowerTable
--

unisOltTransceiverTxPowerTable OBJECT-TYPE
    SYNTAX      SEQUENCE OF UnisOltTransceiverTxPowerEntry
    MAX-ACCESS  not-accessible
    STATUS      current
    DESCRIPTION
        "
        This table is used for setting ONU's Tx power on an OLT.
        "
    ::= { unisEponOltMan 24 }

unisOltTransceiverTxPowerEntry OBJECT-TYPE
    SYNTAX      UnisOltTransceiverTxPowerEntry
    MAX-ACCESS  not-accessible
    STATUS      current
    DESCRIPTION
        "
        The entry of the table unisOltTransceiverTxPowerTable.
        "
    INDEX
        {
            ifIndex
        }
    ::= { unisOltTransceiverTxPowerTable 1 }

UnisOltTransceiverTxPowerEntry ::= SEQUENCE
    {
        unisOltTransTxPwrTransId             INTEGER,
        unisOltTransTxPwrOffTime             Unsigned32,
        unisOltTransTxPwrIsAllOnu            TruthValue,
        unisOltTransTxPwrOnuIfList           OCTET STRING
    }

unisOltTransTxPwrTransId OBJECT-TYPE
    SYNTAX      INTEGER
        {
            main(0),
            standby(1),
            all(2)
        }
    MAX-ACCESS  read-write
    STATUS      current
    DESCRIPTION
        "
        The transceiver ID of an ONU in an OLT.
        "
    ::= { unisOltTransceiverTxPowerEntry 1 }

unisOltTransTxPwrOffTime OBJECT-TYPE
    SYNTAX      Unsigned32
    MAX-ACCESS  read-write
    STATUS      current
    DESCRIPTION
        "
        The turnoff time of the transceiver Tx power.
        "
    ::= { unisOltTransceiverTxPowerEntry 2 }

unisOltTransTxPwrIsAllOnu OBJECT-TYPE
    SYNTAX      TruthValue
    MAX-ACCESS  read-write
    STATUS      current
    DESCRIPTION
        "
        Setting all ONUs' transceiver Tx power or not.
        "
    ::= { unisOltTransceiverTxPowerEntry 3 }

unisOltTransTxPwrOnuIfList OBJECT-TYPE
    SYNTAX      OCTET STRING(SIZE(0..20))
    MAX-ACCESS  read-write
    STATUS      current
    DESCRIPTION
        "
        ONUs' ifIndex for which the transceiver Tx power is to be set.
        "
    ::= { unisOltTransceiverTxPowerEntry 4 }

unisEponOnuMan OBJECT IDENTIFIER ::= { unisEponMibObjects 5 }

--
-- unisOnuSysManTable
--

unisOnuSysManTable OBJECT-TYPE
    SYNTAX      SEQUENCE OF UnisOnuSysManEntry
    MAX-ACCESS  not-accessible
    STATUS      current
    DESCRIPTION
        "
        This table implements the following functions for ONUs:
        1. Encrypting all downstream/upstream and
        downstream directions traffic destined to and
        originated from a specific LLID
        (ONU in current implementation).
        2. Restart a process of ONU authentication, using
        the OLT (IEEE 802.1x) authenticator.
        "
    ::= { unisEponOnuMan 1 }

unisOnuSysManEntry OBJECT-TYPE
    SYNTAX      UnisOnuSysManEntry
    MAX-ACCESS  not-accessible
    STATUS      current
    DESCRIPTION
        "
        The entry of the table unisOnuSysManTable.
        "
    INDEX
        {
            ifIndex
        }
    ::= { unisOnuSysManTable 1 }

UnisOnuSysManEntry ::= SEQUENCE
    {
        unisOnuEncryptMan                 INTEGER,
        unisOnuReAuthorize                INTEGER,
        unisOnuMulticastFilterStatus      TruthValue,
        unisOnuDbaReportQueueSetNumber    Integer32,
        unisOnuRemoteFecStatus            INTEGER,
        unisOnuPortBerStatus              INTEGER,
        unisOnuReset                      INTEGER,
        unisOnuMulticastControlMode       INTEGER,
        unisOnuAccessVlan                 Integer32,
        unisOnuEncryptKey                 DisplayString,
        unisOnuUniUpDownTrapStatus        TruthValue,
        unisOnuFecStatus                  INTEGER,
        unisOnuMcastCtrlHostAgingTime     Integer32,
        unisOnuMulticastFastLeaveEnable   TruthValue,
        unisOnuPortIsolateEnable          TruthValue,
        unisOnuMacAddressTimer            Unsigned32
    }

unisOnuEncryptMan OBJECT-TYPE
    SYNTAX      INTEGER
        {
            off(1),
            downlink(2),
            updownlink(3)
        }
    MAX-ACCESS  read-write
    STATUS      current
    DESCRIPTION
        "
        Start encrypting all downstream/upstream and downstream
        directions traffic destined to and originated from a
        specific LLID (ONU in current implementation).  ONU
        registration encryption key is used as an initial value.
        If the encryption key was updated after ONU
        registration, the last updated key is used.
        off(1):        - Stop encrypting.
        downlink(2):   - Start encrypting all downstream
        directions traffic.
        updownlink(3): - Start encrypting all downstream/upstream
        directions traffic.
        "
    DEFVAL { downlink }
    ::= { unisOnuSysManEntry 1 }

unisOnuReAuthorize OBJECT-TYPE
    SYNTAX      INTEGER
        {
            reAuthorize(1)
        }
    MAX-ACCESS  read-write
    STATUS      current
    DESCRIPTION
        "
        Restart a process of ONU authentication.
        If 802.1x authentication is enabled, the OLT
        (IEEE 802.1x) authenticator is applied.
        Otherwise, use the default authentication.
        Until the reauthentication succeeds, the ONU remains
        its previous authorization mode.
        The reauthentication process includes a new
        authentication request sent to the authentication server.
        "
    ::= { unisOnuSysManEntry 2 }

unisOnuMulticastFilterStatus OBJECT-TYPE
    SYNTAX      TruthValue
    MAX-ACCESS  read-write
    STATUS      current
    DESCRIPTION
        "
        true(1)  - Multicast-Filter enable on ONU.
        false(2) - Multicast-Filter disable on ONU.
        "
    DEFVAL { false }
    ::= { unisOnuSysManEntry 3 }

unisOnuDbaReportQueueSetNumber OBJECT-TYPE
    SYNTAX      Integer32
    MAX-ACCESS  read-write
    STATUS      current
    DESCRIPTION
        "
        The number of queue sets reported in MPCP report frames.
        "
    DEFVAL { 2 }
    ::= { unisOnuSysManEntry 4 }

unisOnuRemoteFecStatus OBJECT-TYPE
    SYNTAX      INTEGER
        {
            enable(1),
            disable(2)
        }
    MAX-ACCESS  read-write
    STATUS      current
    DESCRIPTION
        "
        Value that indicates status of the 1000BASE-PX PHY
        optional FEC Sublayer for forward error correction
        see [802.3ah] clause 65.2.
        enable - enable remote forward error correction.
        disable - disable remote forward error correction.
        "
    DEFVAL { disable }
    ::= { unisOnuSysManEntry 5 }

unisOnuPortBerStatus OBJECT-TYPE
    SYNTAX      INTEGER
        {
            enable(1),
            disable(2)
        }
    MAX-ACCESS  read-write
    STATUS      current
    DESCRIPTION
        "
        enable - enable ONU port bit error rate alarm.
        disable - disable ONU port bit error rate alarm.
        "
    DEFVAL { enable }
    ::= { unisOnuSysManEntry 6 }

unisOnuReset OBJECT-TYPE
    SYNTAX      INTEGER
        {
            reset(1)
        }
    MAX-ACCESS  read-write
    STATUS      current
    DESCRIPTION
        "
        Reboot ONU.
        "
    ::= { unisOnuSysManEntry 7 }

unisOnuMulticastControlMode OBJECT-TYPE
    SYNTAX      INTEGER
        {
            igmpsnooping(1),
            multicastcontrol(2)
        }
    MAX-ACCESS  read-write
    STATUS      current
    DESCRIPTION
        "
        igmpsnooping - the traditional IGMP snooping mode.
        multicastcontrol - the specific multicast control mode.
        "
    DEFVAL { igmpsnooping }
    ::= { unisOnuSysManEntry 8 }

unisOnuAccessVlan OBJECT-TYPE
    SYNTAX      Integer32
    MAX-ACCESS  read-write
    STATUS      current
    DESCRIPTION
        "
        The VLAN ID assigned to untagged frames received on ONU.
        "
    ::= { unisOnuSysManEntry 9 }

unisOnuEncryptKey OBJECT-TYPE
    SYNTAX      DisplayString(SIZE(0..255))
    MAX-ACCESS  read-write
    STATUS      current
    DESCRIPTION
        "
        The encryption key, used to encrypt all downstream
        traffic destined to and/or upstream traffic originating
        from a specific ONU.  It is a zero length, or MD5 hashed string,
        by default, the string is empty.
        "
    ::= { unisOnuSysManEntry 10 }

unisOnuUniUpDownTrapStatus OBJECT-TYPE
    SYNTAX      TruthValue
    MAX-ACCESS  read-write
    STATUS      current
    DESCRIPTION
        "
        true - A notification will be sent when UNI link status is change.
        false - Device will not sent notification when UNI link status is
        change.
        "
    DEFVAL { false }
    ::= { unisOnuSysManEntry 11 }

unisOnuFecStatus OBJECT-TYPE
    SYNTAX      INTEGER
        {
            enable(1),
            disable(2)
        }
    MAX-ACCESS  read-write
    STATUS      current
    DESCRIPTION
        "
        Value that indicates status of the 1000BASE-PX PHY
        optional FEC Sublayer for forward error correction
        (include remote onu and local OLT)
        see [802.3ah] clause 65.2
        enable - enable forward error correction.
        disable - disable forward error correction.
        "
    DEFVAL { disable }
    ::= { unisOnuSysManEntry 12 }

unisOnuMcastCtrlHostAgingTime OBJECT-TYPE
    SYNTAX      Integer32
    MAX-ACCESS  read-write
    STATUS      current
    DESCRIPTION
        "
        The host aging time of multicast control mode on ONU,
        ranging from 200 to 1000, measured in seconds.
        "
    ::= { unisOnuSysManEntry 13 }

unisOnuMulticastFastLeaveEnable OBJECT-TYPE
    SYNTAX     TruthValue
    MAX-ACCESS read-write
    STATUS     current
    DESCRIPTION
        "
        true(1)  - Enable multicast fast leave attribute on all ethernet UNIs of the ONU.
        false(2) - Disable multicast fast leave attribute on all ethernet UNIs of the ONU.
        "
    ::= { unisOnuSysManEntry 14 }

unisOnuPortIsolateEnable OBJECT-TYPE
    SYNTAX     TruthValue
    MAX-ACCESS read-write
    STATUS     current
    DESCRIPTION
        "
        true(1)  - Enable port isolate setting on all ethernet UNIs of the ONU.
        false(2) - Disable port isolate setting on all ethernet UNIs of the ONU.
        "
    ::= { unisOnuSysManEntry 15 }

unisOnuMacAddressTimer OBJECT-TYPE
    SYNTAX     Unsigned32
    MAX-ACCESS read-write
    STATUS     current
    DESCRIPTION
        "
        no-aging(0)  - Disable aging.
        others       - Aging time(seconds).
        "
    DEFVAL { 300 }
    ::= { unisOnuSysManEntry 16 }

--
-- unisOnuLinkTestTable
--

unisOnuLinkTestTable OBJECT-TYPE
    SYNTAX      SEQUENCE OF UnisOnuLinkTestEntry
    MAX-ACCESS  not-accessible
    STATUS      current
    DESCRIPTION
        "
        LLID link test applying to the ONU only including delay
        measurement option.  The command tests a link to a single
        LLID over a period of time or once, using a variable
        number of measurement frames.  The length of the measurement
        frames is also parameterized.  The test uses a loopback
        mode of the ONU to return each measurement frame,
        loopback activation is done using randomly patterned
        OAM Protocol Data Unit(PDU) frames.
        "
    ::= { unisEponOnuMan 2 }

unisOnuLinkTestEntry OBJECT-TYPE
    SYNTAX      UnisOnuLinkTestEntry
    MAX-ACCESS  not-accessible
    STATUS      current
    DESCRIPTION
        "
        The entry of unisOnuLinkTestEntry.
        "
    INDEX
        {
            ifIndex
        }
    ::= { unisOnuLinkTestTable 1 }

UnisOnuLinkTestEntry ::= SEQUENCE
    {
        unisOnuLinkTestFrameNum                Integer32,
        unisOnuLinkTestFrameSize               Integer32,
        unisOnuLinkTestDelay                   TruthValue,
        unisOnuLinkTestVlanTag                 TruthValue,
        unisOnuLinkTestVlanPriority            Integer32,
        unisOnuLinkTestVlanTagID               Integer32,
        unisOnuLinkTestResultSentFrameNum      Integer32,
        unisOnuLinkTestResultRetFrameNum       Integer32,
        unisOnuLinkTestResultRetErrFrameNum    Integer32,
        unisOnuLinkTestResultMinDelay          Integer32,
        unisOnuLinkTestResultMeanDelay         Integer32,
        unisOnuLinkTestResultMaxDelay          Integer32
    }

unisOnuLinkTestFrameNum OBJECT-TYPE
    SYNTAX      Integer32
    MAX-ACCESS  read-write
    STATUS      current
    DESCRIPTION
        "
        Exact number of measurement frames.
        "
    DEFVAL { 20 }
    ::= { unisOnuLinkTestEntry 1 }

unisOnuLinkTestFrameSize OBJECT-TYPE
    SYNTAX      Integer32(60..1514)
    MAX-ACCESS  read-write
    STATUS      current
    DESCRIPTION
        "
        Measurement frames data size, measured in bytes.
        Not including Preamble, SFD, VLAN tag, and FCS.
        Frame size minimum value is 56 - if VLAN tag is
        enabled('VLAN enable' field is set to ENABLE),
        and 60 - if VLAN tag is disabled.  The actual
        measurement frames sent to the PON are always
        minimum 60 bytes long.  When VLAN tag is enabled,
        the actual measurement frames size including
        FCS may reach (1514+4+4=)1522 bytes.
        60(60 is VLAN tag disabled) - 1514 .
        "
    DEFVAL { 1000 }
    ::= { unisOnuLinkTestEntry 2 }

unisOnuLinkTestDelay OBJECT-TYPE
    SYNTAX      TruthValue
    MAX-ACCESS  read-write
    STATUS      current
    DESCRIPTION
        "
        true:Link test includes delay measurement,
        which corresponds to the difference between sent
        and received times(including granting delay and
        firmware processing time overheads).
        false:Link test not includes a delay measurement.
        "
    DEFVAL { true }
    ::= { unisOnuLinkTestEntry 3 }

unisOnuLinkTestVlanTag OBJECT-TYPE
    SYNTAX      TruthValue
    MAX-ACCESS  read-write
    STATUS      current
    DESCRIPTION
        "
        true:Enable VLAN tag in link test frames.
        false:Link test not includes frames with VLAN tag.
        "
    DEFVAL { true }
    ::= { unisOnuLinkTestEntry 4 }

unisOnuLinkTestVlanPriority OBJECT-TYPE
    SYNTAX      Integer32(0..7)
    MAX-ACCESS  read-write
    STATUS      current
    DESCRIPTION
        "
        VLAN priority: 0-7.
        "
    DEFVAL { 2 }
    ::= { unisOnuLinkTestEntry 5 }

unisOnuLinkTestVlanTagID OBJECT-TYPE
    SYNTAX      Integer32(1..4094)
    MAX-ACCESS  read-write
    STATUS      current
    DESCRIPTION
        "
        VLAN ID: 1-4094.
        "
    DEFVAL { 1 }
    ::= { unisOnuLinkTestEntry 6 }

unisOnuLinkTestResultSentFrameNum OBJECT-TYPE
    SYNTAX      Integer32
    MAX-ACCESS  read-only
    STATUS      current
    DESCRIPTION
        "
        The total number of frames sent during the link test process.
        "
    ::= { unisOnuLinkTestEntry 7 }

unisOnuLinkTestResultRetFrameNum OBJECT-TYPE
    SYNTAX      Integer32
    MAX-ACCESS  read-only
    STATUS      current
    DESCRIPTION
        "
        The total number of frames return back during the link test process.
        "
    ::= { unisOnuLinkTestEntry 8 }

unisOnuLinkTestResultRetErrFrameNum OBJECT-TYPE
    SYNTAX      Integer32
    MAX-ACCESS  read-only
    STATUS      current
    DESCRIPTION
        "
        The total number of error frames return back during the
        link test process.
        "
    ::= { unisOnuLinkTestEntry 9 }

unisOnuLinkTestResultMinDelay OBJECT-TYPE
    SYNTAX      Integer32
    MAX-ACCESS  read-only
    STATUS      current
    DESCRIPTION
        "
        The minimum delay time in TQ units, which corresponds
        to the difference between sent and received times
        (including granting delay and firmware processing time
        overheads).  It's invalid if the field
        'unisOnuLinkTestDelay' is set to be true.
        "
    ::= { unisOnuLinkTestEntry 10 }

unisOnuLinkTestResultMeanDelay OBJECT-TYPE
    SYNTAX      Integer32
    MAX-ACCESS  read-only
    STATUS      current
    DESCRIPTION
        "
        The average delay time in TQ units, which corresponds
        to the difference between sent and received times
        (including granting delay and firmware processing time
        overheads).  It's invalid if the field
        'unisOnuLinkTestDelay' is set to be true.
        "
    ::= { unisOnuLinkTestEntry 11 }

unisOnuLinkTestResultMaxDelay OBJECT-TYPE
    SYNTAX      Integer32
    MAX-ACCESS  read-only
    STATUS      current
    DESCRIPTION
        "
        The maximum delay time in TQ units, which corresponds
        to the difference between sent and received times
        (including granting delay and firmware processing time
        overheads).  It's invalid if the field
        'unisOnuLinkTestDelay' is set to be true.
        "
    ::= { unisOnuLinkTestEntry 12 }

--
-- unisOnuBandWidthTable
--

unisOnuBandWidthTable OBJECT-TYPE
    SYNTAX      SEQUENCE OF UnisOnuBandWidthEntry
    MAX-ACCESS  not-accessible
    STATUS      current
    DESCRIPTION
        "
        Set bandwidth policy parameters(restrictions)for a LLID
        (only for the ONU).  Default policies are set to disable.
        Policy parameters will be erased upon LLID network disconnection.
        "
    ::= { unisEponOnuMan 3 }

unisOnuBandWidthEntry OBJECT-TYPE
    SYNTAX      UnisOnuBandWidthEntry
    MAX-ACCESS  not-accessible
    STATUS      current
    DESCRIPTION
        "
        The entry of table unisOnuBandWidthTable.
        "
    INDEX
        {
            ifIndex
        }
    ::= { unisOnuBandWidthTable 1 }

UnisOnuBandWidthEntry ::= SEQUENCE
    {
        unisOnuDownStreamBandWidthPolicy      TruthValue,
        unisOnuDownStreamMaxBandWidth         Integer32,
        unisOnuDownStreamMaxBurstSize         Integer32,
        unisOnuDownStreamHighPriorityFirst    TruthValue,
        unisOnuDownStreamShortFrameFirst      TruthValue,
        unisOnuP2PBandWidthPolicy             TruthValue,
        unisOnuP2PMaxBandWidth                Integer32,
        unisOnuP2PMaxBurstSize                Integer32,
        unisOnuP2PHighPriorityFirst           TruthValue,
        unisOnuP2PShortFrameFirst             TruthValue
    }

unisOnuDownStreamBandWidthPolicy OBJECT-TYPE
    SYNTAX      TruthValue
    MAX-ACCESS  read-write
    STATUS      current
    DESCRIPTION
        "
        true:Enable static bandwidth configuration policing.
        false:Disable static bandwidth configuration policing.
        "
    DEFVAL { false }
    ::= { unisOnuBandWidthEntry 1 }

unisOnuDownStreamMaxBandWidth OBJECT-TYPE
    SYNTAX      Integer32
    MAX-ACCESS  read-write
    STATUS      current
    DESCRIPTION
        "
        Maximum bandwidth allowed for the ONU,
        measured in Kbits/Sec.
        "
    DEFVAL { 1000000 }
    ::= { unisOnuBandWidthEntry 2 }

unisOnuDownStreamMaxBurstSize OBJECT-TYPE
    SYNTAX      Integer32(0..8388480)
    MAX-ACCESS  read-write
    STATUS      current
    DESCRIPTION
        "
        Maximal number of bytes in a burst.
        The value is truncated to the nearest
        smaller 128 bytes multiple value,
        measured in bytes.
        "
    DEFVAL { 8388480 }
    ::= { unisOnuBandWidthEntry 3 }

unisOnuDownStreamHighPriorityFirst OBJECT-TYPE
    SYNTAX      TruthValue
    MAX-ACCESS  read-write
    STATUS      current
    DESCRIPTION
        "
        true:Enable high priority frames preference.
        false:Disable high priority frames preference.
        "
    DEFVAL { false }
    ::= { unisOnuBandWidthEntry 4 }

unisOnuDownStreamShortFrameFirst OBJECT-TYPE
    SYNTAX      TruthValue
    MAX-ACCESS  read-write
    STATUS      current
    DESCRIPTION
        "
        true:Enable short frames preference.
        false:Disable short frames preference.
        "
    DEFVAL { false }
    ::= { unisOnuBandWidthEntry 5 }

unisOnuP2PBandWidthPolicy OBJECT-TYPE
    SYNTAX      TruthValue
    MAX-ACCESS  read-write
    STATUS      current
    DESCRIPTION
        "
        true:Enable static bandwidth configuration policing.
        false:Disable static bandwidth configuration policing.
        "
    DEFVAL { false }
    ::= { unisOnuBandWidthEntry 6 }

unisOnuP2PMaxBandWidth OBJECT-TYPE
    SYNTAX      Integer32(0..1000000)
    MAX-ACCESS  read-write
    STATUS      current
    DESCRIPTION
        "
        Maximum bandwidth allowed for the ONU,
        measured in Kbits/Sec.
        "
    DEFVAL { 1000000 }
    ::= { unisOnuBandWidthEntry 7 }

unisOnuP2PMaxBurstSize OBJECT-TYPE
    SYNTAX      Integer32(0..8388480)
    MAX-ACCESS  read-write
    STATUS      current
    DESCRIPTION
        "
        Maximal number of bytes in a burst.
        The value is truncated to the nearest
        smaller 128 bytes multiple value,
        measured in bytes.
        "
    DEFVAL { 8388480 }
    ::= { unisOnuBandWidthEntry 8 }

unisOnuP2PHighPriorityFirst OBJECT-TYPE
    SYNTAX      TruthValue
    MAX-ACCESS  read-write
    STATUS      current
    DESCRIPTION
        "
        true:Enable high priority frames preference.
        false:Disable high priority frames preference.
        "
    DEFVAL { false }
    ::= { unisOnuBandWidthEntry 9 }

unisOnuP2PShortFrameFirst OBJECT-TYPE
    SYNTAX      TruthValue
    MAX-ACCESS  read-write
    STATUS      current
    DESCRIPTION
        "
        true:Enable short frames preference.
        false:Disable short frames preference.
        "
    DEFVAL { false }
    ::= { unisOnuBandWidthEntry 10 }

--
-- unisOnuSlaManTable
--

unisOnuSlaManTable OBJECT-TYPE
    SYNTAX      SEQUENCE OF UnisOnuSlaManEntry
    MAX-ACCESS  not-accessible
    STATUS      current
    DESCRIPTION
        "
        Two types of DBA algorithm are supported in the ONU.
        The internal SLA based algorithm is always activated.
        This table defines the primary parameter about the
        internal SLA algorithm.
        "
    ::= { unisEponOnuMan 4 }

unisOnuSlaManEntry OBJECT-TYPE
    SYNTAX      UnisOnuSlaManEntry
    MAX-ACCESS  not-accessible
    STATUS      current
    DESCRIPTION
        "
        The entry of table unisOnuSlaManTable.
        "
    INDEX
        {
            ifIndex
        }
    ::= { unisOnuSlaManTable 1 }

UnisOnuSlaManEntry ::= SEQUENCE
    {
        unisOnuSlaMaxBandWidth        Integer32,
        unisOnuSlaMinBandWidth        Integer32,
        unisOnuSlaBandWidthStepVal    Integer32,
        unisOnuSlaDelay               INTEGER,
        unisOnuSlaFixedBandWidth      Integer32,
        unisOnuSlaPriorityClass       Integer32,
        unisOnuSlaFixedPacketSize     Integer32,
        unisOnuSlaWrrBandWidth        Integer32
    }

unisOnuSlaMaxBandWidth OBJECT-TYPE
    SYNTAX      Integer32
    MAX-ACCESS  read-write
    STATUS      current
    DESCRIPTION
        "
        Maximum bandwidth - measured in Kbit/s.
        The value of this object should be the multiple of
        the value of unisOnuSlaBandWidthStepVal.
        The minimum bandwidth should not be larger than the maximum
        bandwidth.
        "
    ::= { unisOnuSlaManEntry 1 }

unisOnuSlaMinBandWidth OBJECT-TYPE
    SYNTAX      Integer32
    MAX-ACCESS  read-write
    STATUS      current
    DESCRIPTION
        "
        Minimum bandwidth - measured in Kbit/s.
        The value of this object should be the multiple of
        the value of unisOnuSlaBandWidthStepVal.
        The maximum bandwidth should be larger than the minimum bandwidth.
        "
    ::= { unisOnuSlaManEntry 2 }

unisOnuSlaBandWidthStepVal OBJECT-TYPE
    SYNTAX      Integer32
    MAX-ACCESS  read-only
    STATUS      current
    DESCRIPTION
        "
        Granularity of bandwidth - measured in Kbit/s.
        The value of unisOnuSlaMaxBandWidth and unisOnuSlaMinBandWidth should
        be the multiple of the value of this object.
        "
    ::= { unisOnuSlaManEntry 3 }

unisOnuSlaDelay OBJECT-TYPE
    SYNTAX      INTEGER
        {
            low(1),
            high(2)
        }
    MAX-ACCESS  read-write
    STATUS      current
    DESCRIPTION
        "
        low  - low delay.
        high - high delay.
        The delay constraint of a specific ONU.  Set to high may improve the
        bandwidth usage at the cost of delay.
        "
    DEFVAL { low }
    ::= { unisOnuSlaManEntry 4 }

unisOnuSlaFixedBandWidth OBJECT-TYPE
    SYNTAX      Integer32
    MAX-ACCESS  read-write
    STATUS      current
    DESCRIPTION
        "
        Fixed bandwidth - measured in Kbit/s.
        The value of this object should be the multiple of
        the value of unisOnuSlaBandWidthStepVal.
        "
    ::= { unisOnuSlaManEntry 5 }

unisOnuSlaPriorityClass OBJECT-TYPE
    SYNTAX      Integer32
    MAX-ACCESS  read-write
    STATUS      current
    DESCRIPTION
        "
        Precedence of this flow over others in case of contention.
        0 is the lowest priority and 7 is the highest priority.
        "
    DEFVAL { 0 }
    ::= { unisOnuSlaManEntry 6 }

unisOnuSlaFixedPacketSize OBJECT-TYPE
    SYNTAX      Integer32
    MAX-ACCESS  read-write
    STATUS      current
    DESCRIPTION
        "
        Fixed packet size - measured in byte.
        The value of this object should be valid when unisOnuSlaFixedBandWidth is configured.
        "
    ::= { unisOnuSlaManEntry 7 }

unisOnuSlaWrrBandWidth OBJECT-TYPE
    SYNTAX      Integer32
    MAX-ACCESS  read-write
    STATUS      current
    DESCRIPTION
        "
        The WRR weight will be used to compute the remaining bandwidth
        allocation after each CIR has been guaranteed.
        "
    DEFVAL { 1 }
    ::= { unisOnuSlaManEntry 8 }
--
-- unisOnuInfoTable
--

unisOnuInfoTable OBJECT-TYPE
    SYNTAX      SEQUENCE OF UnisOnuInfoEntry
    MAX-ACCESS  not-accessible
    STATUS      current
    DESCRIPTION
        "
        Primary status of the specified ONU.
        There will be one row in this table for each
        information in the system.
        (1)Software and hardware versions of the specified ONU
        (unisOnuHardMajorVersion, unisOnuHardMinorVersion,
        unisOnuUniMacType)
        (2)Several physical capabilities of the ONU.
        (unisOnuLaserOnTime, unisOnuLaserOffTime,
        unisOnuGrantFifoDep.)
        (3)The operation(activation) status of the ONU.
        (unisOnuWorkMode)
        "
    ::= { unisEponOnuMan 5 }

unisOnuInfoEntry OBJECT-TYPE
    SYNTAX      UnisOnuInfoEntry
    MAX-ACCESS  not-accessible
    STATUS      current
    DESCRIPTION
        "
        The entry of the unisOnuInfoTable.
        "
    INDEX
        {
            ifIndex
        }
    ::= { unisOnuInfoTable 1 }

UnisOnuInfoEntry ::= SEQUENCE
    {
        unisOnuHardMajorVersion    OCTET STRING,
        unisOnuHardMinorVersion    OCTET STRING,
        unisOnuSoftwareVersion     OCTET STRING,
        unisOnuUniMacType          INTEGER,
        unisOnuLaserOnTime         Integer32,
        unisOnuLaserOffTime        Integer32,
        unisOnuGrantFifoDep        Integer32,
        unisOnuWorkMode            INTEGER,
        unisOnuPCBVersion          OCTET STRING,
        unisOnuRtt                 Unsigned32,
        unisOnuEEPROMVersion       OCTET STRING,
        unisOnuRegType             OCTET STRING,
        unisOnuHostType            OCTET STRING,
        unisOnuDistance            Integer32,
        unisOnuLlid                Integer32,
        unisOnuVendorId            OCTET STRING,
        unisOnuFirmwareVersion     OCTET STRING,
        unisOnuOpticalPowerReceivedByOlt  Integer32,
        unisOnuInfoMac             MacAddress,
        unisOnuInfoLoid            OCTET STRING
    }

unisOnuHardMajorVersion OBJECT-TYPE
    SYNTAX      OCTET STRING
    MAX-ACCESS  read-only
    STATUS      current
    DESCRIPTION
        "
        ONU hardware major version.  If the object length is
        zero, it means the version is unknown.
        "
    ::= { unisOnuInfoEntry 1 }

unisOnuHardMinorVersion OBJECT-TYPE
    SYNTAX      OCTET STRING
    MAX-ACCESS  read-only
    STATUS      current
    DESCRIPTION
        "
        ONU hardware minor version.  If the object length is
        zero, it means the version is unknown.
        "
    ::= { unisOnuInfoEntry 2 }

unisOnuSoftwareVersion OBJECT-TYPE
    SYNTAX      OCTET STRING
    MAX-ACCESS  read-only
    STATUS      current
    DESCRIPTION
        "
        ONU software version.
        "
    ::= { unisOnuInfoEntry 3 }

unisOnuUniMacType OBJECT-TYPE
    SYNTAX      INTEGER
        {
            other(1),
            mii(2),
            gmii(3),
            tbi(4)
        }
    MAX-ACCESS  read-only
    STATUS      current
    DESCRIPTION
        "
        ONU User Network Interface(UNI) port MAC type.
        "
    ::= { unisOnuInfoEntry 4 }

unisOnuLaserOnTime OBJECT-TYPE
    SYNTAX      Integer32
    MAX-ACCESS  read-only
    STATUS      current
    DESCRIPTION
        "
        The ONU laser on time measured in TQ units.  If the object value is
        0x7FFFFFFF, it means unisOnuLaserOnTime is unknown.
        "
    ::= { unisOnuInfoEntry 5 }

unisOnuLaserOffTime OBJECT-TYPE
    SYNTAX      Integer32
    MAX-ACCESS  read-only
    STATUS      current
    DESCRIPTION
        "
        The ONU laser off time measured in TQ units.  If the object value is
        0x7FFFFFFF, it means unisOnuLaserOffTime is unknown.
        "
    ::= { unisOnuInfoEntry 6 }

unisOnuGrantFifoDep OBJECT-TYPE
    SYNTAX      Integer32(1..255|2147483647)
    MAX-ACCESS  read-only
    STATUS      current
    DESCRIPTION
        "
        Maximal number of grant records an ONU can store,
        relevant to ONU only.
        range: 1 - 255.
        0x7FFFFFFF: unknown value.
        "
    ::= { unisOnuInfoEntry 7 }

unisOnuWorkMode OBJECT-TYPE
    SYNTAX      INTEGER
        {
            other(1),
            on(2),
            pending(3),
            off(4)
        }
    MAX-ACCESS  read-only
    STATUS      current
    DESCRIPTION
        "
        The operation(activation) mode of an ONU.
        other(1)   - ONU is in another mode.
        on(2)      - ONU is registered and authorized to the
        network.  In this mode it works
        as a media converter.
        pending(3) - ONU has been registered to the PON, but
        not authorized to the network.
        off(4)     - ONU is not registered to the network.
        "
    ::= { unisOnuInfoEntry 8 }

unisOnuPCBVersion OBJECT-TYPE
    SYNTAX      OCTET STRING
    MAX-ACCESS  read-only
    STATUS      current
    DESCRIPTION
        "
        ONU PCB version.
        "
    ::= { unisOnuInfoEntry 9 }

unisOnuRtt OBJECT-TYPE
    SYNTAX      Unsigned32
    MAX-ACCESS  read-only
    STATUS      current
    DESCRIPTION
        "
        The signal round-trip-time(RTT) received.
        "
    ::= { unisOnuInfoEntry 10 }

unisOnuEEPROMVersion OBJECT-TYPE
    SYNTAX      OCTET STRING
    MAX-ACCESS  read-only
    STATUS      current
    DESCRIPTION
        "
        ONU EEPROM version.
        "
    ::= { unisOnuInfoEntry 11 }

unisOnuRegType OBJECT-TYPE
    SYNTAX      OCTET STRING
    MAX-ACCESS  read-only
    STATUS      current
    DESCRIPTION
        "
        ONU registered type.
        "
    ::= { unisOnuInfoEntry 12 }

unisOnuHostType OBJECT-TYPE
    SYNTAX      OCTET STRING
    MAX-ACCESS  read-only
    STATUS      current
    DESCRIPTION
        "
        ONU host type.
        "
    ::= { unisOnuInfoEntry 13 }

unisOnuDistance OBJECT-TYPE
    SYNTAX      Integer32
    MAX-ACCESS  read-only
    STATUS      current
    DESCRIPTION
        "
        The distance between OLT and ONU, measured in meter.
        "
    ::= { unisOnuInfoEntry 14 }

unisOnuLlid OBJECT-TYPE
    SYNTAX      Integer32
    MAX-ACCESS  read-only
    STATUS      current
    DESCRIPTION
        "
        The link layer identifier, which uniquely identifies the ONU
        of a specific OLT.
        "
    ::= { unisOnuInfoEntry 15 }

unisOnuVendorId OBJECT-TYPE
    SYNTAX      OCTET STRING
    MAX-ACCESS  read-only
    STATUS      current
    DESCRIPTION
        "
        ONU vendor ID.
        "
    ::= { unisOnuInfoEntry 16 }

unisOnuFirmwareVersion OBJECT-TYPE
    SYNTAX      OCTET STRING
    MAX-ACCESS  read-only
    STATUS      current
    DESCRIPTION
        "
        ONU firmware version.
        "
    ::= { unisOnuInfoEntry 17 }

unisOnuOpticalPowerReceivedByOlt OBJECT-TYPE
    SYNTAX     Integer32
    MAX-ACCESS read-only
    STATUS     current
    DESCRIPTION
        "
        The burst ONU optical power received by OLT,
        and when the ONU status is up the value is usable.
        It measured in 0.01 dBm unit.
        "
    ::= { unisOnuInfoEntry 18 }

unisOnuInfoMac OBJECT-TYPE
    SYNTAX     MacAddress
    MAX-ACCESS read-only
    STATUS     current
    DESCRIPTION
        "
        ONU's MAC.
        "
    ::= { unisOnuInfoEntry 19 }

unisOnuInfoLoid OBJECT-TYPE
    SYNTAX     OCTET STRING(SIZE(0..24))
    MAX-ACCESS read-only
    STATUS     current
    DESCRIPTION
        "
        ONU's LOID.
        "
    ::= { unisOnuInfoEntry 20 }

--
-- unisOnuMacAddrInfoTable
--

unisOnuMacAddrInfoTable OBJECT-TYPE
    SYNTAX      SEQUENCE OF UnisOnuMacAddrInfoEntry
    MAX-ACCESS  not-accessible
    STATUS      current
    DESCRIPTION
        "
        This table used for getting MAC address information of ONU.
        "
    ::= { unisEponOnuMan 6 }

unisOnuMacAddrInfoEntry OBJECT-TYPE
    SYNTAX      UnisOnuMacAddrInfoEntry
    MAX-ACCESS  not-accessible
    STATUS      current
    DESCRIPTION
        "
        The entry of the unisEponOnuMacAddrInfoTable.
        "
    INDEX
        {
            ifIndex,
            unisOnuMacIndex
        }
    ::= { unisOnuMacAddrInfoTable 1 }

UnisOnuMacAddrInfoEntry ::= SEQUENCE
    {
        unisOnuMacIndex       Integer32,
        unisOnuMacAddrFlag    INTEGER,
        unisOnuMacAddress     MacAddress
    }

unisOnuMacIndex OBJECT-TYPE
    SYNTAX      Integer32
    MAX-ACCESS  not-accessible
    STATUS      current
    DESCRIPTION
        "
        The index of ONUs in one OLT.
        "
    ::= { unisOnuMacAddrInfoEntry 1 }

unisOnuMacAddrFlag OBJECT-TYPE
    SYNTAX      INTEGER
        {
            bound(1),
            registered(2),
            run(3),
            regIncorrect(4)
        }
    MAX-ACCESS  read-only
    STATUS      current
    DESCRIPTION
        "
        The flag of ONU status.
        1 - bound: The ONU is bound but not registered.
        2 - registered: The ONU is registered but not bound.
        3 - run: The ONU is registered and bound on one OLT.
        4 - regIncorrect: The ONU is bound on one OLT and registered on
        another OLT.
        "
    ::= { unisOnuMacAddrInfoEntry 2 }

unisOnuMacAddress OBJECT-TYPE
    SYNTAX      MacAddress
    MAX-ACCESS  read-only
    STATUS      current
    DESCRIPTION
        "
        The MAC address of ONU.
        "
    ::= { unisOnuMacAddrInfoEntry 3 }

--
-- unisOnuBindMacAddrTable
--

unisOnuBindMacAddrTable OBJECT-TYPE
    SYNTAX      SEQUENCE OF UnisOnuBindMacAddrEntry
    MAX-ACCESS  not-accessible
    STATUS      current
    DESCRIPTION
        "
        This table implements the following functions for ONUs:
        Bind MAC of ONU.
        "
    ::= { unisEponOnuMan 7 }

unisOnuBindMacAddrEntry OBJECT-TYPE
    SYNTAX      UnisOnuBindMacAddrEntry
    MAX-ACCESS  not-accessible
    STATUS      current
    DESCRIPTION
        "
        The entry of the table unisOnuBindMacAddrTable.
        "
    INDEX
        {
            ifIndex
        }
    ::= { unisOnuBindMacAddrTable 1 }

UnisOnuBindMacAddrEntry ::= SEQUENCE
    {
        unisOnuBindMacAddress    MacAddress,
        unisOnuBindType          Integer32,
        unisOnuBindLoid          OCTET STRING,
        unisOnuBindPassword      OCTET STRING
    }

unisOnuBindMacAddress OBJECT-TYPE
    SYNTAX      MacAddress
    MAX-ACCESS  read-write
    STATUS      current
    DESCRIPTION
        "
        Bind the MAC of ONU.
        While the MAC is not bound, the ONU can not go into
        effect and configurations can not be set.
        Set 0-0-0 (MAC address) to the EPON device port will
        unbind the relationship with the original MAC and
        configurations will be set to default values.
        "
    ::= { unisOnuBindMacAddrEntry 1 }

unisOnuBindType OBJECT-TYPE
    SYNTAX      Integer32
    MAX-ACCESS  read-write
    STATUS      current
    DESCRIPTION
        "
        Set the binding type with the ONU which is confined
        to the index of unisEponOnuTypeDescr.
        "
    ::= { unisOnuBindMacAddrEntry 2 }

unisOnuBindLoid OBJECT-TYPE
    SYNTAX      OCTET STRING(SIZE(0..24))
    MAX-ACCESS  read-write
    STATUS      current
    DESCRIPTION
        "
        Bind the LOID of ONU.
        While the LOID is not bound, the ONU can not go into
        effect and configurations can not be set.
        "
    ::= { unisOnuBindMacAddrEntry 3 }

unisOnuBindPassword OBJECT-TYPE
    SYNTAX      OCTET STRING(SIZE(0..12))
    MAX-ACCESS  read-write
    STATUS      current
    DESCRIPTION
        "
        The password of LOID by using LOID-PASSWORD binding type to bind ONU.
        A zero-length string will be returned when reading.
        "
    ::= { unisOnuBindMacAddrEntry 4 }

--
-- unisOnuFirmwareUpdateTable
--

unisOnuFirmwareUpdateTable OBJECT-TYPE
    SYNTAX      SEQUENCE OF UnisOnuFirmwareUpdateEntry
    MAX-ACCESS  not-accessible
    STATUS      current
    DESCRIPTION
        "
        This table implements the following functions for ONUs:
        1. Update the ONU firmware.
        2. Result of update ONU firmware.
        "
    ::= { unisEponOnuMan 8 }

unisOnuFirmwareUpdateEntry OBJECT-TYPE
    SYNTAX      UnisOnuFirmwareUpdateEntry
    MAX-ACCESS  not-accessible
    STATUS      current
    DESCRIPTION
        "
        The entry of the table unisOnuFirmwareUpdateTable.
        "
    INDEX
        {
            ifIndex
        }
    ::= { unisOnuFirmwareUpdateTable 1 }

UnisOnuFirmwareUpdateEntry ::= SEQUENCE
    {
        unisOnuUpdate            INTEGER,
        unisOnuUpdateResult      INTEGER,
        unisOnuUpdateFileName    OCTET STRING,
        unisOnuUpdateProtType    INTEGER
    }

unisOnuUpdate OBJECT-TYPE
    SYNTAX      INTEGER
        {
            update(1)
        }
    MAX-ACCESS  read-write
    STATUS      current
    DESCRIPTION
        "
        update(1): Update the ONU firmware.
        Config the MIB object module unisEponOnuUpdateFileName
        with the filename of ONU firmware first.
        "
    ::= { unisOnuFirmwareUpdateEntry 1 }

unisOnuUpdateResult OBJECT-TYPE
    SYNTAX      INTEGER
        {
            updating(1),
            ok(2),
            fail(3),
            fileNotExist(4),
            notSetFilename(5),
            fileNotMatchONU(6),
            timeout(7),
            otherError(8)
        }
    MAX-ACCESS  read-only
    STATUS      current
    DESCRIPTION
        "
        The ONU firmware update result.
        updating  - The ONU is updating firmware right now.
        ok     - The ONU update result is OK.
        fail   - The ONU update result is fail.
        fileNotExist - The ONU update failed because the file does not exist.
        notSetFilename - The ONU firmware filename is not set.
        fileNotMatchONU - The ONU firmware does not match the ONU.
        timeout - The ONU responses timeout.
        otherError - The ONU update result is unknown.
        "
    ::= { unisOnuFirmwareUpdateEntry 2 }

unisOnuUpdateFileName OBJECT-TYPE
    SYNTAX      OCTET STRING(SIZE(0..255))
    MAX-ACCESS  read-write
    STATUS      current
    DESCRIPTION
        "
        The filename of the ONU firmware to be updated.
        Note that the filename must contain the file path.
        "
    ::= { unisOnuFirmwareUpdateEntry 3 }

unisOnuUpdateProtType OBJECT-TYPE
    SYNTAX      INTEGER
        {
            private(0),
            ctc(1)
        }
    MAX-ACCESS  read-write
    STATUS      current
    DESCRIPTION
        "
        private(0): Using private protocol to update the ONU firmware.
        ctc(1): Using ctc standard protocol to update the ONU firmware.
        "
    DEFVAL { private }
    ::= { unisOnuFirmwareUpdateEntry 4 }

unisOnuLinkTestFrameNumMinVal OBJECT-TYPE
    SYNTAX      Integer32
    MAX-ACCESS  read-only
    STATUS      current
    DESCRIPTION
        "The lower limit of measurement frames which is confined to
        unisOnuLinkTestFrameNum."
    ::= { unisEponOnuMan 9 }

unisOnuLinkTestFrameNumMaxVal OBJECT-TYPE
    SYNTAX      Integer32
    MAX-ACCESS  read-only
    STATUS      current
    DESCRIPTION
        "The upper limit of measurement frames which is confined to
        unisOnuLinkTestFrameNum."
    ::= { unisEponOnuMan 10 }

unisOnuSlaMaxBandWidthMinVal OBJECT-TYPE
    SYNTAX      Integer32
    MAX-ACCESS  read-only
    STATUS      current
    DESCRIPTION
        "
        The lower limit of maximum-bandwidth which is confined to
        unisOnuSlaMaxBandWidth."
    ::= { unisEponOnuMan 11 }

unisOnuSlaMaxBandWidthMaxVal OBJECT-TYPE
    SYNTAX      Integer32
    MAX-ACCESS  read-only
    STATUS      current
    DESCRIPTION
        "
        The upper limit of maximum-bandwidth which is confined to
        unisOnuSlaMaxBandWidth."
    ::= { unisEponOnuMan 12 }

unisOnuSlaMinBandWidthMinVal OBJECT-TYPE
    SYNTAX      Integer32
    MAX-ACCESS  read-only
    STATUS      current
    DESCRIPTION
        "
        The lower limit of minimum-bandwidth which is confined to
        unisOnuSlaMinBandWidth."
    ::= { unisEponOnuMan 13 }

unisOnuSlaMinBandWidthMaxVal OBJECT-TYPE
    SYNTAX      Integer32
    MAX-ACCESS  read-only
    STATUS      current
    DESCRIPTION
        "
        The upper limit of minimum-bandwidth which is confined to
        unisOnuSlaMinBandWidth."
    ::= { unisEponOnuMan 14 }

--
-- unisEponOnuTypeManTable
--

unisEponOnuTypeManTable OBJECT-TYPE
    SYNTAX      SEQUENCE OF UnisEponOnuTypeManEntry
    MAX-ACCESS  not-accessible
    STATUS      current
    DESCRIPTION
        "
        This table is used for getting ONU bind type in current version.
        "
    ::= { unisEponOnuMan 15 }

unisEponOnuTypeManEntry OBJECT-TYPE
    SYNTAX      UnisEponOnuTypeManEntry
    MAX-ACCESS  not-accessible
    STATUS      current
    DESCRIPTION
        "
        The entry of the unisEponOnuTypeManTable.
        "
    INDEX
        {
            unisEponOnuTypeIndex
        }
    ::= { unisEponOnuTypeManTable 1 }

UnisEponOnuTypeManEntry ::= SEQUENCE
    {
        unisEponOnuTypeIndex    Integer32,
        unisEponOnuTypeDescr    OCTET STRING
    }

unisEponOnuTypeIndex OBJECT-TYPE
    SYNTAX      Integer32
    MAX-ACCESS  not-accessible
    STATUS      current
    DESCRIPTION
        "
        The ONU type index.
        "
    ::= { unisEponOnuTypeManEntry 1 }

unisEponOnuTypeDescr OBJECT-TYPE
    SYNTAX      OCTET STRING
    MAX-ACCESS  read-only
    STATUS      current
    DESCRIPTION
        "
        The ONU type description which can be used to bind ONU in current
        version.
        the value of unisOnuBindType can be configured by the index of
        unisEponOnuTypeDescr.
        "
    ::= { unisEponOnuTypeManEntry 2 }

unisOnuPacketManTable OBJECT-TYPE
    SYNTAX      SEQUENCE OF UnisOnuPacketManEntry
    MAX-ACCESS  not-accessible
    STATUS      current
    DESCRIPTION
        "
        This table implements the following functions:
        (1)Manage packet priority trust mode.
        (2)Manage packet queue-scheduler mode.
        "
    ::= { unisEponOnuMan 16 }

unisOnuPacketManEntry OBJECT-TYPE
    SYNTAX      UnisOnuPacketManEntry
    MAX-ACCESS  not-accessible
    STATUS      current
    DESCRIPTION
        "
        The entry of the unisOnuPacketManTable.
        "
    INDEX
        {
            ifIndex
        }
    ::= { unisOnuPacketManTable 1 }

UnisOnuPacketManEntry ::= SEQUENCE
    {
        unisOnuPriorityTrust     INTEGER,
        unisOnuQueueScheduler    INTEGER
    }

unisOnuPriorityTrust OBJECT-TYPE
    SYNTAX      INTEGER
        {
            dscp(1),
            ipprecedence(2),
            cos(3)
        }
    MAX-ACCESS  read-write
    STATUS      current
    DESCRIPTION
        "
        The QOS mode which is assigned on ONU.
        dscp - The service dscp of politic Priority.
        ipprecedence - The service IP precedence of politic Priority.
        cos - The service cos of politic Priority.
        "
    DEFVAL { cos }
    ::= { unisOnuPacketManEntry 1 }

unisOnuQueueScheduler OBJECT-TYPE
    SYNTAX      INTEGER
        {
            spq(1),
            wfq(2)
        }
    MAX-ACCESS  read-write
    STATUS      current
    DESCRIPTION
        "
        The packet queue-scheduler mode which is assigned on ONU.
        spq - strict priority queuing.
        wfq - specifies the weights for weighted round-robin queuing.
        "
    DEFVAL { spq }
    ::= { unisOnuPacketManEntry 2 }

unisOnuProtocolTable OBJECT-TYPE
    SYNTAX      SEQUENCE OF UnisOnuProtocolEntry
    MAX-ACCESS  not-accessible
    STATUS      current
    DESCRIPTION
        "
        This table implements the following functions:
        (1)Manage STP status.
        (2)Manage IGMP-snooping.
        (3)Manage DHCP-snooping.
        "
    ::= { unisEponOnuMan 17 }

unisOnuProtocolEntry OBJECT-TYPE
    SYNTAX      UnisOnuProtocolEntry
    MAX-ACCESS  not-accessible
    STATUS      current
    DESCRIPTION
        "
        The entry of unisOnuProtocolTable.
        "
    INDEX
        {
            ifIndex
        }
    ::= { unisOnuProtocolTable 1 }

UnisOnuProtocolEntry ::= SEQUENCE
    {
        unisOnuStpStatus                   TruthValue,
        unisOnuIgmpSnoopingStatus          TruthValue,
        unisOnuDhcpsnoopingOption82        TruthValue,
        unisOnuDhcpsnooping                TruthValue,
        unisOnuPppoe                       TruthValue,
        unisOnuIgmpSnoopingHostAgingT      Integer32,
        unisOnuIgmpSnoopingMaxRespT        Integer32,
        unisOnuIgmpSnoopingRouterAgingT    Integer32,
        unisOnuIgmpSnoopingAggReportS      TruthValue,
        unisOnuIgmpSnoopingAggLeaveS       TruthValue
    }

unisOnuStpStatus OBJECT-TYPE
    SYNTAX      TruthValue
    MAX-ACCESS  read-write
    STATUS      current
    DESCRIPTION
        "
        true(1)  - STP status enable on ONU.
        false(2) - STP status disable on ONU.
        "
    DEFVAL { true }
    ::= { unisOnuProtocolEntry 1 }

unisOnuIgmpSnoopingStatus OBJECT-TYPE
    SYNTAX      TruthValue
    MAX-ACCESS  read-write
    STATUS      current
    DESCRIPTION
        "
        true(1)  - IGMP snooping status enable on ONU.
        false(2) - IGMP snooping status disable on ONU.
        "
    DEFVAL { true }
    ::= { unisOnuProtocolEntry 2 }

unisOnuDhcpsnoopingOption82 OBJECT-TYPE
    SYNTAX      TruthValue
    MAX-ACCESS  read-write
    STATUS      current
    DESCRIPTION
        "
        true(1)  - DHCP snooping Option 82 status enable on ONU.
        false(2) - DHCP snooping Option 82 status disable on ONU.
        "
    DEFVAL { false }
    ::= { unisOnuProtocolEntry 3 }

unisOnuDhcpsnooping OBJECT-TYPE
    SYNTAX      TruthValue
    MAX-ACCESS  read-write
    STATUS      current
    DESCRIPTION
        "
        true(1)  - DHCP snooping status enable on ONU.
        false(2) - DHCP snooping status disable on ONU.
        "
    DEFVAL { false }
    ::= { unisOnuProtocolEntry 4 }

unisOnuPppoe OBJECT-TYPE
    SYNTAX      TruthValue
    MAX-ACCESS  read-write
    STATUS      current
    DESCRIPTION
        "
        true(1)  - PPPOE status enable on ONU.
        false(2) - PPPOE status disable on ONU.
        "
    DEFVAL { false }
    ::= { unisOnuProtocolEntry 5 }

unisOnuIgmpSnoopingHostAgingT OBJECT-TYPE
    SYNTAX      Integer32
    MAX-ACCESS  read-write
    STATUS      current
    DESCRIPTION
        "
        Set the host aging time of IGMP on ONU.
        "
    ::= { unisOnuProtocolEntry 6 }

unisOnuIgmpSnoopingMaxRespT OBJECT-TYPE
    SYNTAX      Integer32
    MAX-ACCESS  read-write
    STATUS      current
    DESCRIPTION
        "
        Set the max response time of IGMP on ONU.
        "
    ::= { unisOnuProtocolEntry 7 }

unisOnuIgmpSnoopingRouterAgingT OBJECT-TYPE
    SYNTAX      Integer32
    MAX-ACCESS  read-write
    STATUS      current
    DESCRIPTION
        "
        Set the router aging time of IGMP on ONU.
        "
    ::= { unisOnuProtocolEntry 8 }

unisOnuIgmpSnoopingAggReportS OBJECT-TYPE
    SYNTAX      TruthValue
    MAX-ACCESS  read-write
    STATUS      current
    DESCRIPTION
        "
        true(1)  - Igmp snooping aggregation report status enable on ONU.
        false(2) - Igmp snooping aggregation report status disable on ONU.
        "
    DEFVAL { false }
    ::= { unisOnuProtocolEntry 9 }

unisOnuIgmpSnoopingAggLeaveS OBJECT-TYPE
    SYNTAX      TruthValue
    MAX-ACCESS  read-write
    STATUS      current
    DESCRIPTION
        "
        true(1)  - Igmp snooping aggregation leave status enable on ONU.
        false(2) - Igmp snooping aggregation leave status disable on ONU.
        "
    DEFVAL { true }
    ::= { unisOnuProtocolEntry 10 }

unisOnuDot1xTable OBJECT-TYPE
    SYNTAX      SEQUENCE OF UnisOnuDot1xEntry
    MAX-ACCESS  not-accessible
    STATUS      current
    DESCRIPTION
        "
        This table implements the following functions:
        (1)Manage 802.1x account.
        (2)Manage 802.1x password.
        ONU will be authorized to send and receive frames when the
        account and the password are all right, otherwise this ONU
        will be unavailable.
        "
    ::= { unisEponOnuMan 18 }

unisOnuDot1xEntry OBJECT-TYPE
    SYNTAX      UnisOnuDot1xEntry
    MAX-ACCESS  not-accessible
    STATUS      current
    DESCRIPTION
        "
        The entry of the unisOnuDot1xTable.
        "
    INDEX
        {
            ifIndex
        }
    ::= { unisOnuDot1xTable 1 }

UnisOnuDot1xEntry ::= SEQUENCE
    {
        unisOnuDot1xAccount     OCTET STRING,
        unisOnuDot1xPassword    OCTET STRING
    }

unisOnuDot1xAccount OBJECT-TYPE
    SYNTAX      OCTET STRING
    MAX-ACCESS  read-write
    STATUS      current
    DESCRIPTION
        "
        ONU 802.1X account.
        The object value cannot be set as 'a', 'al' or 'all'.
        The object should be set together with unisOnuDot1xPassword.
        "
    ::= { unisOnuDot1xEntry 1 }

unisOnuDot1xPassword OBJECT-TYPE
    SYNTAX      OCTET STRING
    MAX-ACCESS  read-write
    STATUS      current
    DESCRIPTION
        "
        ONU 802.1X password.
        The object should be set together with unisOnuDot1xAccount.
        "
    ::= { unisOnuDot1xEntry 2 }

unisEponBatchOperationMan OBJECT IDENTIFIER ::= { unisEponMibObjects 6 }

--
-- unisOnuPriorityQueueTable
--

unisOnuPriorityQueueTable OBJECT-TYPE
    SYNTAX      SEQUENCE OF UnisOnuPriorityQueueEntry
    MAX-ACCESS  not-accessible
    STATUS      current
    DESCRIPTION
        "
        This table contains specific information of priority queue.
        "
    ::= { unisEponOnuMan 19 }

unisOnuPriorityQueueEntry OBJECT-TYPE
    SYNTAX      UnisOnuPriorityQueueEntry
    MAX-ACCESS  not-accessible
    STATUS      current
    DESCRIPTION
        "
        The entry of unisOnuPriorityQueueTable.
        "
    INDEX
        {
            ifIndex,
            unisOnuQueueDirection,
            unisOnuQueueId
        }
    ::= { unisOnuPriorityQueueTable 1 }

UnisOnuPriorityQueueEntry ::= SEQUENCE
    {
        unisOnuQueueDirection    INTEGER,
        unisOnuQueueId           Integer32,
        unisOnuQueueSize         Integer32
    }

unisOnuQueueDirection OBJECT-TYPE
    SYNTAX      INTEGER
        {
            inbound(1),
            outbound(2)
        }
    MAX-ACCESS  not-accessible
    STATUS      current
    DESCRIPTION
        "
        The direction of priority queue.
        "
    ::= { unisOnuPriorityQueueEntry 1 }

unisOnuQueueId OBJECT-TYPE
    SYNTAX      Integer32(0..7)
    MAX-ACCESS  not-accessible
    STATUS      current
    DESCRIPTION
        "
        The queue ID of priority queue.
        "
    ::= { unisOnuPriorityQueueEntry 2 }

unisOnuQueueSize OBJECT-TYPE
    SYNTAX      Integer32
    MAX-ACCESS  read-write
    STATUS      current
    DESCRIPTION
        "
        The size of priority queue, measured in percent.  The total length of
        all priority queues is a constant, by default, it is assigned to all
        of the priority queues evenly.  The length of each priority queue may
        be changed by changing the value of unisOnuPriorityQueueSize.
        The total size of the inbound or outbound priority queues should be
        not more than 100.
        "
    ::= { unisOnuPriorityQueueEntry 3 }

--
-- unisOnuCountTable
--

unisOnuCountTable OBJECT-TYPE
    SYNTAX      SEQUENCE OF UnisOnuCountEntry
    MAX-ACCESS  not-accessible
    STATUS      current
    DESCRIPTION
        "
        This table contains statistics of ONU port.
        "
    ::= { unisEponOnuMan 20 }

unisOnuCountEntry OBJECT-TYPE
    SYNTAX      UnisOnuCountEntry
    MAX-ACCESS  not-accessible
    STATUS      current
    DESCRIPTION
        "
        The entry of unisOnuCountTable.
        "
    INDEX
        {
            ifIndex
        }
    ::= { unisOnuCountTable 1 }

UnisOnuCountEntry ::= SEQUENCE
    {
        unisOnuInCRCErrPkts        Counter64,
        unisOnuOutDroppedFrames    Counter64
    }

unisOnuInCRCErrPkts OBJECT-TYPE
    SYNTAX      Counter64
    MAX-ACCESS  read-only
    STATUS      current
    DESCRIPTION
        "
        The total number of frames received with bad CRC checksum.
        "
    ::= { unisOnuCountEntry 1 }

unisOnuOutDroppedFrames OBJECT-TYPE
    SYNTAX      Counter64
    MAX-ACCESS  read-only
    STATUS      current
    DESCRIPTION
        "
        The total number of frames dropped because of buffer failure.
        "
    ::= { unisOnuCountEntry 2 }

unisEponOnuScalarGroup OBJECT IDENTIFIER ::= { unisEponOnuMan 21 }

unisOnuPriorityQueueSizeMinVal OBJECT-TYPE
    SYNTAX      Integer32
    MAX-ACCESS  read-only
    STATUS      current
    DESCRIPTION
        "
        The lower limit of queue size which is confined to
        unisOnuQueueSize.
        "
    ::= { unisEponOnuScalarGroup 1 }

unisOnuPriorityQueueSizeMaxVal OBJECT-TYPE
    SYNTAX      Integer32
    MAX-ACCESS  read-only
    STATUS      current
    DESCRIPTION
        "
        The upper limit of queue size which is confined to
        unisOnuQueueSize.
        "
    ::= { unisEponOnuScalarGroup 2 }

unisOnuPriorityQueueBandwidthMinVal OBJECT-TYPE
    SYNTAX      Integer32
    MAX-ACCESS  read-only
    STATUS      current
    DESCRIPTION
        "
        The lower limit of unisOnuQueueMaxBandwidth.
        "
    ::= { unisEponOnuScalarGroup 3 }

unisOnuPriorityQueueBandwidthMaxVal OBJECT-TYPE
    SYNTAX      Integer32
    MAX-ACCESS  read-only
    STATUS      current
    DESCRIPTION
        "
        The upper limit of unisOnuQueueMaxBandwidth.
        "
    ::= { unisEponOnuScalarGroup 4 }

unisOnuPriorityQueueBurstsizeMinVal OBJECT-TYPE
    SYNTAX      Integer32
    MAX-ACCESS  read-only
    STATUS      current
    DESCRIPTION
        "
        The lower limit of unisOnuQueueMaxBurstsize.
        "
    ::= { unisEponOnuScalarGroup 5 }

unisOnuPriorityQueueBurstsizeMaxVal OBJECT-TYPE
    SYNTAX      Integer32
    MAX-ACCESS  read-only
    STATUS      current
    DESCRIPTION
        "
        The upper limit of unisOnuQueueMaxBurstsize.
        "
    ::= { unisEponOnuScalarGroup 6 }

unisOnuUpdateByTypeNextIndex OBJECT-TYPE
    SYNTAX      Integer32
    MAX-ACCESS  read-only
    STATUS      current
    DESCRIPTION
        "
        Offer a free index of unisOnuFirmwareUpdateByTypeTable.
        "
    ::= { unisEponOnuScalarGroup 7 }

--
-- unisOnuQueueBandwidthTable
--

unisOnuQueueBandwidthTable OBJECT-TYPE
    SYNTAX      SEQUENCE OF UnisOnuQueueBandwidthEntry
    MAX-ACCESS  not-accessible
    STATUS      current
    DESCRIPTION
        "
        This table contains specific bandwidth information of ONU priority queue.
        "
    ::= { unisEponOnuMan 22 }

unisOnuQueueBandwidthEntry OBJECT-TYPE
    SYNTAX      UnisOnuQueueBandwidthEntry
    MAX-ACCESS  not-accessible
    STATUS      current
    DESCRIPTION
        "
        The entry of unisOnuQueueBandwidthTable.
        "
    INDEX
        {
            ifIndex,
            unisOnuQueueDirection,
            unisOnuQueueId
        }
    ::= { unisOnuQueueBandwidthTable 1 }

UnisOnuQueueBandwidthEntry ::= SEQUENCE
    {
        unisOnuQueueMaxBandwidth    Integer32,
        unisOnuQueueMaxBurstsize    Integer32,
        unisOnuQueuePolicyStatus    TruthValue
    }

unisOnuQueueMaxBandwidth OBJECT-TYPE
    SYNTAX      Integer32
    MAX-ACCESS  read-write
    STATUS      current
    DESCRIPTION
        "
        The maximum bandwidth of specific ONU priority queue,
        measured in 100Kbps.
        "
    ::= { unisOnuQueueBandwidthEntry 1 }

unisOnuQueueMaxBurstsize OBJECT-TYPE
    SYNTAX      Integer32
    MAX-ACCESS  read-write
    STATUS      current
    DESCRIPTION
        "
        The maximum burst size of specific ONU priority queue,
        measured in 64Bytes.
        "
    ::= { unisOnuQueueBandwidthEntry 2 }

unisOnuQueuePolicyStatus OBJECT-TYPE
    SYNTAX      TruthValue
    MAX-ACCESS  read-write
    STATUS      current
    DESCRIPTION
        "
        true - enable bandwidth policy
        false - disable bandwidth policy
        The bandwidth administrative status of specific ONU priority queue.
        "
    ::= { unisOnuQueueBandwidthEntry 3 }

--
-- unisOnuIpAddressTable
--

unisOnuIpAddressTable OBJECT-TYPE
    SYNTAX      SEQUENCE OF UnisOnuIpAddressEntry
    MAX-ACCESS  not-accessible
    STATUS      current
    DESCRIPTION
        "
        ONU IP address table.
        "
    ::= { unisEponOnuMan 23 }

unisOnuIpAddressEntry OBJECT-TYPE
    SYNTAX      UnisOnuIpAddressEntry
    MAX-ACCESS  not-accessible
    STATUS      current
    DESCRIPTION
        "
        The entry of unisOnuIpAddressTable.
        "
    INDEX
        {
            ifIndex
        }
    ::= { unisOnuIpAddressTable 1 }

UnisOnuIpAddressEntry ::= SEQUENCE
    {
        unisOnuIpAddress           IpAddress,
        unisOnuIpAddressMask       IpAddress,
        unisOnuIpAddressGateway    IpAddress,
        unisOnuDhcpallocate        TruthValue,
        unisOnuManageVID           Integer32,
        unisOnuManageVlanIntfS     TruthValue
    }

unisOnuIpAddress OBJECT-TYPE
    SYNTAX      IpAddress
    MAX-ACCESS  read-write
    STATUS      current
    DESCRIPTION
        "
        The IP address assigned to the ONU.
        "
    ::= { unisOnuIpAddressEntry 1 }

unisOnuIpAddressMask OBJECT-TYPE
    SYNTAX      IpAddress
    MAX-ACCESS  read-write
    STATUS      current
    DESCRIPTION
        "
        The mask of IP address denoted by unisOnuIpAddress.
        "
    ::= { unisOnuIpAddressEntry 2 }

unisOnuIpAddressGateway OBJECT-TYPE
    SYNTAX      IpAddress
    MAX-ACCESS  read-write
    STATUS      current
    DESCRIPTION
        "
        The gateway of IP address denoted by unisOnuIpAddress.
        "
    ::= { unisOnuIpAddressEntry 3 }

unisOnuDhcpallocate OBJECT-TYPE
    SYNTAX      TruthValue
    MAX-ACCESS  read-write
    STATUS      current
    DESCRIPTION
        "
        true(1)  - ONU auto allocate IP address status enable.
        false(2) - ONU auto allocate IP address status disable.
        "
    ::= { unisOnuIpAddressEntry 4 }

unisOnuManageVID OBJECT-TYPE
    SYNTAX      Integer32
    MAX-ACCESS  read-write
    STATUS      current
    DESCRIPTION
        "
        The management VLAN of ONU denoted by unisOnuManageVID.
        "
    ::= { unisOnuIpAddressEntry 5 }

unisOnuManageVlanIntfS OBJECT-TYPE
    SYNTAX      TruthValue
    MAX-ACCESS  read-write
    STATUS      current
    DESCRIPTION
        "
        The management interface status of ONU denoted by unisOnuManageVlanIntfS.
        "
    ::= { unisOnuIpAddressEntry 6 }

--
-- unisOnuChipSetInfoTable
--

unisOnuChipSetInfoTable OBJECT-TYPE
    SYNTAX      SEQUENCE OF UnisOnuChipSetInfoEntry
    MAX-ACCESS  not-accessible
    STATUS      current
    DESCRIPTION
        "
        ONU vendor specific information of ONU.
        "
    ::= { unisEponOnuMan 24 }

unisOnuChipSetInfoEntry OBJECT-TYPE
    SYNTAX      UnisOnuChipSetInfoEntry
    MAX-ACCESS  not-accessible
    STATUS      current
    DESCRIPTION
        "
        The entry of unisOnuChipSetInfoTable.
        "
    INDEX
        {
            ifIndex
        }
    ::= { unisOnuChipSetInfoTable 1 }

UnisOnuChipSetInfoEntry ::= SEQUENCE
    {
        unisOnuChipSetVendorId      OCTET STRING,
        unisOnuChipSetModel         OCTET STRING,
        unisOnuChipSetRevision      Integer32,
        unisOnuChipSetDesignDate    DateAndTime
    }

unisOnuChipSetVendorId OBJECT-TYPE
    SYNTAX      OCTET STRING(SIZE(0..255))
    MAX-ACCESS  read-only
    STATUS      current
    DESCRIPTION
        "
        Chipset vendor ID, which identifies the ONU's PON chip vendor
        according JEDEC ID code.
        "
    ::= { unisOnuChipSetInfoEntry 1 }

unisOnuChipSetModel OBJECT-TYPE
    SYNTAX      OCTET STRING(SIZE(0..255))
    MAX-ACCESS  read-only
    STATUS      current
    DESCRIPTION
        "
        Chip model, numbering(range from 0 to 0xFF) by the chip vendor.
        "
    ::= { unisOnuChipSetInfoEntry 2 }

unisOnuChipSetRevision OBJECT-TYPE
    SYNTAX      Integer32
    MAX-ACCESS  read-only
    STATUS      current
    DESCRIPTION
        "
        Chip revision.
        "
    ::= { unisOnuChipSetInfoEntry 3 }

unisOnuChipSetDesignDate OBJECT-TYPE
    SYNTAX      DateAndTime
    MAX-ACCESS  read-only
    STATUS      current
    DESCRIPTION
        "
        Chip design date.
        "
    ::= { unisOnuChipSetInfoEntry 4 }

--
-- unisOnuCapabilityTable
--

unisOnuCapabilityTable OBJECT-TYPE
    SYNTAX      SEQUENCE OF UnisOnuCapabilityEntry
    MAX-ACCESS  not-accessible
    STATUS      current
    DESCRIPTION
        "
        Capability of ONU.
        "
    ::= { unisEponOnuMan 25 }

unisOnuCapabilityEntry OBJECT-TYPE
    SYNTAX      UnisOnuCapabilityEntry
    MAX-ACCESS  not-accessible
    STATUS      current
    DESCRIPTION
        "
        The entry of the table unisOnuCapabilityTable.
        "
    INDEX
        {
            ifIndex
        }
    ::= { unisOnuCapabilityTable 1 }

UnisOnuCapabilityEntry ::= SEQUENCE
    {
        unisOnuServiceSupported             BITS,
        unisOnuGEPortNumber                 Integer32,
        unisOnuFEPortNumber                 Integer32,
        unisOnuPOTSPortNumber               Integer32,
        unisOnuE1PortsNumber                Integer32,
        unisOnuUpstreamQueueNumber          Integer32,
        unisOnuMaxUpstreamQueuePerPort      Integer32,
        unisOnuDownstreamQueueNumber        Integer32,
        unisOnuMaxDownstreamQueuePerPort    Integer32,
        unisOnuBatteryBackup                TruthValue,
        unisOnuIgspFastLeaveSupported       TruthValue,
        unisOnuMCtrlFastLeaveSupported      TruthValue,
        unisOnuType                         Integer32,
        unisOnuMultiLLID                    Integer32,
        unisOnuProtectionType               Integer32,
        unisOnuPonIFNum                     Integer32,
        unisOnuSlotNum                      Integer32,
        unisOnuIPv6Supported                Integer32,
        unisOnuPowerSupplyControl           Integer32,
        unisOnuServiceSLA                   Integer32
    }

unisOnuServiceSupported OBJECT-TYPE
    SYNTAX      BITS
        {
            geinterfacesupport(0),
            feinterfacesupport(1),
            voipservicesupport(2),
            tdmservicesupport(3)
        }
    MAX-ACCESS  read-only
    STATUS      current
    DESCRIPTION
        "
        Services types supported by the ONU.
        These functional groups can be supported independently.
        geinterfacesupport - supporting (1)/not supporting(0)
        Gbit Ethernet GE interface.
        feinterfacesupport - supporting (1)/not supporting(0)
        100M Ethernet FE interface.(maximum rate is 100M, without GEinterface)
        voipservicesupport - supporting (1)/not supporting(0)VoIP service.
        tdmservicesupport - supporting (1)/not supporting(0)TDM CES service.
        "
    ::= { unisOnuCapabilityEntry 1 }

unisOnuGEPortNumber OBJECT-TYPE
    SYNTAX      Integer32
    MAX-ACCESS  read-only
    STATUS      current
    DESCRIPTION
        "
        The current  gigabit ethernet ports number supported by the ONU.
        "
    ::= { unisOnuCapabilityEntry 2 }

unisOnuFEPortNumber OBJECT-TYPE
    SYNTAX      Integer32
    MAX-ACCESS  read-only
    STATUS      current
    DESCRIPTION
        "
        the current fast ethernet ports number supported by the ONU.
        "
    ::= { unisOnuCapabilityEntry 3 }

unisOnuPOTSPortNumber OBJECT-TYPE
    SYNTAX      Integer32
    MAX-ACCESS  read-only
    STATUS      current
    DESCRIPTION
        "
        The current POTS ports number supported by the ONU
        "
    ::= { unisOnuCapabilityEntry 4 }

unisOnuE1PortsNumber OBJECT-TYPE
    SYNTAX      Integer32
    MAX-ACCESS  read-only
    STATUS      current
    DESCRIPTION
        "
        The current E1 ports number supported by the ONU.
        "
    ::= { unisOnuCapabilityEntry 5 }

unisOnuUpstreamQueueNumber OBJECT-TYPE
    SYNTAX      Integer32
    MAX-ACCESS  read-only
    STATUS      current
    DESCRIPTION
        "
        The number of upstream queues supported by the ONU.
        "
    ::= { unisOnuCapabilityEntry 6 }

unisOnuMaxUpstreamQueuePerPort OBJECT-TYPE
    SYNTAX      Integer32
    MAX-ACCESS  read-only
    STATUS      current
    DESCRIPTION
        "
        The number of maximum upstream queues per port of the ONU.
        "
    ::= { unisOnuCapabilityEntry 7 }

unisOnuDownstreamQueueNumber OBJECT-TYPE
    SYNTAX      Integer32
    MAX-ACCESS  read-only
    STATUS      current
    DESCRIPTION
        "
        The number of downstream queues supported by the ONU.
        "
    ::= { unisOnuCapabilityEntry 8 }

unisOnuMaxDownstreamQueuePerPort OBJECT-TYPE
    SYNTAX      Integer32
    MAX-ACCESS  read-only
    STATUS      current
    DESCRIPTION
        "
        The number of maximum downstream queues per port of the ONU.
        "
    ::= { unisOnuCapabilityEntry 9 }

unisOnuBatteryBackup OBJECT-TYPE
    SYNTAX      TruthValue
    MAX-ACCESS  read-only
    STATUS      current
    DESCRIPTION
        "
        true(1) - ONU supports a reserve battery.
        false(2) - ONU does not support a reserve battery.
        "
    ::= { unisOnuCapabilityEntry 10 }

unisOnuIgspFastLeaveSupported OBJECT-TYPE
    SYNTAX      TruthValue
    MAX-ACCESS  read-only
    STATUS      current
    DESCRIPTION
        "
        true(1) -  ONU supports fast leave in igsp mode.
        false(2) - ONU does not support fast leave in igsp mode.
        "
    ::= { unisOnuCapabilityEntry 11 }

unisOnuMCtrlFastLeaveSupported OBJECT-TYPE
    SYNTAX      TruthValue
    MAX-ACCESS  read-only
    STATUS      current
    DESCRIPTION
        "
        true(1) -  ONU supports fast leave in multicast control mode.
        false(2) - ONU does not support fast leave in multicast control mode.
        "
    ::= { unisOnuCapabilityEntry 12 }

unisOnuType OBJECT-TYPE
    SYNTAX      Integer32
    MAX-ACCESS  read-only
    STATUS      current
    DESCRIPTION
        "
        ONU type:
        SFU(0)
        HGU(1)
        SBU(2)
        MDU(3) which is cassette equipment and uses Ethernet access as broadband
        MDU(4) which is small card equipment and uses Ethernet access as broadband
        MDU(5) which is small card equipment and uses DSL access as broadband
        MDU(6) which is middle card equipment and uses DSL access as broadband
        MDU(7) which is card equipment and can use both Ethernet and DSL access as broadband
        MTU(8)
        "
    ::= { unisOnuCapabilityEntry 13 }

unisOnuMultiLLID OBJECT-TYPE
    SYNTAX      Integer32
    MAX-ACCESS  read-only
    STATUS      current
    DESCRIPTION
        "
        (0) - Invalid value.
        (1) - ONU supports one LLID.
        other - ONU supports multiple LLIDs.
        "
    ::= { unisOnuCapabilityEntry 14 }

unisOnuProtectionType OBJECT-TYPE
    SYNTAX      Integer32
    MAX-ACCESS  read-only
    STATUS      current
    DESCRIPTION
        "
        (0) - Not supported.
        (1) - ONU supports type C optical link protection.
        (2) - ONU supports type D optical link protection.
        "
    ::= { unisOnuCapabilityEntry 15 }

unisOnuPonIFNum OBJECT-TYPE
    SYNTAX      Integer32
    MAX-ACCESS  read-only
    STATUS      current
    DESCRIPTION
        "
        (1) - ONU support one PON interface.
        (2) - ONU support two PON interfaces.
        "
    ::= { unisOnuCapabilityEntry 16 }

unisOnuSlotNum OBJECT-TYPE
    SYNTAX      Integer32
    MAX-ACCESS  read-only
    STATUS      current
    DESCRIPTION
        "
        The slot number of a card ONU.
        If the ONU is not card equipment, 0 is returned.
        "
    ::= { unisOnuCapabilityEntry 17 }

unisOnuIPv6Supported OBJECT-TYPE
    SYNTAX      Integer32
    MAX-ACCESS  read-only
    STATUS      current
    DESCRIPTION
        "
        (0) - ONU supports IPv6.
        (1) - ONU does not support IPv6.
        "
    ::= { unisOnuCapabilityEntry 18 }

unisOnuPowerSupplyControl OBJECT-TYPE
    SYNTAX      Integer32
    MAX-ACCESS  read-only
    STATUS      current
    DESCRIPTION
        "
        (0) - ONU does not support ONU power supply control.
        (1) - ONU supports Tx power supply control only.
        The Tx and Rx power supply can only be controlled together
        whereby Rx power supply is also shutdown when Tx power supply is shutdown.
        (2) - ONU supports both Tx and Rx power supply control.
        In this case, Tx and Rx power supply can be controlled separately whereby
        Rx power supply is still on while Tx power supply is shutdown.
        "
    ::= { unisOnuCapabilityEntry 19 }

unisOnuServiceSLA OBJECT-TYPE
    SYNTAX      Integer32
    MAX-ACCESS  read-only
    STATUS      current
    DESCRIPTION
        "
        (1) - ONU does not support SLA services.
        (2~8) - ONU supports 2~8 SLA services.
        "
    ::= { unisOnuCapabilityEntry 20 }

--
-- unisOnuDbaReportTable
--

unisOnuDbaReportTable OBJECT-TYPE
    SYNTAX      SEQUENCE OF UnisOnuDbaReportEntry
    MAX-ACCESS  not-accessible
    STATUS      current
    DESCRIPTION
        "
        This table defines the information of DBA(dynamic bandwidth allocation)
        report threshold contained in the MPCP report frames.
        "
    ::= { unisEponOnuMan 26 }

unisOnuDbaReportEntry OBJECT-TYPE
    SYNTAX      UnisOnuDbaReportEntry
    MAX-ACCESS  not-accessible
    STATUS      current
    DESCRIPTION
        "
        The entry of the table unisOnuDbaReportTable.
        "
    INDEX
        {
            ifIndex,
            unisOnuDbaReportQueueId
        }
    ::= { unisOnuDbaReportTable 1 }

UnisOnuDbaReportEntry ::= SEQUENCE
    {
        unisOnuDbaReportQueueId      Integer32,
        unisOnuDbaReportThreshold    Integer32,
        unisOnuDbaReportStatus       INTEGER
    }

unisOnuDbaReportQueueId OBJECT-TYPE
    SYNTAX      Integer32
    MAX-ACCESS  not-accessible
    STATUS      current
    DESCRIPTION
        "
        The DBA report queue ID.
        "
    ::= { unisOnuDbaReportEntry 1 }

unisOnuDbaReportThreshold OBJECT-TYPE
    SYNTAX      Integer32
    MAX-ACCESS  read-write
    STATUS      current
    DESCRIPTION
        "
        The threshold of the DBA report queue.
        the following is the queue ID and
        the related default threshold setting.
        1 - 0
        2 - 0
        3 - 0
        4 - 65535
        5 - 65535
        6 - 0
        7 - 0
        8 - 0
        "
    ::= { unisOnuDbaReportEntry 2 }

unisOnuDbaReportStatus OBJECT-TYPE
    SYNTAX      INTEGER
        {
            enable(1),
            disable(2)
        }
    MAX-ACCESS  read-write
    STATUS      current
    DESCRIPTION
        "
        enable  -threshold configuration is active for the queue.
        disable -threshold configuration is not active for the queue.
        "
    DEFVAL { disable }
    ::= { unisOnuDbaReportEntry 3 }

--
-- unisOnuCosToLocalPrecedenceTable
--

unisOnuCosToLocalPrecedenceTable OBJECT-TYPE
    SYNTAX      SEQUENCE OF UnisOnuCosToLocalPrecedenceEntry
    MAX-ACCESS  not-accessible
    STATUS      current
    DESCRIPTION
        "Table of map of the COS to local-precedence."
    ::= { unisEponOnuMan 27 }

unisOnuCosToLocalPrecedenceEntry OBJECT-TYPE
    SYNTAX      UnisOnuCosToLocalPrecedenceEntry
    MAX-ACCESS  not-accessible
    STATUS      current
    DESCRIPTION
        "Configuration information of map of the COS to local precedence."
    INDEX
        {
            ifIndex,
            unisOnuCosToLocalPrecedenceCosIndex
        }
    ::= { unisOnuCosToLocalPrecedenceTable 1 }

UnisOnuCosToLocalPrecedenceEntry ::= SEQUENCE
    {
        unisOnuCosToLocalPrecedenceCosIndex    Integer32,
        unisOnuCosToLocalPrecedenceValue       Integer32
    }

unisOnuCosToLocalPrecedenceCosIndex OBJECT-TYPE
    SYNTAX      Integer32(0..7)
    MAX-ACCESS  read-only
    STATUS      current
    DESCRIPTION
        "Index of the map, obtains from packet cos value."
    ::={ unisOnuCosToLocalPrecedenceEntry 1 }

unisOnuCosToLocalPrecedenceValue OBJECT-TYPE
    SYNTAX      Integer32(0..3)
    MAX-ACCESS  read-write
    STATUS      current
    DESCRIPTION
        "Value of local precedence."
    ::={ unisOnuCosToLocalPrecedenceEntry 2 }

--
-- unisEponOnuStpPortTable
--

unisEponOnuStpPortTable OBJECT-TYPE
    SYNTAX      SEQUENCE OF UnisEponOnuStpPortEntry
    MAX-ACCESS  not-accessible
    STATUS      current
    DESCRIPTION
        "Table of ONU STP ports."
    ::= { unisEponOnuMan 28 }

unisEponOnuStpPortEntry OBJECT-TYPE
    SYNTAX      UnisEponOnuStpPortEntry
    MAX-ACCESS  not-accessible
    STATUS      current
    DESCRIPTION
        "Configuration information of ONU STP ports."
    INDEX
        {
            ifIndex,
            unisEponStpPortIndex
        }
    ::= { unisEponOnuStpPortTable 1 }

UnisEponOnuStpPortEntry ::= SEQUENCE
    {
        unisEponStpPortIndex     Integer32,
        unisEponStpPortDescr     OCTET STRING,
        unisEponStpPortState     INTEGER
    }

unisEponStpPortIndex OBJECT-TYPE
    SYNTAX      Integer32(0..144)
    MAX-ACCESS  accessible-for-notify
    STATUS      current
    DESCRIPTION
        "The index of the STP ports."
    ::={ unisEponOnuStpPortEntry 1 }

unisEponStpPortDescr OBJECT-TYPE
    SYNTAX      OCTET STRING
    MAX-ACCESS  read-only
    STATUS      current
    DESCRIPTION
        "The description of the STP ports."
    ::={ unisEponOnuStpPortEntry 2 }

unisEponStpPortState OBJECT-TYPE
    SYNTAX      INTEGER
        {
            disabled(1),
            discarding(2),
            learning(3),
            forwarding(4)
        }
    MAX-ACCESS  read-only
    STATUS      current
    DESCRIPTION
        "The current state of the port (i.e. disabled, discarding,
         learning and forwarding)."
    ::={ unisEponOnuStpPortEntry 3 }

--
-- unisOnuPhysicalTable
--

unisOnuPhysicalTable OBJECT-TYPE
    SYNTAX      SEQUENCE OF UnisOnuPhysicalEntry
    MAX-ACCESS  not-accessible
    STATUS      current
    DESCRIPTION
        "
        This table is used for getting ONU physical information.
        "
    ::= { unisEponOnuMan 29 }

unisOnuPhysicalEntry OBJECT-TYPE
    SYNTAX      UnisOnuPhysicalEntry
    MAX-ACCESS  not-accessible
    STATUS      current
    DESCRIPTION
        "
        The entry of the unisOnuPhysicalTable.
        "
    INDEX
        {
            ifIndex
        }
    ::= { unisOnuPhysicalTable 1 }

UnisOnuPhysicalEntry ::= SEQUENCE
    {
        unisOnuBridgeMac         MacAddress,
        unisOnuFirstPonMac       MacAddress,
        unisOnuFirstPonRegState  INTEGER,
        unisOnuSecondPonMac      MacAddress,
        unisOnuSecondPonRegState INTEGER
    }

unisOnuBridgeMac OBJECT-TYPE
    SYNTAX      MacAddress
    MAX-ACCESS  read-only
    STATUS      current
    DESCRIPTION
        "
        The bridge MAC address of ONU.
        "
    ::= { unisOnuPhysicalEntry 1 }

unisOnuFirstPonMac OBJECT-TYPE
    SYNTAX      MacAddress
    MAX-ACCESS  read-only
    STATUS      current
    DESCRIPTION
        "
        The MAC address of ONU first PON port.
        "
    ::= { unisOnuPhysicalEntry 2 }

unisOnuFirstPonRegState OBJECT-TYPE
    SYNTAX      INTEGER
        {
            notExist(1),
            absent(2),
            offline(3),
            silent(4),
            down(5),
            up(6)
        }
    MAX-ACCESS  read-only
    STATUS      current
    DESCRIPTION
        "
        The register state of ONU first PON port.
        "
    ::= { unisOnuPhysicalEntry 3 }

unisOnuSecondPonMac OBJECT-TYPE
    SYNTAX      MacAddress
    MAX-ACCESS  read-only
    STATUS      current
    DESCRIPTION
        "
        The MAC address of ONU second PON port.
        "
    ::= { unisOnuPhysicalEntry 4 }

unisOnuSecondPonRegState OBJECT-TYPE
    SYNTAX      INTEGER
        {
            notExist(1),
            absent(2),
            offline(3),
            silent(4),
            down(5),
            up(6)
        }
    MAX-ACCESS  read-only
    STATUS      current
    DESCRIPTION
        "
        The register state of ONU second PON port.
        "
    ::= { unisOnuPhysicalEntry 5 }

--
-- unisOnuSmlkTable
--

unisOnuSmlkTable OBJECT-TYPE
    SYNTAX      SEQUENCE OF UnisOnuSmlkEntry
    MAX-ACCESS  not-accessible
    STATUS      current
    DESCRIPTION
        "
        This table is used for getting ONU SMLK information.
        "
    ::= { unisEponOnuMan 30 }

unisOnuSmlkEntry OBJECT-TYPE
    SYNTAX      UnisOnuSmlkEntry
    MAX-ACCESS  not-accessible
    STATUS      current
    DESCRIPTION
        "
        The entry of the unisOnuSmlkTable.
        "
    INDEX
        {
            ifIndex,
            unisOnuSmlkGroupID
        }
    ::= { unisOnuSmlkTable 1 }

UnisOnuSmlkEntry ::= SEQUENCE
    {
        unisOnuSmlkGroupID            Integer32,
        unisOnuSmlkFirstPonRole       INTEGER,
        unisOnuSmlkFirstPonStatus     INTEGER,
        unisOnuSmlkSecondPonRole      INTEGER,
        unisOnuSmlkSecondPonStatus    INTEGER
    }

unisOnuSmlkGroupID OBJECT-TYPE
    SYNTAX      Integer32
    MAX-ACCESS  read-only
    STATUS      current
    DESCRIPTION
        "
        The SMLK group ID of ONU.
        "
    ::= { unisOnuSmlkEntry 1 }

unisOnuSmlkFirstPonRole OBJECT-TYPE
    SYNTAX      INTEGER
        {
            master(1),
            slave(2),
            null(3)
        }
    MAX-ACCESS  read-only
    STATUS      current
    DESCRIPTION
        "
        The role of ONU first PON port in a SMLK group.
        "
    ::= { unisOnuSmlkEntry 2 }

unisOnuSmlkFirstPonStatus OBJECT-TYPE
    SYNTAX      INTEGER
        {
            active(1),
            standby(2),
            down(3),
            null(4)
        }
    MAX-ACCESS  read-only
    STATUS      current
    DESCRIPTION
        "
        The transmitting status of ONU first PON port in a SMLK group.
        "
    ::= { unisOnuSmlkEntry 3 }

unisOnuSmlkSecondPonRole OBJECT-TYPE
    SYNTAX      INTEGER
        {
            master(1),
            slave(2),
            null(3)
        }
    MAX-ACCESS  read-only
    STATUS      current
    DESCRIPTION
        "
        The role of ONU second PON port in a SMLK group.
        "
    ::= { unisOnuSmlkEntry 4 }

unisOnuSmlkSecondPonStatus OBJECT-TYPE
    SYNTAX      INTEGER
        {
            active(1),
            standby(2),
            down(3),
            null(4)
        }
    MAX-ACCESS  read-only
    STATUS      current
    DESCRIPTION
        "
        The transmitting status of ONU second PON port in a SMLK group.
        "
    ::= { unisOnuSmlkEntry 5 }

--
-- unisOnuRS485PropertiesTable
--

unisOnuRS485PropertiesTable OBJECT-TYPE
    SYNTAX      SEQUENCE OF UnisOnuRS485PropertiesEntry
    MAX-ACCESS  not-accessible
    STATUS      current
    DESCRIPTION
            "Property table."
    ::= { unisEponOnuMan 31 }

unisOnuRS485PropertiesEntry OBJECT-TYPE
    SYNTAX          UnisOnuRS485PropertiesEntry
    MAX-ACCESS      not-accessible
    STATUS          current
    DESCRIPTION
            "The entry of property table."
    INDEX      {
                ifIndex,
                unisOnuRS485SerialIndex
               }
    ::= { unisOnuRS485PropertiesTable 1 }

UnisOnuRS485PropertiesEntry ::=
    SEQUENCE{
        unisOnuRS485SerialIndex
            Integer32,
        unisOnuRS485BaudRate
            INTEGER,
        unisOnuRS485DataBits
            INTEGER,
        unisOnuRS485Parity
            INTEGER,
        unisOnuRS485StopBits
            INTEGER,
        unisOnuRS485FlowControl
            INTEGER,
        unisOnuRS485TXOctets
            Integer32,
        unisOnuRS485RXOctets
            Integer32,
        unisOnuRS485TXErrOctets
            Integer32,
        unisOnuRS485RXErrOctets
            Integer32,
        unisOnuRS485ResetStatistics
            INTEGER
    }

unisOnuRS485SerialIndex OBJECT-TYPE
    SYNTAX          Integer32 (1..64)
    MAX-ACCESS      not-accessible
    STATUS          current
    DESCRIPTION
        "The index of serial port."
    ::= { unisOnuRS485PropertiesEntry 1 }

unisOnuRS485BaudRate OBJECT-TYPE
    SYNTAX          INTEGER {
                        baudRate300(1),
                        baudRate600(2),
                        baudRate1200(3),
                        baudRate2400(4),
                        baudRate4800(5),
                        baudRate9600(6),
                        baudRate19200(7),
                        baudRate38400(8),
                        baudRate57600(9),
                        baudRate115200(10)
                        }
    MAX-ACCESS      read-write
    STATUS          current
    DESCRIPTION
            "The port baud rate."
    DEFVAL          { baudRate9600 }
    ::= { unisOnuRS485PropertiesEntry 2 }

unisOnuRS485DataBits OBJECT-TYPE
    SYNTAX          INTEGER {
                        five(1),            -- 5 data bits
                        six(2),             -- 6 data bits
                        seven(3),           -- 7 data bits
                        eight(4)            -- 8 data bits
                    }
    UNITS           "bit"
    MAX-ACCESS      read-write
    STATUS          current
    DESCRIPTION
            "The port number of data bits in a character."
    DEFVAL          { eight }
    ::= { unisOnuRS485PropertiesEntry 3 }

unisOnuRS485Parity OBJECT-TYPE
    SYNTAX          INTEGER {
                        none(1),
                        odd(2),
                        even(3),
                        mark(4),
                        space(5)
                    }
    MAX-ACCESS      read-write
    STATUS          current
    DESCRIPTION
            "The port sense of a character parity bit."
    DEFVAL          { none }
    ::= { unisOnuRS485PropertiesEntry 4 }

unisOnuRS485StopBits OBJECT-TYPE
    SYNTAX          INTEGER {
                        one(1),               -- 1 stop bit
                        two(2),               -- 2 stop bits
                        oneAndHalf(3)         -- 1.5 stop bits
                    }
    UNITS           "bit"
    MAX-ACCESS      read-write
    STATUS          current
    DESCRIPTION
            "The port number of stop bits."
    DEFVAL          { one }
    ::= { unisOnuRS485PropertiesEntry 5 }

unisOnuRS485FlowControl OBJECT-TYPE
    SYNTAX          INTEGER{
                        none(1),
                        hardware(2),
                        xonOrxoff(3)
                    }
    MAX-ACCESS      read-write
    STATUS          current
    DESCRIPTION
            "The port type of input flow control.
             'none' indicates no flow control at this level.
             'hardware' indicates using hardware signals.
             'xonOrxoff' indicates using software function."
    DEFVAL          { none }
    ::= { unisOnuRS485PropertiesEntry 6 }

unisOnuRS485TXOctets OBJECT-TYPE
    SYNTAX          Integer32
    MAX-ACCESS      read-only
    STATUS          current
    DESCRIPTION
            "The number of output octets about the port.
             The unit is byte."
    ::= { unisOnuRS485PropertiesEntry 7 }

unisOnuRS485RXOctets OBJECT-TYPE
    SYNTAX          Integer32
    MAX-ACCESS      read-only
    STATUS          current
    DESCRIPTION
            "The number of input octets about the port.
             The unit is byte."
    ::= { unisOnuRS485PropertiesEntry 8 }

unisOnuRS485TXErrOctets OBJECT-TYPE
    SYNTAX          Integer32
    MAX-ACCESS      read-only
    STATUS          current
    DESCRIPTION
            "The number of output error octets about the port.
             The unit is byte."
    ::= { unisOnuRS485PropertiesEntry 9 }

unisOnuRS485RXErrOctets OBJECT-TYPE
    SYNTAX          Integer32
    MAX-ACCESS      read-only
    STATUS          current
    DESCRIPTION
            "The number of input error octets about the port.
             The unit is byte."
    ::= { unisOnuRS485PropertiesEntry 10 }

unisOnuRS485ResetStatistics OBJECT-TYPE
    SYNTAX          INTEGER {
                        counting(1),
                        clear(2)
                    }
    MAX-ACCESS      read-write
    STATUS          current
    DESCRIPTION
            "Reset the counters to zero, including unisOnuRS485TXOctets,
             unisOnuRS485RXOctets, unisOnuRS485TXErrOctets and
             unisOnuRS485RXErrOctets."
    DEFVAL          { counting }
    ::= { unisOnuRS485PropertiesEntry 11 }

--
-- unisOnuRS485SessionSummaryTable
--

unisOnuRS485SessionSummaryTable OBJECT-TYPE
    SYNTAX      SEQUENCE OF UnisOnuRS485SessionSummaryEntry
    MAX-ACCESS  not-accessible
    STATUS      current
    DESCRIPTION
            "Session summary table."
    ::= { unisEponOnuMan 32 }

unisOnuRS485SessionSummaryEntry OBJECT-TYPE
    SYNTAX          UnisOnuRS485SessionSummaryEntry
    MAX-ACCESS      not-accessible
    STATUS          current
    DESCRIPTION
            "The entry of session summary table."
    INDEX      {
                ifIndex,
                unisOnuRS485SerialIndex
               }
    ::= { unisOnuRS485SessionSummaryTable 1 }

UnisOnuRS485SessionSummaryEntry ::=
    SEQUENCE{
        unisOnuRS485SessionMaxNum
            Integer32,
        unisOnuRS485SessionNextIndex
            Integer32
            }

unisOnuRS485SessionMaxNum OBJECT-TYPE
    SYNTAX          Integer32 (1..64)
    MAX-ACCESS      read-only
    STATUS          current
    DESCRIPTION
            "The max session number of every serial port
             which can be supported."
    ::= { unisOnuRS485SessionSummaryEntry 1 }

unisOnuRS485SessionNextIndex OBJECT-TYPE
    SYNTAX          Integer32 (0..64)
    MAX-ACCESS      read-only
    STATUS          current
    DESCRIPTION
            "The next valid index used for creating a new session raw.
             When there is no valid index left, it will return 0.
            "
    ::= { unisOnuRS485SessionSummaryEntry 2 }

--
-- unisOnuRS485SessionTable
--

unisOnuRS485SessionTable OBJECT-TYPE
    SYNTAX      SEQUENCE OF UnisOnuRS485SessionEntry
    MAX-ACCESS  not-accessible
    STATUS      current
    DESCRIPTION
            "RS485 raw session table.  Data received from RS485 will be sent
            to the destination by raw sockets.
            "
    ::= { unisEponOnuMan 33 }

unisOnuRS485SessionEntry OBJECT-TYPE
    SYNTAX          UnisOnuRS485SessionEntry
    MAX-ACCESS      not-accessible
    STATUS          current
    DESCRIPTION
            "The entry of session table."
    INDEX      {
                ifIndex,
                unisOnuRS485SerialIndex,
                unisOnuRS485SessionIndex
               }
    ::= { unisOnuRS485SessionTable 1 }

UnisOnuRS485SessionEntry ::=
    SEQUENCE{
        unisOnuRS485SessionIndex
            Integer32,
        unisOnuRS485SessionType
            INTEGER,
        unisOnuRS485SessionAddType
            InetAddressType,
        unisOnuRS485SessionRemoteIP
            InetAddress,
        unisOnuRS485SessionRemotePort
            Integer32,
        unisOnuRS485SessionLocalPort
            Integer32,
        unisOnuRS485SessionRowStatus
            RowStatus
    }

unisOnuRS485SessionIndex OBJECT-TYPE
    SYNTAX          Integer32 (1..64)
    MAX-ACCESS      not-accessible
    STATUS          current
    DESCRIPTION
            "Raw session index."
    ::= { unisOnuRS485SessionEntry 1 }

unisOnuRS485SessionType OBJECT-TYPE
    SYNTAX          INTEGER {
                        udp(1),
                        tcpClient(2),
                        tcpServer(3)
                    }
    MAX-ACCESS      read-create
    STATUS          current
    DESCRIPTION
            "The type of a session.
             A session can use UDP socket, TCP socket as a client,
             or TCP socket as a server."
    ::= { unisOnuRS485SessionEntry 2 }

unisOnuRS485SessionAddType OBJECT-TYPE
    SYNTAX          InetAddressType
    MAX-ACCESS      read-create
    STATUS          current
    DESCRIPTION
            "This object indicates the transport type of the
             address contained in unisOnuRS485SessionRemoteIP object."
    ::= { unisOnuRS485SessionEntry 3 }

unisOnuRS485SessionRemoteIP OBJECT-TYPE
    SYNTAX          InetAddress
    MAX-ACCESS      read-create
    STATUS          current
    DESCRIPTION
            "The IP of remote landing.
            When session type is 'udp', this is the peer IP.
            When session type is 'tcpClient', this is the server IP.
            When session type is 'tcpServer', this is invalid.
            "
    ::= { unisOnuRS485SessionEntry 4 }

unisOnuRS485SessionRemotePort OBJECT-TYPE
    SYNTAX          Integer32 (1024..65535)
    MAX-ACCESS      read-create
    STATUS          current
    DESCRIPTION
            "The port of remote landing.
            When session type is 'udp', this is the peer port.
            When session type is 'tcpClient', this is the server port.
            When session type is 'tcpServer', this is invalid.
            "
    ::= { unisOnuRS485SessionEntry 5 }

unisOnuRS485SessionLocalPort OBJECT-TYPE
    SYNTAX          Integer32 (1024..65535)
    MAX-ACCESS      read-create
    STATUS          current
    DESCRIPTION
            "Local socket port.
            When session type is 'udp', this is local UDP socket port.
            When session type is 'tcpClient', this is invalid.
            When session type is 'tcpServer', this is the local port which
            will be listened.
            "
    ::= { unisOnuRS485SessionEntry 6 }

unisOnuRS485SessionRowStatus OBJECT-TYPE
    SYNTAX          RowStatus
    MAX-ACCESS      read-create
    STATUS          current
    DESCRIPTION
            "The status used for creating,
            modifying, and deleting instances of
            the columnar objects in raw session table."
    ::= { unisOnuRS485SessionEntry 7 }

--
-- unisOnuRS485SessionErrInfoTable
--

unisOnuRS485SessionErrInfoTable OBJECT-TYPE
    SYNTAX      SEQUENCE OF UnisOnuRS485SessionErrInfoEntry
    MAX-ACCESS  not-accessible
    STATUS      current
    DESCRIPTION
            "Error information table.  When failed to create a session,
             error information can be got from this table."
    ::= { unisEponOnuMan 34 }

unisOnuRS485SessionErrInfoEntry OBJECT-TYPE
    SYNTAX          UnisOnuRS485SessionErrInfoEntry
    MAX-ACCESS      not-accessible
    STATUS          current
    DESCRIPTION
            "The entry of error information table."
    INDEX      {
                ifIndex,
                unisOnuRS485SerialIndex,
                unisOnuRS485SessionIndex
               }
    ::= { unisOnuRS485SessionErrInfoTable 1 }

UnisOnuRS485SessionErrInfoEntry ::=
    SEQUENCE{
        unisOnuRS485SessionErrInfo
            DisplayString
    }

unisOnuRS485SessionErrInfo OBJECT-TYPE
    SYNTAX          DisplayString
    MAX-ACCESS      read-only
    STATUS          current
    DESCRIPTION
        "Error information string.  When a response with 'noCreeation' for
        row creation in table unisOnuRS485SessionTable,
        the error reason can be got from this object."
    ::= { unisOnuRS485SessionErrInfoEntry 1 }

--
-- unisOnuDbaReport2Table
--

unisOnuDbaReport2Table OBJECT-TYPE
    SYNTAX      SEQUENCE OF UnisOnuDbaReport2Entry
    MAX-ACCESS  not-accessible
    STATUS      current
    DESCRIPTION
        "
        This table defines the information of DBA(dynamic bandwidth allocation)
        report threshold contained in the MPCP report frames.
        "
    ::= { unisEponOnuMan 35 }

unisOnuDbaReport2Entry OBJECT-TYPE
    SYNTAX      UnisOnuDbaReport2Entry
    MAX-ACCESS  not-accessible
    STATUS      current
    DESCRIPTION
        "
        The entry of the table unisOnuDbaReport2Table.
        "
    INDEX
        {
            ifIndex,
            unisOnuDbaReport2QueueSetId,
            unisOnuDbaReport2QueueId
        }
    ::= { unisOnuDbaReport2Table 1 }

UnisOnuDbaReport2Entry ::= SEQUENCE
    {
        unisOnuDbaReport2QueueSetId   Integer32,
        unisOnuDbaReport2QueueId      Integer32,
        unisOnuDbaReport2Threshold    Integer32,
        unisOnuDbaReport2Status       TruthValue
    }

unisOnuDbaReport2QueueSetId OBJECT-TYPE
    SYNTAX      Integer32 (1..3)
    MAX-ACCESS  not-accessible
    STATUS      current
    DESCRIPTION
        "
        The DBA report queue set ID.
        "
    ::= { unisOnuDbaReport2Entry 1 }

unisOnuDbaReport2QueueId OBJECT-TYPE
    SYNTAX      Integer32 (1..8)
    MAX-ACCESS  not-accessible
    STATUS      current
    DESCRIPTION
        "
        The DBA report queue ID.
        "
    ::= { unisOnuDbaReport2Entry 2 }

unisOnuDbaReport2Threshold OBJECT-TYPE
    SYNTAX      Integer32
    MAX-ACCESS  read-write
    STATUS      current
    DESCRIPTION
        "
        The thresholds of the DBA report queue.
        The following are the queue ID and
        the related default threshold settings.
        1 - 0
        2 - 0
        3 - 0
        4 - 65535
        5 - 65535
        6 - 0
        7 - 0
        8 - 0
        "
    ::= { unisOnuDbaReport2Entry 3 }

unisOnuDbaReport2Status OBJECT-TYPE
    SYNTAX      TruthValue
    MAX-ACCESS  read-write
    STATUS      current
    DESCRIPTION
        "
        true  -threshold configuration is active for the queue.
        false -threshold configuration is not active for the queue.
        "
    ::= { unisOnuDbaReport2Entry 4 }

--
-- unisOnuLoidInfoTable
--

unisOnuLoidInfoTable OBJECT-TYPE
    SYNTAX      SEQUENCE OF UnisOnuLoidInfoEntry
    MAX-ACCESS  not-accessible
    STATUS      current
    DESCRIPTION
        "
        This table is used for getting LOID information of an ONU.
        "
    ::= { unisEponOnuMan 36 }

unisOnuLoidInfoEntry OBJECT-TYPE
    SYNTAX      UnisOnuLoidInfoEntry
    MAX-ACCESS  not-accessible
    STATUS      current
    DESCRIPTION
        "
        The entry of the unisOnuLoidInfoTable.
        "
    INDEX
        {
            ifIndex,
            unisOnuLoidIndex
        }
    ::= { unisOnuLoidInfoTable 1 }

UnisOnuLoidInfoEntry ::= SEQUENCE
    {
        unisOnuLoidIndex      Integer32,
        unisOnuLoidFlag       INTEGER,
        unisOnuLoid           OCTET STRING
    }

unisOnuLoidIndex OBJECT-TYPE
    SYNTAX      Integer32
    MAX-ACCESS  not-accessible
    STATUS      current
    DESCRIPTION
        "
        The index of an ONU in one OLT.
        "
    ::= { unisOnuLoidInfoEntry 1 }

unisOnuLoidFlag OBJECT-TYPE
    SYNTAX      INTEGER
        {
            bound(1),
            registered(2),
            run(3),
            regIncorrect(4)
        }
    MAX-ACCESS  read-only
    STATUS      current
    DESCRIPTION
        "
        The flag of ONU status.
        1 - bound: The ONU is bound but not registered.
        2 - registered: The ONU is registered but not bound.
        3 - run: The ONU is registered and bound on one OLT.
        4 - regIncorrect: The ONU is bound on one OLT and registered on
        another OLT.
        "
    ::= { unisOnuLoidInfoEntry 2 }

unisOnuLoid OBJECT-TYPE
    SYNTAX      OCTET STRING(SIZE(1..24))
    MAX-ACCESS  read-only
    STATUS      current
    DESCRIPTION
        "
        The LOID of an ONU.
        "
    ::= { unisOnuLoidInfoEntry 3 }

--
-- unisOnuStatisticsTable
--

unisOnuStatisticsTable OBJECT-TYPE
    SYNTAX      SEQUENCE OF UnisOnuStatisticsEntry
    MAX-ACCESS  not-accessible
    STATUS      current
    DESCRIPTION
        "
        This table is used for enabling or disabling statistics and setting period of a PON.
        "
    ::= { unisEponOnuMan 37 }

unisOnuStatisticsEntry OBJECT-TYPE
    SYNTAX      UnisOnuStatisticsEntry
    MAX-ACCESS  not-accessible
    STATUS      current
    DESCRIPTION
        "
        The entry of the unisOnuStatisticsTable.
        "
    INDEX
        {
            ifIndex
        }
    ::= { unisOnuStatisticsTable 1 }

UnisOnuStatisticsEntry ::= SEQUENCE
    {
        unisOnuStatisticsPeriodVal  Unsigned32,
        unisOnuStatisticsEnable     TruthValue
    }

unisOnuStatisticsPeriodVal OBJECT-TYPE
    SYNTAX      Unsigned32
    MAX-ACCESS  read-write
    STATUS      current
    DESCRIPTION
        "
        PON statistics period value.
        "
    ::= { unisOnuStatisticsEntry 1 }

unisOnuStatisticsEnable OBJECT-TYPE
    SYNTAX      TruthValue
    MAX-ACCESS  read-write
    STATUS      current
    DESCRIPTION
        "
        Enable or disable statistics of a PON.
        true(1)  - alarm enable.
        false(2) - alarm disable.
        "
    ::= { unisOnuStatisticsEntry 2 }

unisOnuSlaMaxBandWidthMinVal10G OBJECT-TYPE
    SYNTAX      Integer32
    MAX-ACCESS  read-only
    STATUS      current
    DESCRIPTION
        "
        The lower limit of maximum-bandwidth which is confined to
        unisOnuSlaMaxBandWidth for 10G EPON."
    ::= { unisEponOnuMan 38 }

unisOnuSlaMaxBandWidthMaxVal10G OBJECT-TYPE
    SYNTAX      Integer32
    MAX-ACCESS  read-only
    STATUS      current
    DESCRIPTION
        "
        The upper limit of maximum-bandwidth which is confined to
        unisOnuSlaMaxBandWidth for 10G EPON."
    ::= { unisEponOnuMan 39 }

unisOnuSlaMinBandWidthMinVal10G OBJECT-TYPE
    SYNTAX      Integer32
    MAX-ACCESS  read-only
    STATUS      current
    DESCRIPTION
        "
        The lower limit of minimum-bandwidth which is confined to
        unisOnuSlaMinBandWidth for 10G EPON."
    ::= { unisEponOnuMan 40 }

unisOnuSlaMinBandWidthMaxVal10G OBJECT-TYPE
    SYNTAX      Integer32
    MAX-ACCESS  read-only
    STATUS      current
    DESCRIPTION
        "
        The upper limit of minimum-bandwidth which is confined to
        unisOnuSlaMinBandWidth for 10G EPON."
    ::= { unisEponOnuMan 41 }

--
-- unisOnuServiceSlaTable
--

unisOnuServiceSlaTable OBJECT-TYPE
    SYNTAX      SEQUENCE OF UnisOnuServiceSlaEntry
    MAX-ACCESS  not-accessible
    STATUS      current
    DESCRIPTION
        "
        This table is used for setting the service SLA mode and applying the service SLA to an ONU.
        "
    ::= { unisEponOnuMan 42 }

unisOnuServiceSlaEntry OBJECT-TYPE
    SYNTAX      UnisOnuServiceSlaEntry
    MAX-ACCESS  not-accessible
    STATUS      current
    DESCRIPTION
        "
        The entry of the unisOnuServiceSlaTable.
        "
    INDEX
        {
            ifIndex
        }
    ::= { unisOnuServiceSlaTable 1 }

UnisOnuServiceSlaEntry ::= SEQUENCE
    {
        unisSlaSchedulingMode       INTEGER,
        unisSlaHighPrioBoundary     Integer32,
        unisSlaCycleLength          Integer32,
        unisSlaApply                TruthValue
    }

unisSlaSchedulingMode OBJECT-TYPE
    SYNTAX      INTEGER
        {
            sp(0),
            wrr(1),
            spWrr(2),
            invalid(3)
        }
    MAX-ACCESS  read-write
    STATUS      current
    DESCRIPTION
        "
        Service SLA scheduling mode.
        "
    DEFVAL { invalid }
    ::= { unisOnuServiceSlaEntry 1 }

unisSlaHighPrioBoundary OBJECT-TYPE
    SYNTAX      Integer32
    MAX-ACCESS  read-write
    STATUS      current
    DESCRIPTION
        "
        Service SLA high priority boundary in SP-WRR mode.
        "
    ::= { unisOnuServiceSlaEntry 2 }

unisSlaCycleLength OBJECT-TYPE
    SYNTAX      Integer32(200..16777215)
    UNITS       "time quantums"
    MAX-ACCESS  read-write
    STATUS      current
    DESCRIPTION
        "
        Service SLA cycle length in time quantums.
        "
    DEFVAL { 62500 }
    ::= { unisOnuServiceSlaEntry 3 }

unisSlaApply OBJECT-TYPE
    SYNTAX      TruthValue
    MAX-ACCESS  read-write
    STATUS      current
    DESCRIPTION
        "
        Apply service SLA configuration.
        true(1)  - Apply.
        false(2) - Not apply.
        "
    DEFVAL { false }
    ::= { unisOnuServiceSlaEntry 4 }

--
-- unisOnuServiceSlaQueTable
--

unisOnuServiceSlaQueTable OBJECT-TYPE
    SYNTAX      SEQUENCE OF UnisOnuServiceSlaQueEntry
    MAX-ACCESS  not-accessible
    STATUS      current
    DESCRIPTION
        "
        This table is used for configuring service SLA queues.
        "
    ::= { unisEponOnuMan 43 }

unisOnuServiceSlaQueEntry OBJECT-TYPE
    SYNTAX      UnisOnuServiceSlaQueEntry
    MAX-ACCESS  not-accessible
    STATUS      current
    DESCRIPTION
        "
        The entry of the unisOnuServiceSlaQueTable.
        "
    INDEX
        {
            ifIndex,
            unisSlaQueId
        }
    ::= { unisOnuServiceSlaQueTable 1 }

UnisOnuServiceSlaQueEntry ::= SEQUENCE
    {
        unisSlaQueId                Integer32,
        unisSlaQueMode              INTEGER,
        unisSlaQueWeight            Integer32,
        unisSlaQueFixPktSize        Integer32,
        unisSlaQueFixBandwidth      Integer32,
        unisSlaQueGuaBandwidth      Integer32,
        unisSlaQueBstBandwidth      Integer32,
        unisSlaQueRowStatus         RowStatus
    }

unisSlaQueId OBJECT-TYPE
    SYNTAX      Integer32
    MAX-ACCESS  not-accessible
    STATUS      current
    DESCRIPTION
        "
        Service SLA queue ID.
        "
    ::= { unisOnuServiceSlaQueEntry 1 }

unisSlaQueMode OBJECT-TYPE
    SYNTAX      INTEGER
        {
            sp(0),
            wrr(1)
        }
    MAX-ACCESS  read-create
    STATUS      current
    DESCRIPTION
        "
        Service SLA queue mode.
        "
    ::= { unisOnuServiceSlaQueEntry 2 }

unisSlaQueWeight OBJECT-TYPE
    SYNTAX      Integer32(0..100)
    MAX-ACCESS  read-create
    STATUS      current
    DESCRIPTION
        "
        Service SLA queue weight in WRR mode.
        "
    ::= { unisOnuServiceSlaQueEntry 3 }

unisSlaQueFixPktSize OBJECT-TYPE
    SYNTAX      Integer32(0..2000)
    UNITS       "bytes"
    MAX-ACCESS  read-create
    STATUS      current
    DESCRIPTION
        "
        Service SLA queue fixed packet size in bytes.
        "
    DEFVAL { 0 }
    ::= { unisOnuServiceSlaQueEntry 4 }

unisSlaQueFixBandwidth OBJECT-TYPE
    SYNTAX      Integer32
    UNITS       "kbps"
    MAX-ACCESS  read-create
    STATUS      current
    DESCRIPTION
        "
        Service SLA queue fixed bandwidth in kbps,
        which will be rounded down to the nearest multiple of 256.
        "
    ::= { unisOnuServiceSlaQueEntry 5 }

unisSlaQueGuaBandwidth OBJECT-TYPE
    SYNTAX      Integer32
    UNITS       "kbps"
    MAX-ACCESS  read-create
    STATUS      current
    DESCRIPTION
        "
        Service SLA queue guaranteed bandwidth in kbps,
        which will be rounded down to the nearest multiple of 256.
        "
    ::= { unisOnuServiceSlaQueEntry 6 }

unisSlaQueBstBandwidth OBJECT-TYPE
    SYNTAX      Integer32
    UNITS       "kbps"
    MAX-ACCESS  read-create
    STATUS      current
    DESCRIPTION
        "
        Service SLA queue best effort bandwidth in kbps,
        which will be rounded down to the nearest multiple of 256.
        "
    ::= { unisOnuServiceSlaQueEntry 7 }

unisSlaQueRowStatus OBJECT-TYPE
    SYNTAX      RowStatus
    MAX-ACCESS  read-create
    STATUS      current
    DESCRIPTION
        "
        The status of this table entry. Only active,
        createAndGo, and destroy are supported.
        "
    ::= { unisOnuServiceSlaQueEntry 8 }

--
-- unisOnuPoeTable
--

unisOnuPoeTable OBJECT-TYPE
    SYNTAX      SEQUENCE OF UnisOnuPoeEntry
    MAX-ACCESS  not-accessible
    STATUS      current
    DESCRIPTION
        "
        This table is used for configuring the PoE function for ONUs.
        "
    ::= { unisEponOnuMan 44 }

unisOnuPoeEntry OBJECT-TYPE
    SYNTAX      UnisOnuPoeEntry
    MAX-ACCESS  not-accessible
    STATUS      current
    DESCRIPTION
        "
        The entry of the unisOnuPoeTable.
        "
    INDEX
        {
            ifIndex
        }
    ::= { unisOnuPoeTable 1 }

UnisOnuPoeEntry ::= SEQUENCE
    {
        unisOnuPoeEnable            TruthValue,
        unisOnuPoeMode              INTEGER,
        unisOnuPoeMaxPowerClass     INTEGER,
        unisOnuPoeMaxPowerValue     Integer32,
        unisOnuPoeLegacyEnable      TruthValue
    }

unisOnuPoeEnable OBJECT-TYPE
    SYNTAX      TruthValue
    MAX-ACCESS  read-write
    STATUS      current
    DESCRIPTION
        "
        Enable PoE for an ONU.
        "
    DEFVAL { true }
    ::= { unisOnuPoeEntry 1 }

unisOnuPoeMode OBJECT-TYPE
    SYNTAX      INTEGER
        {
            signal(0),
            spare(1)
        }
    MAX-ACCESS  read-write
    STATUS      current
    DESCRIPTION
        "
        Set the PoE mode for an ONU.
        "
    DEFVAL { 0 }
    ::= { unisOnuPoeEntry 2 }

unisOnuPoeMaxPowerClass OBJECT-TYPE
    SYNTAX      INTEGER
        {
            default(0),
            class0(1),
            class1(2),
            class2(3),
            class3(4),
            class4(5),
            undefined(255)
        }
    MAX-ACCESS  read-write
    STATUS      current
    DESCRIPTION
        "
        Set the PoE max power class for an ONU.
        "
    DEFVAL { 0 }
    ::= { unisOnuPoeEntry 3 }

unisOnuPoeMaxPowerValue OBJECT-TYPE
    SYNTAX      Integer32
    UNITS       "mW"
    MAX-ACCESS  read-write
    STATUS      current
    DESCRIPTION
        "
        Set the PoE max power value for an ONU.
        "
    DEFVAL { 0 }
    ::= { unisOnuPoeEntry 4 }

unisOnuPoeLegacyEnable OBJECT-TYPE
    SYNTAX      TruthValue
    MAX-ACCESS  read-write
    STATUS      current
    DESCRIPTION
        "
        Enable the PoE legacy PD detection for an ONU.
        "
    ::= { unisOnuPoeEntry 5 }

--
-- unisEponBatchOperationBySlotTable
--

unisEponBatchOperationBySlotTable OBJECT-TYPE
    SYNTAX      SEQUENCE OF UnisEponBatchOperationBySlotEntry
    MAX-ACCESS  not-accessible
    STATUS      current
    DESCRIPTION
        "
        This table is used for batch operation by slot.
        "
    ::= { unisEponBatchOperationMan 1 }

unisEponBatchOperationBySlotEntry OBJECT-TYPE
    SYNTAX      UnisEponBatchOperationBySlotEntry
    MAX-ACCESS  not-accessible
    STATUS      current
    DESCRIPTION
        "
        The entry of the unisEponBatchOperationBySlotTable.
        "
    INDEX
        {
            unisEponBatchOperationBySlotIndex
        }
    ::= { unisEponBatchOperationBySlotTable 1 }

UnisEponBatchOperationBySlotEntry ::= SEQUENCE
    {
        unisEponBatchOperationBySlotIndex     Integer32,
        unisEponBatchOperationBySlotType      INTEGER,
        unisEponBatchOperationBySlot          INTEGER,
        unisEponBatchOperationBySlotResult    Integer32,
        unisEponBatchOpBySlotBindType         BITS
    }

unisEponBatchOperationBySlotIndex OBJECT-TYPE
    SYNTAX      Integer32
    MAX-ACCESS  not-accessible
    STATUS      current
    DESCRIPTION
        "
        The EPON board index.
        "
    ::= { unisEponBatchOperationBySlotEntry 1 }

unisEponBatchOperationBySlotType OBJECT-TYPE
    SYNTAX      INTEGER
        {
            resetUnknown(1),
            updateDba(9),
            updateONU(10)
        }
    MAX-ACCESS  read-write
    STATUS      current
    DESCRIPTION
        "
        The types of batch operation by slot:
        1  - resetUnknown, the object value is not set.
        9  - updateDba, update OLT DBA algorithm.
        Config the MIB object module unisEponDbaUpdateFileName.
        10 - updateONU, update ONU firmware.
        Config the MIB object module unisEponOnuUpdateFileName
        with the filename of ONU firmware first.
        "
    ::= { unisEponBatchOperationBySlotEntry 2 }

unisEponBatchOperationBySlot OBJECT-TYPE
    SYNTAX      INTEGER
        {
            batOpBySlot(1)
        }
    MAX-ACCESS  read-write
    STATUS      current
    DESCRIPTION
        "
        Execute batch operation.
        "
    ::= { unisEponBatchOperationBySlotEntry 3 }

unisEponBatchOperationBySlotResult OBJECT-TYPE
    SYNTAX      Integer32
    MAX-ACCESS  read-only
    STATUS      current
    DESCRIPTION
        "
        The result of batch operation.
        0xFFFF - other, general error.
        1 - working, operation is not completed.
        2 - successful, completed successfully.
        3 - failed because the DBA source file does not exist.
        4 - failed because the ONU firmware file does not exist.
        5 - failed because of not set the filename of DBA source.
        6 - failed because of not set the filename of ONU firmware.
        7 - failed because of not set slottype.
        "
    ::= { unisEponBatchOperationBySlotEntry 4 }

unisEponBatchOpBySlotBindType OBJECT-TYPE
    SYNTAX      BITS
        {
            mac(0),
            loid(1),
            loidPassword(2)
        }
    MAX-ACCESS  read-write
    STATUS      current
    DESCRIPTION
        "
        Set batch binding type, which can only be assigned one type.
        "
    ::= { unisEponBatchOperationBySlotEntry 5 }

--
-- unisEponBatchOperationByOLTTable
--

unisEponBatchOperationByOLTTable OBJECT-TYPE
    SYNTAX      SEQUENCE OF UnisEponBatchOperationByOLTEntry
    MAX-ACCESS  not-accessible
    STATUS      current
    DESCRIPTION
        "
        This table is used for batch operation by OLT.
        "
    ::= { unisEponBatchOperationMan 2 }

unisEponBatchOperationByOLTEntry OBJECT-TYPE
    SYNTAX      UnisEponBatchOperationByOLTEntry
    MAX-ACCESS  not-accessible
    STATUS      current
    DESCRIPTION
        "
        The entry of the unisEponBatchOperationByOLTTable.
        "
    INDEX
        {
            ifIndex
        }
    ::= { unisEponBatchOperationByOLTTable 1 }

UnisEponBatchOperationByOLTEntry ::= SEQUENCE
    {
        unisEponBatchOperationByOLTType      INTEGER,
        unisEponBatchOperationByOLT          INTEGER,
        unisEponBatchOperationByOLTResult    Integer32
    }

unisEponBatchOperationByOLTType OBJECT-TYPE
    SYNTAX      INTEGER
        {
            resetUnknown(1),
            updateONU(5)
        }
    MAX-ACCESS  read-write
    STATUS      current
    DESCRIPTION
        "
        The types of batch operation by OLT(operation for all ONUs in the
        OLT):
        1 -- resetUnknown, the object value is not set.
        5 -- updateONU, update ONU firmware.
        configure the MIB object module unisEponOnuUpdateFileName
        with the filename of ONU firmware first.
        "
    ::= { unisEponBatchOperationByOLTEntry 1 }

unisEponBatchOperationByOLT OBJECT-TYPE
    SYNTAX      INTEGER
        {
            batOpByOlt(1)
        }
    MAX-ACCESS  read-write
    STATUS      current
    DESCRIPTION
        "
        Execute batch operation.
        "
    ::= { unisEponBatchOperationByOLTEntry 2 }

unisEponBatchOperationByOLTResult OBJECT-TYPE
    SYNTAX      Integer32
    MAX-ACCESS  read-only
    STATUS      current
    DESCRIPTION
        "
        The result of batch operation:
        0xFFFF -- other, general error.
        1 -- working, operation is not completed.
        2 -- successful, operation completed successfully.
        4 -- failed because the ONU firmware file does not exist.
        6 -- failed because of not set the filename of ONU firmware.
        7 -- failed because of not set olttype.
        "
    ::= { unisEponBatchOperationByOLTEntry 3 }

--
-- unisOnuFirmwareUpdateByTypeTable
--

unisOnuFirmwareUpdateByTypeTable OBJECT-TYPE
    SYNTAX      SEQUENCE OF UnisOnuFirmwareUpdateByTypeEntry
    MAX-ACCESS  not-accessible
    STATUS      current
    DESCRIPTION
        "
        This table is used to update ONU by ONU type.
        "
    ::= { unisEponBatchOperationMan 3 }

unisOnuFirmwareUpdateByTypeEntry OBJECT-TYPE
    SYNTAX      UnisOnuFirmwareUpdateByTypeEntry
    MAX-ACCESS  not-accessible
    STATUS      current
    DESCRIPTION
        "
        The entry of the unisOnuFirmwareUpdateByTypeTable.
        "
    INDEX
        {
            unisOnuUpdateByOnuTypeIndex
        }
    ::= { unisOnuFirmwareUpdateByTypeTable 1 }

UnisOnuFirmwareUpdateByTypeEntry ::= SEQUENCE
    {
        unisOnuUpdateByOnuTypeIndex     Integer32,
        unisOnuUpdateByTypeOnuType      OCTET STRING,
        unisOnuUpdateByTypeFileName     OCTET STRING,
        unisOnuUpdateByTypeRowStatus    RowStatus,
        unisOnuUpdateByTypeProtType     INTEGER
    }

unisOnuUpdateByOnuTypeIndex OBJECT-TYPE
    SYNTAX      Integer32
    MAX-ACCESS  not-accessible
    STATUS      current
    DESCRIPTION
        "
        The type and file relationship table entry index.
        "
    ::= { unisOnuFirmwareUpdateByTypeEntry 1 }

unisOnuUpdateByTypeOnuType OBJECT-TYPE
    SYNTAX      OCTET STRING(SIZE(0..15))
    MAX-ACCESS  read-create
    STATUS      current
    DESCRIPTION
        "
        The type of ONUs.
        "
    ::= { unisOnuFirmwareUpdateByTypeEntry 2 }

unisOnuUpdateByTypeFileName OBJECT-TYPE
    SYNTAX      OCTET STRING(SIZE(0..255))
    MAX-ACCESS  read-create
    STATUS      current
    DESCRIPTION
        "
        The file to be updated for the type of ONUs.
        "
    ::= { unisOnuFirmwareUpdateByTypeEntry 3 }

unisOnuUpdateByTypeRowStatus OBJECT-TYPE
    SYNTAX      RowStatus
    MAX-ACCESS  read-create
    STATUS      current
    DESCRIPTION
        "
        The status of this table entry.
        Only createAndGo and destroy actions are supported.
        "
    ::= { unisOnuFirmwareUpdateByTypeEntry 4 }

unisOnuUpdateByTypeProtType OBJECT-TYPE
    SYNTAX      INTEGER
        {
            private(0),
            ctc(1)
        }
    MAX-ACCESS  read-write
    STATUS      current
    DESCRIPTION
        "
        private(0): Using private protocol to update the ONU firmware.
        ctc(1): Using ctc standard protocol to update the ONU firmware.
        "
    DEFVAL { private }
    ::= { unisOnuFirmwareUpdateByTypeEntry 5 }

unisEponErrorInfo OBJECT IDENTIFIER ::= { unisEponMibObjects 7 }

unisEponSoftwareErrorCode OBJECT-TYPE
    SYNTAX      Integer32
    MAX-ACCESS  accessible-for-notify
    STATUS      current
    DESCRIPTION
        "
        OLT software error code.
        "
    ::= { unisEponErrorInfo 1 }

unisOamVendorSpecificAlarmCode OBJECT-TYPE
    SYNTAX      Integer32
    MAX-ACCESS  accessible-for-notify
    STATUS      current
    DESCRIPTION
        "
        Alarm code of the vendor.
        "
    ::= { unisEponErrorInfo 2 }

unisEponOnuRegErrorMacAddr OBJECT-TYPE
    SYNTAX      OCTET STRING
    MAX-ACCESS  accessible-for-notify
    STATUS      current
    DESCRIPTION
        "
        The MAC of ONU registered error.
        "
    ::= { unisEponErrorInfo 3 }

unisOamEventLogType OBJECT-TYPE
    SYNTAX      Unsigned32
    MAX-ACCESS  accessible-for-notify
    STATUS      current
    DESCRIPTION
        "
        The type of event that generated this entry in the event log.
        "
    ::= { unisEponErrorInfo 4 }

unisOamEventLogLocation OBJECT-TYPE
    SYNTAX      INTEGER{local(1),remote(2)}
    MAX-ACCESS  accessible-for-notify
    STATUS      current
    DESCRIPTION
        "
        Whether this event occurred locally, or was received from the
        OAM peer via Ethernet OAM.
        "
    ::= { unisEponErrorInfo 5 }

unisEponLoopbackPortIndex OBJECT-TYPE
    SYNTAX      Integer32
    MAX-ACCESS  accessible-for-notify
    STATUS      current
    DESCRIPTION
        "
        The index of port which generate loop back event.
        "
    ::= { unisEponErrorInfo 6 }

unisEponLoopbackPortDescr OBJECT-TYPE
    SYNTAX      OCTET STRING(SIZE(0..255))
    MAX-ACCESS  accessible-for-notify
    STATUS      current
    DESCRIPTION
        "
        A textual string containing information about the
        port generated loop back event.
        "
    ::= { unisEponErrorInfo 7 }

unisOltPortAlarmLlidMisFrames OBJECT-TYPE
    SYNTAX      Unsigned32
    MAX-ACCESS  accessible-for-notify
    STATUS      current
    DESCRIPTION
        "
        the amount of mismatched frames about the LLID mismatch alarm.
        "
    ::= { unisEponErrorInfo 8 }

unisOltPortAlarmBer OBJECT-TYPE
    SYNTAX      Unsigned32
    MAX-ACCESS  accessible-for-notify
    STATUS      current
    DESCRIPTION
        "
        error bit rate.
        "
    ::= { unisEponErrorInfo 9 }

unisOltPortAlarmFer OBJECT-TYPE
    SYNTAX      Unsigned32
    MAX-ACCESS  accessible-for-notify
    STATUS      current
    DESCRIPTION
        "
        error frames rate.
        "
    ::= { unisEponErrorInfo 10 }

unisEponOnuRegSilentMac OBJECT-TYPE
    SYNTAX      OCTET STRING
    MAX-ACCESS  accessible-for-notify
    STATUS      current
    DESCRIPTION
        "
        The MAC of silent ONU.
        "
    ::= { unisEponErrorInfo 11 }

unisEponOperationResult OBJECT-TYPE
    SYNTAX      OCTET STRING(SIZE(0..255))
    MAX-ACCESS  accessible-for-notify
    STATUS      current
    DESCRIPTION
        "
        The result of EPON operation.
        "
    ::= { unisEponErrorInfo 12 }

unisEponOnuLaserState OBJECT-TYPE
    SYNTAX      INTEGER
    {
        normal(1),
        laserAlwaysOn(2),
        signalDegradation(3),
        endOfLife(4)
    }
    MAX-ACCESS  accessible-for-notify
    STATUS      current
    DESCRIPTION
        "
        The state of ONU laser.
        "
    ::= { unisEponErrorInfo 13 }

unisEponOnuRegSilentBindType OBJECT-TYPE
    SYNTAX      BITS
        {
            mac(0),
            loid(1),
            loidPassword(2)
        }
    MAX-ACCESS  accessible-for-notify
    STATUS      current
    DESCRIPTION
        "
        The binding type of a silent ONU.
        "
    ::= { unisEponErrorInfo 14 }

unisEponOnuRegSilentLoid OBJECT-TYPE
    SYNTAX      OCTET STRING
    MAX-ACCESS  accessible-for-notify
    STATUS      current
    DESCRIPTION
        "
        The LOID of a silent ONU.
        "
    ::= { unisEponErrorInfo 15 }

unisEponOnuRegSilentLoidPwd OBJECT-TYPE
    SYNTAX      OCTET STRING
    MAX-ACCESS  accessible-for-notify
    STATUS      current
    DESCRIPTION
        "
        The LOID's password of a silent ONU.
        A zero-length string will be returned when reading.
        "
    ::= { unisEponErrorInfo 16 }

unisEponOnuRegErrorLoid OBJECT-TYPE
    SYNTAX      OCTET STRING
    MAX-ACCESS  accessible-for-notify
    STATUS      current
    DESCRIPTION
        "
        The LOID of an ONU with registration error.
        "
    ::= { unisEponErrorInfo 17 }

unisEponOnuRegErrorLoidCode OBJECT-TYPE
    SYNTAX      INTEGER
    {
        loidNotExist(1),
        wrongPassword(2),
        conflictLoid(3),
        notSupport(4),
        mismatch(5)
    }
    MAX-ACCESS  accessible-for-notify
    STATUS      current
    DESCRIPTION
        "
        The reason of ONU registration failure.
        "
    ::= { unisEponErrorInfo 18 }

--
-- unisEpon NOTIFICATION
--

unisEponTrap OBJECT IDENTIFIER ::= { unisEponMibObjects 8 }

unisEponTrapPrefix OBJECT IDENTIFIER ::= { unisEponTrap 0 }

unisEponPortAlarmBerTrap NOTIFICATION-TYPE
    OBJECTS
        {
            ifIndex,
            ifDescr,
            unisOltPortAlarmBerDirect,
            unisOltPortAlarmBer,
            unisOltPortAlarmBerThreshold
        }
    STATUS      current
    DESCRIPTION
        "
        A unisEponPortAlarmBerTrap notification is sent when
        a BER threshold crossing event is detected.
        "
    ::= { unisEponTrapPrefix 1 }

unisEponPortAlarmFerTrap NOTIFICATION-TYPE
    OBJECTS
        {
            ifIndex,
            ifDescr,
            unisOltPortAlarmFerDirect,
            unisOltPortAlarmFer,
            unisOltPortAlarmFerThreshold
        }
    STATUS      current
    DESCRIPTION
        "
        A unisEponPortAlarmFerTrap notification is sent when
        a frame error rate threshold crossing event is detected.
        "
    ::= { unisEponTrapPrefix 2 }

unisEponErrorLLIDFrameTrap NOTIFICATION-TYPE
    OBJECTS
        {
            ifIndex,
            ifDescr,
            unisOltPortAlarmLlidMisFrames,
            unisOltPortAlarmLlidMismatchThreshold
        }
    STATUS      current
    DESCRIPTION
        "
        A unisEponErrorLLIDFrameTrap notification is sent when a
        LLID mismatched frames rate threshold crossing event is detected.
        "
    ::= { unisEponTrapPrefix 3 }

unisEponLoopBackEnableTrap NOTIFICATION-TYPE
    OBJECTS
        {
            ifIndex,
            ifDescr,
            unisEponLoopbackPortIndex,
            unisEponLoopbackPortDescr
        }
    STATUS      current
    DESCRIPTION
        "
        A unisEponLoopBackEnableTrap notification is sent when
        the loop back command is committed.
        "
    ::= { unisEponTrapPrefix 4 }

unisEponOnuRegistrationErrTrap NOTIFICATION-TYPE
    OBJECTS
        {
            ifIndex,
            ifDescr,
            unisEponOnuRegErrorMacAddr
        }
    STATUS      current
    DESCRIPTION
        "
        A unisEponOnuRegistrationErrTrap notification is sent when a
        ONU register failed.
        "
    ::= { unisEponTrapPrefix 5 }

unisEponOamDisconnectionTrap NOTIFICATION-TYPE
    OBJECTS
        {
            ifIndex,
            ifDescr
        }
    STATUS      current
    DESCRIPTION
        "
        A unisEponOamDisconnectionTrap notification is sent when
        LLID's OAM link is disconnected.
        "
    ::= { unisEponTrapPrefix 6 }

unisEponEncryptionKeyErrTrap NOTIFICATION-TYPE
    OBJECTS
        {
            ifIndex,
            ifDescr
        }
    STATUS      current
    DESCRIPTION
        "
        A unisEponEncryptionKeyErrTrap notification is sent when
        LLID's encryption key is bad.
        "
    ::= { unisEponTrapPrefix 7 }

unisEponRemoteStableTrap NOTIFICATION-TYPE
    OBJECTS
        {
            ifIndex,
            ifDescr
        }
    STATUS      current
    DESCRIPTION
        "
        A unisEponRemoteStableTrap notification is sent when
        remote Data Terminal Equipment(DTE) has not seen or
        is unsatisfied with local state information.
        "
    ::= { unisEponTrapPrefix 8 }

unisEponLocalStableTrap NOTIFICATION-TYPE
    OBJECTS
        {
            ifIndex,
            ifDescr
        }
    STATUS      current
    DESCRIPTION
        "
        A unisEponLocalStableTrap notification is sent when
        DTE has not seen or is unsatisfied with remote state
        information.
        "
    ::= { unisEponTrapPrefix 9 }

unisEponOamVendorSpecificTrap NOTIFICATION-TYPE
    OBJECTS
        {
            ifIndex,
            ifDescr,
            unisOamVendorSpecificAlarmCode
        }
    STATUS      current
    DESCRIPTION
        "
        A unisEponOamVendorSpecificTrap notification is sent when
        system vendor specific OAM alarm raised.
        "
    ::= { unisEponTrapPrefix 10 }

unisEponSoftwareErrTrap NOTIFICATION-TYPE
    OBJECTS
        {
            unisLswFrameIndex,
            unisLswSlotIndex,
            unisEponSoftwareErrorCode
        }
    STATUS      current
    DESCRIPTION
        "
        A unisEponSoftwareErrTrap notification is sent when
        a PAS-SOFT internal error occurs.
        "
    ::= { unisEponTrapPrefix 11 }

unisEponPortAlarmBerRecoverTrap NOTIFICATION-TYPE
    OBJECTS
        {
            ifIndex,
            ifDescr,
            unisOltPortAlarmBerDirect
        }
    STATUS      current
    DESCRIPTION
        "
        A unisEponPortAlarmBerRecoverTrap notification is sent when
        a BER threshold crossing event is detected and then recovered.
        "
    ::= { unisEponTrapPrefix 12 }

unisEponPortAlarmFerRecoverTrap NOTIFICATION-TYPE
    OBJECTS
        {
            ifIndex,
            ifDescr,
            unisOltPortAlarmFerDirect
        }
    STATUS      current
    DESCRIPTION
        "
        A unisEponPortAlarmFerRecoverTrap notification is sent when
        a frame error rate threshold crossing event is detected and then
        recovered.
        "
    ::= { unisEponTrapPrefix 13 }

unisEponErrorLLIDFrameRecoverTrap NOTIFICATION-TYPE
    OBJECTS
        {
            ifIndex,
            ifDescr
        }
    STATUS      current
    DESCRIPTION
        "
        A unisEponErrorLLIDFrameRecoverTrap notification is sent when a
        LLID mismatched frames rate threshold crossing event is detected
        and then recovered.
        "
    ::= { unisEponTrapPrefix 14 }

unisEponLoopBackEnableRecoverTrap NOTIFICATION-TYPE
    OBJECTS
        {
            ifIndex,
            ifDescr
        }
    STATUS      current
    DESCRIPTION
        "
        A unisEponLoopBackEnableRecoverTrap notification is sent when
        the loop back is detected and then recovered.
        "
    ::= { unisEponTrapPrefix 15 }

unisEponOnuRegistrationErrRecoverTrap NOTIFICATION-TYPE
    OBJECTS
        {
            ifIndex,
            ifDescr,
            unisEponOnuRegErrorMacAddr
        }
    STATUS      current
    DESCRIPTION
        "
        A unisEponOnuRegistrationErrRecoverTrap notification is sent when an
        ONU register failed and then register successful again.
        "
    ::= { unisEponTrapPrefix 16 }

unisEponOamDisconnectionRecoverTrap NOTIFICATION-TYPE
    OBJECTS
        {
            ifIndex,
            ifDescr
        }
    STATUS      current
    DESCRIPTION
        "
        A unisEponOamDisconnectionRecoverTrap notification is sent when
        LLID's OAM link is disconnected and then connected.
        "
    ::= { unisEponTrapPrefix 17 }

unisEponEncryptionKeyErrRecoverTrap NOTIFICATION-TYPE
    OBJECTS
        {
            ifIndex,
            ifDescr
        }
    STATUS      current
    DESCRIPTION
        "
        A unisEponEncryptionKeyErrRecoverTrap notification is sent when
        LLID's encryption key is bad and then right.
        "
    ::= { unisEponTrapPrefix 18 }

unisEponRemoteStableRecoverTrap NOTIFICATION-TYPE
    OBJECTS
        {
            ifIndex,
            ifDescr
        }
    STATUS      current
    DESCRIPTION
        "
        A unisEponRemoteStableRecoverTrap notification is sent when
        remote DTE has not seen or is unsatisfied with local
        state information and then is realized.
        "
    ::= { unisEponTrapPrefix 19 }

unisEponLocalStableRecoverTrap NOTIFICATION-TYPE
    OBJECTS
        {
            ifIndex,
            ifDescr
        }
    STATUS      current
    DESCRIPTION
        "
        A unisEponLocalStableRecoverTrap notification is sent when
        DTE has not seen or is unsatisfied with remote state
        information and then is realized.
        "
    ::= { unisEponTrapPrefix 20 }

unisEponOamVendorSpecificRecoverTrap NOTIFICATION-TYPE
    OBJECTS
        {
            ifIndex,
            ifDescr,
            unisOamVendorSpecificAlarmCode
        }
    STATUS      current
    DESCRIPTION
        "
        A unisEponOamVendorSpecificRecoverTrap notification is sent when
        system vendor specific OAM alarm is detected and then recovered.
        "
    ::= { unisEponTrapPrefix 21 }

unisEponSoftwareErrRecoverTrap NOTIFICATION-TYPE
    OBJECTS
        {
            unisLswFrameIndex,
            unisLswSlotIndex,
            unisEponSoftwareErrorCode
        }
    STATUS      current
    DESCRIPTION
        "
        A unisEponSoftwareErrRecoverTrap notification is sent when
        a PAS-SOFT internal error is detected and then recovered.
        "
    ::= { unisEponTrapPrefix 22 }

unisDot3OamThresholdRecoverEvent NOTIFICATION-TYPE
    OBJECTS
        {
            ifIndex,
            unisOamEventLogType,
            unisOamEventLogLocation
        }
    STATUS      current
    DESCRIPTION
        "
        A unisDot3OamThresholdRecoverEvent notification is sent when
        unisDot3OamThresholdEvent is detected and then recovered.
        "
    ::= { unisEponTrapPrefix 23 }


unisDot3OamNonThresholdRecoverEvent NOTIFICATION-TYPE
    OBJECTS
        {
            ifIndex,
            unisOamEventLogType,
            unisOamEventLogLocation
        }
    STATUS      current
    DESCRIPTION
        "
        A unisDot3OamNonThresholdRecoverEvent notification is sent when
        unisDot3OamNonThresholdEvent is detected and then recovered.
        "
    ::= { unisEponTrapPrefix 24 }

unisEponOnuRegExcessTrap NOTIFICATION-TYPE
    OBJECTS
        {
            ifIndex,
            ifDescr
        }
    STATUS      current
    DESCRIPTION
        "
        A unisEponOnuRegExcessTrap notification is sent when the
        number of registered ONUs exceeds the limit.
        "
    ::= { unisEponTrapPrefix 25 }

unisEponOnuRegExcessRecoverTrap NOTIFICATION-TYPE
    OBJECTS
        {
            ifIndex,
            ifDescr
        }
    STATUS      current
    DESCRIPTION
        "
        A unisEponOnuRegExcessRecoverTrap notification is sent when
        unisEponOnuRegExcessTrap is detected and then recovered.
        "
    ::= { unisEponTrapPrefix 26 }

unisEponOnuPowerOffTrap NOTIFICATION-TYPE
    OBJECTS
        {
            ifIndex,
            ifDescr
        }
    STATUS      current
    DESCRIPTION
        "
        A unisEponOnuPowerOffTrap notification is sent when ONU is power off.
        "
    ::= { unisEponTrapPrefix 27 }

unisEponOltSwitchoverTrap NOTIFICATION-TYPE
    OBJECTS
        {
            ifIndex,
            ifDescr
        }
    STATUS      current
    DESCRIPTION
        "
        A unisEponOltSwithoverTrap notification is sent when OLT switchover
        is detected.
        "
    ::= { unisEponTrapPrefix 28 }

unisEponOltDFETrap NOTIFICATION-TYPE
    OBJECTS
        {
            ifIndex,
            ifDescr
        }
    STATUS      current
    DESCRIPTION
        "
        A unisEponOltDFETrap notification is sent when there was
        a serious problem(device fatal error) on OLT.
        "
    ::= { unisEponTrapPrefix 29 }

unisEponOltDFERecoverTrap NOTIFICATION-TYPE
    OBJECTS
        {
            ifIndex,
            ifDescr
        }
    STATUS      current
    DESCRIPTION
        "
        A unisEponOltDFERecoverTrap notification is sent when
        device fatal error is detected and then recovered.
        "
    ::= { unisEponTrapPrefix 30 }

unisEponOnuSilenceTrap NOTIFICATION-TYPE
    OBJECTS
        {
            ifIndex,
            ifDescr,
            unisEponOnuRegSilentMac
        }
    STATUS      current
    DESCRIPTION
        "
        The unisEponOnuSilenceTrap notification is sent when an
        unbound ONU try to register to an OLT.
        "
    ::= { unisEponTrapPrefix 31 }

unisEponOnuSilenceRecoverTrap NOTIFICATION-TYPE
    OBJECTS
        {
            ifIndex,
            ifDescr,
            unisEponOnuRegSilentMac
        }
    STATUS      current
    DESCRIPTION
        "
        The unisEponOnuSilenceRecoverTrap notification is sent when
        a silent ONU is bound in the OLT or the aging onu mac
        address is timeout.
        "
    ::= { unisEponTrapPrefix 32 }

unisEponOnuUpdateResultTrap NOTIFICATION-TYPE
    OBJECTS
        {
            ifIndex,
            ifDescr,
            unisOnuBindMacAddress,
            unisOnuUpdateResult,
            unisOnuRegType,
            unisOnuUpdateFileName
        }
    STATUS      current
    DESCRIPTION
        "
        A unisEponUpdateResultTrap notification is sent when
        an ONU reported its firmware update result.
        "
    ::= { unisEponTrapPrefix 33 }

unisEponOnuAutoBindTrap NOTIFICATION-TYPE
    OBJECTS
        {
            ifIndex,
            ifDescr,
            unisOnuBindMacAddress,
            unisEponOperationResult
        }
    STATUS      current
    DESCRIPTION
        "
        A unisEponOnuAutoBindTrap notification is sent
        when a silent ONU is bound automatically.
        "
    ::= { unisEponTrapPrefix 34 }

unisEponOnuPortStpStateTrap NOTIFICATION-TYPE
    OBJECTS
        {
            ifIndex,
            ifDescr,
            unisEponStpPortIndex,
            unisEponStpPortDescr,
            unisEponStpPortState
        }
    STATUS      current
    DESCRIPTION
        "
        A unisEponOnuPortStpStateTrap notification is sent when
        a port turns into another state in STP environment.
        "
    ::= { unisEponTrapPrefix 35 }

unisEponOnuLaserFailedTrap NOTIFICATION-TYPE
    OBJECTS
        {
            ifIndex,
            ifDescr,
            unisEponOnuLaserState
        }
    STATUS      current
    DESCRIPTION
        "
        A unisEponOnuLaserFailedTrap notification is sent when
        an ONU has trouble with laser, such as laser constantly turned on,
        signal degradation or optics EOL (End of Life).
        "
    ::= { unisEponTrapPrefix 36 }

unisOnuSmlkSwitchoverTrap NOTIFICATION-TYPE
    OBJECTS
        {
            ifIndex,
            ifDescr,
            unisOnuSmlkGroupID,
            unisOnuSmlkFirstPonStatus,
            unisOnuSmlkSecondPonStatus
        }
    STATUS      current
    DESCRIPTION
        "
        A unisOnuSmlkSwitchoverTrap notification is sent when
        an ONU SMLK switchover is detected.
        "
    ::= { unisEponTrapPrefix 37 }

unisEponOnuRegLoidErrTrap NOTIFICATION-TYPE
    OBJECTS
        {
            ifIndex,
            ifDescr,
            unisEponOnuRegErrorLoid,
            unisEponOnuRegErrorLoidCode
        }
    STATUS      current
    DESCRIPTION
        "
        A unisEponOnuRegLoidErrTrap notification is sent when an
        ONU failed to register identified by LOID.
        "
    ::= { unisEponTrapPrefix 38 }

unisEponOnuRegLoidErrRecTrap NOTIFICATION-TYPE
    OBJECTS
        {
            ifIndex,
            ifDescr,
            unisEponOnuRegErrorLoid,
            unisEponOnuRegErrorLoidCode
        }
    STATUS      current
    DESCRIPTION
        "
        A unisEponOnuRegLoidErrRecTrap notification is sent when an
        ONU failed to register and then registered successful again identified by LOID.
        "
    ::= { unisEponTrapPrefix 39 }

unisEponOnuSilenceLoidTrap NOTIFICATION-TYPE
    OBJECTS
        {
            ifIndex,
            ifDescr,
            unisEponOnuRegSilentBindType,
            unisEponOnuRegSilentMac,
            unisEponOnuRegSilentLoid,
            unisEponOnuRegSilentLoidPwd
        }
    STATUS      current
    DESCRIPTION
        "
        The unisEponOnuSilenceLoidTrap notification is sent when an
        unbound ONU try to register to an OLT identified by LOID.
        "
    ::= { unisEponTrapPrefix 40 }

unisEponOnuSilenceLoidRecTrap NOTIFICATION-TYPE
    OBJECTS
        {
            ifIndex,
            ifDescr,
            unisEponOnuRegSilentBindType,
            unisEponOnuRegSilentMac,
            unisEponOnuRegSilentLoid,
            unisEponOnuRegSilentLoidPwd
        }
    STATUS      current
    DESCRIPTION
        "
        The unisEponOnuSilenceLoidRecTrap notification is sent when
        a silent ONU is bound in the OLT or the aging ONU MAC
        address times out identified by LOID.
        "
    ::= { unisEponTrapPrefix 41 }

unisEponOnuUpdateLoidRetTrap NOTIFICATION-TYPE
    OBJECTS
        {
            ifIndex,
            ifDescr,
            unisOnuBindLoid,
            unisOnuUpdateResult,
            unisOnuRegType,
            unisOnuUpdateFileName
        }
    STATUS      current
    DESCRIPTION
        "
        A unisEponOnuUpdateLoidRetTrap notification is sent when
        an ONU reported its firmware update result identified by LOID.
        "
    ::= { unisEponTrapPrefix 42 }

unisEponOnuAutoBindLoidTrap NOTIFICATION-TYPE
    OBJECTS
        {
            ifIndex,
            ifDescr,
            unisOnuBindLoid,
            unisEponOperationResult
        }
    STATUS      current
    DESCRIPTION
        "
        A unisEponOnuAutoBindLoidTrap notification is sent
        when a silent ONU is bound automatically identified by LOID.
        "
    ::= { unisEponTrapPrefix 43 }

unisEponOnuPowerOnTrap NOTIFICATION-TYPE
    OBJECTS
        {
            ifIndex,
            ifDescr
        }
    STATUS      current
    DESCRIPTION
        "
        A unisEponOnuPowerOffTrap notification is sent when ONU is powered on.
        "
    ::= { unisEponTrapPrefix 44 }

unisEponOpticalSignalLosTrap NOTIFICATION-TYPE
    OBJECTS
        {
            ifIndex,
            ifDescr
        }
    STATUS      current
    DESCRIPTION
        "
        A unisEponOpticalSignalLosTrap notification is sent when optical signals are lost.
        "
    ::= { unisEponTrapPrefix 45 }

unisEponOpticalSignalLosRecoverTrap NOTIFICATION-TYPE
    OBJECTS
        {
            ifIndex,
            ifDescr
        }
    STATUS      current
    DESCRIPTION
        "
        A unisEponOpticalSignalLosTrap notification is sent when optical signal loss recovers.
        "
    ::= { unisEponTrapPrefix 46 }

unisEponOnuFiberFailTrap NOTIFICATION-TYPE
    OBJECTS
        {
            ifIndex,
            ifDescr
        }
    STATUS      current
    DESCRIPTION
        "
        A unisEponOnuPowerOffTrap notification is sent when the ONU fiber fails.
        "
    ::= { unisEponTrapPrefix 47 }

unisEponOnuFiberFailRecoverTrap NOTIFICATION-TYPE
    OBJECTS
        {
            ifIndex,
            ifDescr
        }
    STATUS      current
    DESCRIPTION
        "
        A unisEponOnuPowerOffTrap notification is sent when the ONU fiber failure recovers.
        "
    ::= { unisEponTrapPrefix 48 }

unisEponStat OBJECT IDENTIFIER ::= { unisEponMibObjects 9 }

--
-- unisEponStatTable
--

unisEponStatTable OBJECT-TYPE
    SYNTAX      SEQUENCE OF UnisEponStatEntry
    MAX-ACCESS  not-accessible
    STATUS      current
    DESCRIPTION
        "
        This table contains line code error statistics of epon port.
        "
    ::= { unisEponStat 1 }

unisEponStatEntry OBJECT-TYPE
    SYNTAX      UnisEponStatEntry
    MAX-ACCESS  not-accessible
    STATUS      current
    DESCRIPTION
        "
        The entry of unisEponStatTable.
        "
    INDEX
        {
            ifIndex
        }
    ::= { unisEponStatTable 1 }

UnisEponStatEntry ::= SEQUENCE
    {
        unisEponStatFER    Counter64,
        unisEponStatBER    Counter64
    }

unisEponStatFER OBJECT-TYPE
    SYNTAX      Counter64
    MAX-ACCESS  read-only
    STATUS      current
    DESCRIPTION
        "
        The frame error rate of epon port, measured in 1e-9 unit.
        "
    ::= { unisEponStatEntry 1 }

unisEponStatBER OBJECT-TYPE
    SYNTAX      Counter64
    MAX-ACCESS  read-only
    STATUS      current
    DESCRIPTION
        "
        The bit error rate of epon port, measured in 1e-9 unit.
        "
    ::= { unisEponStatEntry 2  }

unisEponRoltMan OBJECT IDENTIFIER ::= { unisEponMibObjects 10 }

--
-- unisRoltInterfaceTable
--

unisRoltInterfaceTable OBJECT-TYPE
    SYNTAX      SEQUENCE OF UnisRoltInterfaceEntry
    MAX-ACCESS  not-accessible
    STATUS      current
    DESCRIPTION
        "
        The table of redundant OLT interfaces.
        "
    ::= { unisEponRoltMan 1 }

unisRoltInterfaceEntry  OBJECT-TYPE
    SYNTAX      UnisRoltInterfaceEntry
    MAX-ACCESS  not-accessible
    STATUS      current
    DESCRIPTION
        "
        The entry of the table unisRoltInterfaceTable.
        "
    INDEX
        {
            unisRoltInterfaceNumber
        }
    ::= { unisRoltInterfaceTable 1 }

UnisRoltInterfaceEntry ::= SEQUENCE
    {
        unisRoltInterfaceNumber       Integer32,
        unisRoltInterfaceIfIndex      Integer32,
        unisRoltInterfaceRowStatus    RowStatus
    }

unisRoltInterfaceNumber OBJECT-TYPE
    SYNTAX      Integer32
    MAX-ACCESS  not-accessible
    STATUS      current
    DESCRIPTION
        "
        The number of an ROLT interface.
        "
    ::= { unisRoltInterfaceEntry 1 }

unisRoltInterfaceIfIndex OBJECT-TYPE
    SYNTAX      Integer32
    MAX-ACCESS  read-only
    STATUS      current
    DESCRIPTION
        "
        The ifIndex of an ROLT interface.
        "
    ::= { unisRoltInterfaceEntry 2 }

unisRoltInterfaceRowStatus OBJECT-TYPE
    SYNTAX      RowStatus
    MAX-ACCESS  read-create
    STATUS      current
    DESCRIPTION
        "
        Create or delete a redundant OLT interface.
        Now only two operations are supported:
        createAndGo and destroy.
        "
    ::= { unisRoltInterfaceEntry 3 }

--
-- unisRoltMemberTable
--
unisRoltMemberTable OBJECT-TYPE
    SYNTAX      SEQUENCE OF UnisRoltMemberEntry
    MAX-ACCESS  not-accessible
    STATUS      current
    DESCRIPTION
        "
        This table is used for adding or deleting the OLT member
        interfaces of an redundant OLT interface.
        "
    ::= { unisEponRoltMan 2 }

unisRoltMemberEntry  OBJECT-TYPE
    SYNTAX      UnisRoltMemberEntry
    MAX-ACCESS  not-accessible
    STATUS      current
    DESCRIPTION
        "
        The entry of the table unisRoltMemberTable.
        "
    INDEX
        {
            unisRoltInterfaceNumber,
            unisRoltMemberOltIfindex
        }
    ::= { unisRoltMemberTable 1 }

UnisRoltMemberEntry ::= SEQUENCE
    {
        unisRoltMemberOltIfindex      Integer32,
        unisRoltMemberOltPriority     Integer32,
        unisRoltMemberRowStatus       RowStatus,
        unisRoltMemberForwardStatus   TruthValue
    }

unisRoltMemberOltIfindex OBJECT-TYPE
    SYNTAX      Integer32
    MAX-ACCESS  not-accessible
    STATUS      current
    DESCRIPTION
        "
        The ifindex of an OLT interface.
        "
    ::= { unisRoltMemberEntry 1 }

unisRoltMemberOltPriority OBJECT-TYPE
    SYNTAX      Integer32 (1..255)
    MAX-ACCESS  read-create
    STATUS      current
    DESCRIPTION
        "
        The priority of an OLT interface that will be assigned to an ROLT interface.
        "
    ::= { unisRoltMemberEntry 2 }

unisRoltMemberRowStatus OBJECT-TYPE
    SYNTAX      RowStatus
    MAX-ACCESS  read-create
    STATUS      current
    DESCRIPTION
        "
        Operation status.  Now only two states are supported:
        createAndGo and destroy.
        "
    ::= { unisRoltMemberEntry 3 }

unisRoltMemberForwardStatus OBJECT-TYPE
    SYNTAX      TruthValue
    MAX-ACCESS  read-only
    STATUS      current
    DESCRIPTION
        "
        The forwarding status of an OLT member interface.
        true(1)  - Active.
        false(2) - Inactive.
        "
    ::= { unisRoltMemberEntry 4 }
END
