-- =====================================================================
-- Copyright (c) 2020 Unisyue Technologies Co., Ltd.  All rights reserved.
--
-- Description: IPv6 address MIB
-- Reference:
-- Version: V1.1
-- History:
--   V1.0 2006-03-15 Created by Zhang Jun and Yu Hongqiang
--     Initial version
--   V1.1 2013-01-22 Modified by yuguoqing
--     Modify the description of unisIpv6AddrSetSourceType
--     and unisIpv6AddrReadSourceType
-- =====================================================================
UNIS-IPV6-ADDRESS-MIB DEFINITIONS ::= BEGIN

    IMPORTS
        unisCommon
            FROM UNIS-OID-MIB
        Integer32, OBJECT-TYPE, MODULE-IDENTITY
            FROM SNMPv2-SMI
        RowStatus
            FROM SNMPv2-TC
        InetAddress, InetAddressType
            FROM INET-ADDRESS-MIB;

    unisIpv6AddrMIB MODULE-IDENTITY
        LAST-UPDATED "200603150000Z"
        ORGANIZATION
            "Unisyue Technologies Co., Ltd."
        CONTACT-INFO
            ""
        DESCRIPTION
            "The MIB module for managing IPv6 address"
        REVISION "200603150000Z"
        DESCRIPTION
            "The initial revision of this MIB module."
        ::= { unisCommon 71 }


--
-- Node definitions
--
    unisIpv6AddressObjects OBJECT IDENTIFIER ::= { unisIpv6AddrMIB 1 }

    unisIpv6AddressConfig OBJECT IDENTIFIER ::= { unisIpv6AddressObjects 1 }

    unisIpv6AddrSetTable OBJECT-TYPE
        SYNTAX      SEQUENCE OF UnisIpv6AddrSetEntry
        MAX-ACCESS  not-accessible
        STATUS      current
        DESCRIPTION
            "The table of address information is relevant to this
            entity's IPv6 addresses for setting. The address information
            that can be read and set in this table is a subset of the
            address information that can be read in unisIpv6AddrReadTable
            and ipv6AddrTable in IPV6-MIB. This table is used to configure IPv6
            addresses of an interface identified by unisIpv6AddrSetIfIndex.
            When users create or delete an entry in this table, the agent also
            increases or reduces a corresponding entry in the
            unisIpv6AddrReadTable and ipv6AddrTable in IPV6-MIB.
            When an interface which has been assigned IPv6 address is deleted,
            the agent also deletes the entry corresponding to
            the interface in this table and unisIpv6AddrReadTable.
            All IPv6 addresses in this table will also show in ipv6AddrTable in
            IPV6-MIB."
        REFERENCE
            "RFC 2456"
        ::= { unisIpv6AddressConfig 1 }

    unisIpv6AddrSetEntry OBJECT-TYPE
        SYNTAX      UnisIpv6AddrSetEntry
        MAX-ACCESS  not-accessible
        STATUS      current
        DESCRIPTION
            "Define the IPv6 address information."
        INDEX
        {
            unisIpv6AddrSetIfIndex,
            unisIpv6AddrSetAddrType,
            unisIpv6AddrSetAddr
        }
        ::= { unisIpv6AddrSetTable 1 }

    UnisIpv6AddrSetEntry ::=
    SEQUENCE
    {
        unisIpv6AddrSetIfIndex       Integer32,
        unisIpv6AddrSetAddrType      InetAddressType,
        unisIpv6AddrSetAddr          InetAddress,
        unisIpv6AddrSetPfxLength     Integer32,
        unisIpv6AddrSetSourceType    INTEGER,
        unisIpv6AddrSetRowStatus     RowStatus
    }

    unisIpv6AddrSetIfIndex OBJECT-TYPE
        SYNTAX      Integer32(1..2147483647)
        MAX-ACCESS  not-accessible
        STATUS      current
        DESCRIPTION
            "The index value which uniquely identifies the interface to
            which this entry is applicable. The interface identified by
            a particular value of this index is the same interface as
            identified by the same value of RFC 1573's ifIndex."
        ::= { unisIpv6AddrSetEntry 1 }

    unisIpv6AddrSetAddrType OBJECT-TYPE
        SYNTAX      InetAddressType
        MAX-ACCESS  not-accessible
        STATUS      current
        DESCRIPTION
            "The IP address type to which this entry's address
            information pertains. The value must be ipv6."
        ::= { unisIpv6AddrSetEntry 2 }

    unisIpv6AddrSetAddr OBJECT-TYPE
        SYNTAX      InetAddress
        MAX-ACCESS  not-accessible
        STATUS      current
        DESCRIPTION
            "The IPv6 address to which this entry's address
            information pertains."
        ::= { unisIpv6AddrSetEntry 3 }

    unisIpv6AddrSetPfxLength OBJECT-TYPE
        SYNTAX      Integer32(1..128)
        MAX-ACCESS  read-create
        STATUS      current
        DESCRIPTION
            "The length of the prefix (in bits) associated with
            the IPv6 address of this entry."
        ::= { unisIpv6AddrSetEntry 4 }

    unisIpv6AddrSetSourceType OBJECT-TYPE
        SYNTAX      INTEGER
                    {
                        assignedIp(1),
                        assignedEUI64Ip(2),
                        assignedLinklocalIp(3)
                    }
        MAX-ACCESS  read-create
        STATUS      current
        DESCRIPTION
            "Indicate the type of source of IPv6 address.
            The value can be one of following:
            'assignedIp':
                Assigned global/site-local IPv6 address;
            'assignedEUI64Ip':
                Assigned global/site-local IPv6 address
                by using EUI-64 interface identifier;
            'assignedLinklocalIp':
                Assigned link-local IPv6 address.
            The value of unisIpv6AddrSetSourceType is relevant to
                unisIpv6AddrReadSourceType and unisIpv6AddrReadCatalog .
            For example, if the value of unisIpv6AddrSetSourceType is set to
                'assignedIp', then the value of unisIpv6AddrReadSourceType is
                'assignedIp' and the value of unisIpv6AddrReadCatalog is
                'global' or 'sitelocal'.
            The relation listed in the following table.
            ----------------------------------------------------------------
             unisIpv6Addr-       | unisIpv6Addr-     | unisIpv6Addr-
             SetSourceType       | ReadSourceType    | ReadCatalog
            ----------------------------------------------------------------
             assignedIp          | assignedIp        | global or sitelocal
            ----------------------------------------------------------------
             assignedEUI64Ip     | assignedEUI64Ip   | global or sitelocal
            ----------------------------------------------------------------
             assignedLinklocalIp | assignedIp        | linklocal
            ----------------------------------------------------------------
            "
        ::= { unisIpv6AddrSetEntry 5 }

    unisIpv6AddrSetRowStatus OBJECT-TYPE
        SYNTAX      RowStatus
        MAX-ACCESS  read-create
        STATUS      current
        DESCRIPTION
            "This object is used to create a new row or delete an
            existing row in this table, only supports active(1),
            createAndGo(4) and destroy(6)."
        ::= { unisIpv6AddrSetEntry 6 }

    unisIpv6AddrReadTable OBJECT-TYPE
        SYNTAX      SEQUENCE OF UnisIpv6AddrReadEntry
        MAX-ACCESS  not-accessible
        STATUS      current
        DESCRIPTION
            "The table of address information is relevant to this
            entity's IPv6 addresses for reading.
            This is the extension of the ipv6AddrTable in IPV6-MIB.
            All IPv6 addresses in this table will also show in ipv6AddrTable
            in IPV6-MIB."
        REFERENCE
            "RFC 2456"
        ::= { unisIpv6AddressConfig 2 }

    unisIpv6AddrReadEntry OBJECT-TYPE
        SYNTAX      UnisIpv6AddrReadEntry
        MAX-ACCESS  not-accessible
        STATUS      current
        DESCRIPTION
            "Define the IPv6 address information."
        INDEX
        {
            unisIpv6AddrReadIfIndex,
            unisIpv6AddrReadAddrType,
            unisIpv6AddrReadAddr
        }
        ::= { unisIpv6AddrReadTable 1 }

    UnisIpv6AddrReadEntry ::=
        SEQUENCE
        {
            unisIpv6AddrReadIfIndex       Integer32,
            unisIpv6AddrReadAddrType      InetAddressType,
            unisIpv6AddrReadAddr          InetAddress,
            unisIpv6AddrReadPfxLength     Integer32,
            unisIpv6AddrReadSourceType    INTEGER,
            unisIpv6AddrReadCatalog       INTEGER
        }

    unisIpv6AddrReadIfIndex OBJECT-TYPE
        SYNTAX      Integer32(1..2147483647)
        MAX-ACCESS  not-accessible
        STATUS      current
        DESCRIPTION
            "The index value which uniquely identifies the interface to
            which this entry is applicable. The interface identified by
            a particular value of this index is the same interface as
            identified by the same value of RFC 1573's ifIndex."
        ::= { unisIpv6AddrReadEntry 1 }

    unisIpv6AddrReadAddrType OBJECT-TYPE
        SYNTAX      InetAddressType
        MAX-ACCESS  not-accessible
        STATUS      current
        DESCRIPTION
            "The IP address type to which this entry's address information
            pertains. The value must be ipv6."
        ::= { unisIpv6AddrReadEntry 2 }

    unisIpv6AddrReadAddr OBJECT-TYPE
        SYNTAX      InetAddress
        MAX-ACCESS  not-accessible
        STATUS      current
        DESCRIPTION
            "The IPv6 address to which this entry's address information
            pertains."
        ::= { unisIpv6AddrReadEntry 3 }

    unisIpv6AddrReadPfxLength OBJECT-TYPE
        SYNTAX      Integer32(1..128)
        MAX-ACCESS  read-only
        STATUS      current
        DESCRIPTION
            "The length of the prefix (in bits) associated with
            the IPv6 address of this entry."
        ::= { unisIpv6AddrReadEntry 4 }

    unisIpv6AddrReadSourceType OBJECT-TYPE
        SYNTAX      INTEGER
                    {
                        assignedIp(1),
                        assignedEUI64Ip(2),
                        assignedAutoIp(3),
                        autoIp(4),
                        dhcpv6(5),
                        negotiate(6),
                        cluster(7)
                    }
        MAX-ACCESS  read-only
        STATUS      current
        DESCRIPTION
            "Indicate the type of source of IPv6 address.
            The value can be one of following:
                'assignedIp':      Assigned IPv6 address;
                'assignedEUI64Ip': Assigned IPv6 address by using EUI-64
                                   interface identifier;
                'assignedAutoIp':  Auto generated IPv6 address by user setting;
                'autoIp':          Auto generated IPv6 address as a result
                                   of non-linklocal anycast/unicast address
                                   configuration;
                'dhcpv6':          Assigned IPv6 address through DHCPv6
                                   protocol;
                'negotiate':       Assigned IPv6 address through negotiation;
                'cluster':         Assigned IPv6 address through cluster
                                   module."
        ::= { unisIpv6AddrReadEntry 5 }

    unisIpv6AddrReadCatalog OBJECT-TYPE
        SYNTAX      INTEGER
                    {
                        nodelocal(1),
                        linklocal(2),
                        sitelocal(3),
                        orglocal(4),
                        global(5)
                    }
        MAX-ACCESS  read-only
        STATUS      current
        DESCRIPTION
            "Indicate the category of the IPv6 address.
            The value can be one of following:
            'nodelocal': node-local scope;
            'linklocal': link-local scope;
            'sitelocal': site-local scope;
            'orglocal': organization-local scope;
            'global': global scope. "
        ::= { unisIpv6AddrReadEntry 6 }
END
