-- =================================================================
-- Copyright (c) 2020 Unisyue Technologies Co., Ltd.  All rights reserved.
--
-- Description: Segment Routing VERSION6 Traffic Engineering (SRv6-TE)
-- policy MIB
-- Reference:
-- Version: V1.0
-- History:
-- V1.0 2020-06-06 The initial version, created by Xu Jing
-- =================================================================
UNIS-SRV6POLICY-MIB DEFINITIONS ::= BEGIN

IMPORTS
    MODULE-IDENTITY, Integer32, Unsigned32,OBJECT-TYPE, NOTIFICATION-TYPE
        FROM SNMPv2-SMI
    InetAddressIPv6
        FROM INET-ADDRESS-MIB
    unisCommon
        FROM UNIS-OID-MIB;

unisSrv6Policy MODULE-IDENTITY
    LAST-UPDATED "202006110000Z"
    ORGANIZATION
        "Unisyue Technologies Co., Ltd."
    CONTACT-INFO
        ""

    DESCRIPTION
        "This MIB file provides information about SRv6-TE policies."
    REVISION "202006110000Z"
    DESCRIPTION
        "The initial version of this MIB file."
    ::= { unisCommon 189 }

-- Top-level structure of MIB
unisSrv6PolicyNotifications  OBJECT IDENTIFIER ::= { unisSrv6Policy 0 }
unisSrv6PolicyObjects    OBJECT IDENTIFIER ::= { unisSrv6Policy 1 }

unisSrv6PolicyResourceTable OBJECT-TYPE
    SYNTAX      SEQUENCE OF UnisSrv6PolicyResourceEntry
    MAX-ACCESS      not-accessible
    STATUS      current
    DESCRIPTION
        "This table provides information about SRv6-TE policy resources."
    ::= { unisSrv6PolicyObjects 1 }

unisSrv6PolicyResourceEntry OBJECT-TYPE
    SYNTAX      UnisSrv6PolicyResourceEntry
    MAX-ACCESS      not-accessible
    STATUS      current
    DESCRIPTION
        "Information of the SRv6-TE policy resource."
    INDEX       { unisSrv6PolicyResourceType }
    ::= { unisSrv6PolicyResourceTable 1 }

UnisSrv6PolicyResourceEntry ::= SEQUENCE {
    unisSrv6PolicyResourceType
        INTEGER,
    unisSrv6PolicyResCurrentCnt
        Unsigned32,
    unisSrv6PolicyResUpperLimit
        Unsigned32,
    unisSrv6PolicyResLowerLimit
        Unsigned32,
    unisSrv6PolicyResourceTotalCnt
        Unsigned32
    }

unisSrv6PolicyResourceType OBJECT-TYPE
    SYNTAX      INTEGER {
            unknown(1),
            srv6Policy(2),
            srv6PolicySegmentList(3),
            srv6PolicyGroup(4),
            srv6PolicyFwdPath(5)
      }
    MAX-ACCESS      accessible-for-notify
    STATUS      current
    DESCRIPTION
        "SRv6-TE policy resource type."
    ::= { unisSrv6PolicyResourceEntry 1 }

unisSrv6PolicyResCurrentCnt OBJECT-TYPE
    SYNTAX      Unsigned32
    MAX-ACCESS      read-only
    STATUS      current
    DESCRIPTION
        "Number of used SRv6-TE policy resources."
    ::= { unisSrv6PolicyResourceEntry 2 }

unisSrv6PolicyResUpperLimit OBJECT-TYPE
    SYNTAX      Unsigned32 (1..100)
    MAX-ACCESS      read-only
    STATUS      current
    DESCRIPTION
        "The upper threshold of SRv6-TE policy resources."
    ::= { unisSrv6PolicyResourceEntry 3 }

unisSrv6PolicyResLowerLimit OBJECT-TYPE
    SYNTAX      Unsigned32 (1..100)
    MAX-ACCESS      read-only
    STATUS      current
    DESCRIPTION
        "The lower threshold of SRv6-TE policy resources."
    ::= { unisSrv6PolicyResourceEntry 4 }

unisSrv6PolicyResourceTotalCnt OBJECT-TYPE
    SYNTAX      Unsigned32
    MAX-ACCESS      read-only
    STATUS      current
    DESCRIPTION
        "The maximum number of SRv6-TE policy resources
         that can be used."
    ::= { unisSrv6PolicyResourceEntry 5 }

-- SRv6-TE policy table.

unisSrv6PolicyTable OBJECT-TYPE
    SYNTAX      SEQUENCE OF UnisSrv6PolicyEntry
    MAX-ACCESS      not-accessible
    STATUS      current
    DESCRIPTION
        "This table provides information about SRv6-TE policies."
    ::= { unisSrv6PolicyObjects 2 }

unisSrv6PolicyEntry OBJECT-TYPE
    SYNTAX      UnisSrv6PolicyEntry
    MAX-ACCESS      not-accessible
    STATUS      current
    DESCRIPTION
        "Each entry contains information about a policy."
    INDEX       { unisSrv6PolicyColor, unisSrv6PolicyEndPoint }
    ::= { unisSrv6PolicyTable 1 }

UnisSrv6PolicyEntry ::= SEQUENCE {
    unisSrv6PolicyColor
        Unsigned32,
    unisSrv6PolicyEndPoint
        InetAddressIPv6,
    unisSrv6PolicyName
        OCTET STRING,
    unisSrv6PolicyBsid
        InetAddressIPv6,
    unisSrv6PolicyStatus
        OCTET STRING,
    unisSrv6PolicyDownReason
        OCTET STRING,
    unisSrv6PolicyBsidFailReason
        OCTET STRING,
    unisSrv6PolicyBsidConflictState
        INTEGER
    }

unisSrv6PolicyColor OBJECT-TYPE
    SYNTAX      Unsigned32 (0..4294967295)
    MAX-ACCESS      accessible-for-notify
    STATUS      current
    DESCRIPTION
        "The color associates the SRv6-TE policy with certain intent."
    ::= { unisSrv6PolicyEntry 1 }

unisSrv6PolicyEndPoint OBJECT-TYPE
    SYNTAX      InetAddressIPv6
    MAX-ACCESS      accessible-for-notify
    STATUS      current
    DESCRIPTION
        "The endpoint is the destination of the SRv6-TE policy."
    ::= { unisSrv6PolicyEntry 2 }

unisSrv6PolicyName OBJECT-TYPE
    SYNTAX      OCTET STRING (SIZE (0..128))
    MAX-ACCESS      read-only
    STATUS      current
    DESCRIPTION
        "Name of the SRv6-TE policy."
    ::= { unisSrv6PolicyEntry 3 }

unisSrv6PolicyBsid OBJECT-TYPE
    SYNTAX      InetAddressIPv6
    MAX-ACCESS      read-only
    STATUS      current
    DESCRIPTION
        "Binding segment ID value of the SRv6-TE policy."
    ::= { unisSrv6PolicyEntry 4 }

unisSrv6PolicyStatus OBJECT-TYPE
    SYNTAX      OCTET STRING (SIZE (0..31))
    MAX-ACCESS      read-only
    STATUS      current
    DESCRIPTION
        "Status of the SRv6-TE policy."
    ::= { unisSrv6PolicyEntry 5 }

unisSrv6PolicyDownReason OBJECT-TYPE
    SYNTAX      OCTET STRING (SIZE (0..51))
    MAX-ACCESS      read-only
    STATUS      current
    DESCRIPTION
        "Base identity for the reasons why SRv6-TE policy is operationally down."
    ::= { unisSrv6PolicyEntry 6 }

unisSrv6PolicyBsidFailReason OBJECT-TYPE
    SYNTAX      OCTET STRING (SIZE (0..255))
    MAX-ACCESS      read-only
    STATUS      current
    DESCRIPTION
        "Reason why the binding SID is unavailable."
    ::= { unisSrv6PolicyEntry 7 }

unisSrv6PolicyBsidConflictState OBJECT-TYPE
    SYNTAX      INTEGER {
            inConflict(1),
            conflictResolved(2)
            }
    MAX-ACCESS      read-only
    STATUS      current
    DESCRIPTION
        "The conflict state of the binding SID."
    ::= { unisSrv6PolicyEntry 8 }

-- SRv6-TE policy path table.

unisSrv6PolicyPathTable OBJECT-TYPE
    SYNTAX      SEQUENCE OF UnisSrv6PolicyPathEntry
    MAX-ACCESS      not-accessible
    STATUS      current
    DESCRIPTION
        "This table provides information about SRv6-TE policy candidate paths."
    ::= { unisSrv6PolicyObjects 3 }

unisSrv6PolicyPathEntry OBJECT-TYPE
    SYNTAX      UnisSrv6PolicyPathEntry
    MAX-ACCESS      not-accessible
    STATUS      current
    DESCRIPTION
        "Each entry contains information about candidate paths of a policy."
    INDEX       { unisSrv6PolicyPathColor, unisSrv6PolicyPathEndPoint,
                  unisSrv6PolicyPathProto, unisSrv6PolicyPathInst,
          unisSrv6PolicyPathOri,
          unisSrv6PolicyPathDis }
    ::= { unisSrv6PolicyPathTable 1 }

UnisSrv6PolicyPathEntry ::= SEQUENCE {
    unisSrv6PolicyPathColor
        Unsigned32,
    unisSrv6PolicyPathEndPoint
        InetAddressIPv6,
    unisSrv6PolicyPathProto
        INTEGER,
    unisSrv6PolicyPathInst
        Integer32,
    unisSrv6PolicyPathOri
        OCTET STRING,
    unisSrv6PolicyPathDis
        Unsigned32,
    unisSrv6PolicyPathPref
        Unsigned32,
    unisSrv6PolicyPathPreviousRole
        OCTET STRING,
    unisSrv6PolicyPathDownReason
        OCTET STRING
    }

unisSrv6PolicyPathColor OBJECT-TYPE
    SYNTAX      Unsigned32 (0..4294967295)
    MAX-ACCESS      accessible-for-notify
    STATUS      current
    DESCRIPTION
        "The color associates the SRv6-TE policy with certain intent."
    ::= { unisSrv6PolicyPathEntry 1 }

unisSrv6PolicyPathEndPoint OBJECT-TYPE
    SYNTAX      InetAddressIPv6
    MAX-ACCESS      accessible-for-notify
    STATUS      current
    DESCRIPTION
        "The endpoint is the destination of the SRv6-TE policy."
    ::= { unisSrv6PolicyPathEntry 2 }

unisSrv6PolicyPathProto OBJECT-TYPE
    SYNTAX      INTEGER{
                   pcep(10),
                   bgp(20),
                   cli(30)
               }
    MAX-ACCESS      accessible-for-notify
    STATUS      current
    DESCRIPTION
        "Protocol-Origin of a candidate path identifies the protocol that
         originates or signals the candidate path."
    ::= { unisSrv6PolicyPathEntry 3 }

unisSrv6PolicyPathInst OBJECT-TYPE
    SYNTAX      Integer32 (0..65535)
    MAX-ACCESS      accessible-for-notify
    STATUS      current
    DESCRIPTION
        "The instance is a value of BGP instance number, when
         the candidate path is originated by BGP."
    ::= { unisSrv6PolicyPathEntry 4 }

unisSrv6PolicyPathOri OBJECT-TYPE
    SYNTAX      OCTET STRING (SIZE (1..63))
    MAX-ACCESS      accessible-for-notify
    STATUS      current
    DESCRIPTION
        "Originator is the identifier of the node that instantiated or
         signalled the candidate path on the headend."
    ::= { unisSrv6PolicyPathEntry 5 }

unisSrv6PolicyPathDis OBJECT-TYPE
    SYNTAX      Unsigned32
    MAX-ACCESS      accessible-for-notify
    STATUS      current
    DESCRIPTION
        "The discriminator uniquely identifies a candidate path from a
         specific Protocol-Origin."
    ::= { unisSrv6PolicyPathEntry 6 }

unisSrv6PolicyPathPref OBJECT-TYPE
    SYNTAX      Unsigned32
    MAX-ACCESS      read-only
    STATUS      current
    DESCRIPTION
        "The preference of the SRv6-TE policy candidate path."
    ::= { unisSrv6PolicyPathEntry 7 }

unisSrv6PolicyPathPreviousRole OBJECT-TYPE
    SYNTAX      OCTET STRING (SIZE (0..31))
    MAX-ACCESS      read-only
    STATUS      current
    DESCRIPTION
        "The previous role of an SRv6-TE policy candidate path.
         The value may be primary or backup."
    ::= { unisSrv6PolicyPathEntry 8 }

unisSrv6PolicyPathDownReason OBJECT-TYPE
    SYNTAX      OCTET STRING (SIZE (0..51))
    MAX-ACCESS      read-only
    STATUS      current
    DESCRIPTION
        "Base identity for the reasons why SRv6-TE policy candidate path
         is operationally down."
    ::= { unisSrv6PolicyPathEntry 9 }

-- Segment list information table for the policy
unisSrv6PolicySeglistTable OBJECT-TYPE
    SYNTAX SEQUENCE OF UnisSrv6PolicySeglistEntry
    MAX-ACCESS not-accessible
    STATUS current
    DESCRIPTION
        "This table provides information about the segment lists for the
         SRv6-TE policy."
    ::= { unisSrv6PolicyObjects 4 }

unisSrv6PolicySeglistEntry OBJECT-TYPE
    SYNTAX UnisSrv6PolicySeglistEntry
    MAX-ACCESS not-accessible
    STATUS current
    DESCRIPTION
        "Each entry contains information about segment lists."
    INDEX { unisSrv6PolicySeglistColor, unisSrv6PolicySeglistEndPoint,
            unisSrv6PolicySeglistPathProto,  unisSrv6PolicySeglistPathInst,
            unisSrv6PolicySeglistPathOri, unisSrv6PolicySeglistPathDis,
            unisSrv6PolicySeglistId }
    ::= { unisSrv6PolicySeglistTable 1 }

UnisSrv6PolicySeglistEntry ::=
    SEQUENCE {
        unisSrv6PolicySeglistColor
            Unsigned32,
        unisSrv6PolicySeglistEndPoint
            InetAddressIPv6,
        unisSrv6PolicySeglistPathProto
            INTEGER,
        unisSrv6PolicySeglistPathInst
            Integer32,
        unisSrv6PolicySeglistPathOri
            OCTET STRING,
        unisSrv6PolicySeglistPathDis
            Unsigned32,
        unisSrv6PolicySeglistId
            Unsigned32,
        unisSrv6PolicySeglistName
            OCTET STRING,
        unisSrv6PolicySeglistStatus
           OCTET STRING,
        unisSrv6PolicySeglistDownReason
            OCTET STRING
     }

unisSrv6PolicySeglistColor OBJECT-TYPE
    SYNTAX Unsigned32 (0..4294967295)
    MAX-ACCESS accessible-for-notify
    STATUS current
    DESCRIPTION
        "The color associates the SRv6-TE policy with certain intent."
    ::= { unisSrv6PolicySeglistEntry 1 }

unisSrv6PolicySeglistEndPoint OBJECT-TYPE
    SYNTAX InetAddressIPv6
    MAX-ACCESS accessible-for-notify
    STATUS current
    DESCRIPTION
        "The endpoint is the destination of the SRv6-TE policy."
    ::= { unisSrv6PolicySeglistEntry 2 }

unisSrv6PolicySeglistPathProto OBJECT-TYPE
    SYNTAX INTEGER{
                   pcep(10),
                   bgp(20),
                   cli(30)
               }
    MAX-ACCESS accessible-for-notify
    STATUS current
    DESCRIPTION
        "Protocol-Origin of a candidate path identifies the protocol that
         originates or signals the candidate path."
    ::= { unisSrv6PolicySeglistEntry 3 }

unisSrv6PolicySeglistPathInst OBJECT-TYPE
    SYNTAX Integer32 (0..65535)
    MAX-ACCESS accessible-for-notify
    STATUS current
    DESCRIPTION
        "The instance is a BGP instance number when
         the candidate path is originated by BGP."
    ::= { unisSrv6PolicySeglistEntry 4 }

unisSrv6PolicySeglistPathOri OBJECT-TYPE
    SYNTAX OCTET STRING (SIZE (1..63))
    MAX-ACCESS accessible-for-notify
    STATUS current
    DESCRIPTION
        "Originator is the identifier of the node that instantiated or
         signalled the candidate path on the headend."
    ::= { unisSrv6PolicySeglistEntry 5 }

unisSrv6PolicySeglistPathDis OBJECT-TYPE
    SYNTAX Unsigned32
    MAX-ACCESS accessible-for-notify
    STATUS current
    DESCRIPTION
        "The discriminator uniquely identifies a candidate path from a
         specific Protocol-Origin."
    ::= { unisSrv6PolicySeglistEntry 6 }

unisSrv6PolicySeglistId OBJECT-TYPE
    SYNTAX Unsigned32 (1..4294967295)
    MAX-ACCESS accessible-for-notify
    STATUS current
    DESCRIPTION
        "The ID uniquely identifies the segment list."
    ::= { unisSrv6PolicySeglistEntry 7 }

unisSrv6PolicySeglistName OBJECT-TYPE
    SYNTAX OCTET STRING (SIZE (0..128))
    MAX-ACCESS read-only
    STATUS current
    DESCRIPTION
        "The name of the segment list."
    ::= { unisSrv6PolicySeglistEntry 8 }

unisSrv6PolicySeglistStatus OBJECT-TYPE
    SYNTAX      OCTET STRING (SIZE (0..31))
    MAX-ACCESS      read-only
    STATUS      current
    DESCRIPTION
        "The status of segment list."
    ::= { unisSrv6PolicySeglistEntry 9 }

unisSrv6PolicySeglistDownReason OBJECT-TYPE
    SYNTAX      OCTET STRING (SIZE (0..51))
    MAX-ACCESS      read-only
    STATUS      current
    DESCRIPTION
        "Base identity for the reasons why segment list is down."
    ::= { unisSrv6PolicySeglistEntry 10 }

-- Notification Definitions

-- The notifications need to be throttled so as to not overwhelm the
-- management agent in case of rapid changes to the SR-TE Policy module.

unisSrv6PolicyStatusChange NOTIFICATION-TYPE
    OBJECTS { unisSrv6PolicyColor,
        unisSrv6PolicyEndPoint,
        unisSrv6PolicyStatus,
        unisSrv6PolicyDownReason
        }
    STATUS       current
    DESCRIPTION
        "An unisSrv6PolicyStatusChange trap signifies that there
         has been a change in the state of a policy.
         This trap should be generated when the policy
         state regresses (e.g., goes from active to Down)
         or progresses to a terminal state
         (i.e., down)."
    ::= { unisSrv6PolicyNotifications 1 }

unisSrv6PolicyBsidConflict NOTIFICATION-TYPE
    OBJECTS { unisSrv6PolicyColor,
        unisSrv6PolicyEndPoint,
        unisSrv6PolicyBsid,
        unisSrv6PolicyBsidFailReason,
        unisSrv6PolicyBsidConflictState
        }
    STATUS       current
    DESCRIPTION
        "BSID conflicts."
    ::= { unisSrv6PolicyNotifications 2 }

unisSrv6PolicyBsidConflictClear NOTIFICATION-TYPE
    OBJECTS  { unisSrv6PolicyColor,
        unisSrv6PolicyEndPoint,
        unisSrv6PolicyBsid,
        unisSrv6PolicyBsidFailReason,
        unisSrv6PolicyBsidConflictState
        }
    STATUS  current
    DESCRIPTION
        "BSID conflicts resolved"
    ::= { unisSrv6PolicyNotifications 3 }

unisSrv6PolicyDown NOTIFICATION-TYPE
    OBJECTS { unisSrv6PolicyColor,
        unisSrv6PolicyEndPoint,
        unisSrv6PolicyDownReason
        }
    STATUS  current
    DESCRIPTION
        "Policy down"
    ::= { unisSrv6PolicyNotifications 4 }

unisSrv6PolicyDownClear NOTIFICATION-TYPE
    OBJECTS { unisSrv6PolicyColor,
        unisSrv6PolicyEndPoint
    }
    STATUS  current
    DESCRIPTION
              "Policy down cleared"
    ::= { unisSrv6PolicyNotifications 5 }

unisSrv6PolicyResExdUppLimit NOTIFICATION-TYPE
    OBJECTS { unisSrv6PolicyResourceType,
        unisSrv6PolicyResCurrentCnt,
        unisSrv6PolicyResUpperLimit,
        unisSrv6PolicyResLowerLimit,
        unisSrv6PolicyResourceTotalCnt }
    STATUS  current
    DESCRIPTION
        "The number of used SRv6-TE policy resources exceeded the upper
               threshold."
    ::= { unisSrv6PolicyNotifications 6 }

unisSrv6PolicyResExceedClear NOTIFICATION-TYPE
    OBJECTS { unisSrv6PolicyResourceType,
        unisSrv6PolicyResCurrentCnt,
        unisSrv6PolicyResUpperLimit,
        unisSrv6PolicyResLowerLimit,
        unisSrv6PolicyResourceTotalCnt
        }
    STATUS  current
    DESCRIPTION
        "The number of used SRv6-TE policy resources fell below the lower
               threshold."
    ::= { unisSrv6PolicyNotifications 7 }

unisSrv6PathDown NOTIFICATION-TYPE
    OBJECTS { unisSrv6PolicyPathColor,
        unisSrv6PolicyPathEndPoint,
        unisSrv6PolicyPathProto,
        unisSrv6PolicyPathInst,
        unisSrv6PolicyPathOri,
        unisSrv6PolicyPathDis,
        unisSrv6PolicyPathPref,
        unisSrv6PolicyPathPreviousRole,
        unisSrv6PolicyPathDownReason
        }
    STATUS       current
    DESCRIPTION
        "An unisSrv6PathDown trap signifies that there
         has been a change in the state of a policy primary
         or backup path."
    ::= { unisSrv6PolicyNotifications 8 }

unisSrv6PolicySeglistDown NOTIFICATION-TYPE
    OBJECTS { unisSrv6PolicySeglistColor,
        unisSrv6PolicySeglistEndPoint,
        unisSrv6PolicySeglistPathProto,
        unisSrv6PolicySeglistPathInst,
        unisSrv6PolicySeglistPathOri,
        unisSrv6PolicySeglistPathDis,
        unisSrv6PolicySeglistId,
        unisSrv6PolicySeglistStatus,
        unisSrv6PolicySeglistDownReason
        }
    STATUS       current
    DESCRIPTION
        "An unisSrv6PolicySeglistDown trap signifies that there
         has been a change in the state of a segment list."
    ::= { unisSrv6PolicyNotifications 9 }

unisSrv6SeglistDownClear NOTIFICATION-TYPE
    OBJECTS { unisSrv6PolicySeglistColor,
        unisSrv6PolicySeglistEndPoint,
        unisSrv6PolicySeglistPathProto,
        unisSrv6PolicySeglistPathInst,
        unisSrv6PolicySeglistPathOri,
        unisSrv6PolicySeglistPathDis,
        unisSrv6PolicySeglistId,
        unisSrv6PolicySeglistStatus
        }
    STATUS       current
    DESCRIPTION
        "An unisSrv6SeglistDownClear trap signifies that there
         has been a change in the state of a segment list."
    ::= { unisSrv6PolicyNotifications 10 }

END
