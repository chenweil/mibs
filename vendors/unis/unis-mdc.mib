-- ===========================================================================================================
-- Copyright (c) 2020 Unisyue Technologies Co., Ltd.  All rights reserved.
--
-- Description: Mdc MIB
-- Reference:
-- Version: V1.1
-- History:
--  revision 1.0 2013-03-05 created by c08124
--  revision 1.1 2014-03-12 Modified unisMDCAllocateGroupIndex
--                          from (1..2147483647) to (-2147483648..2147483647)
--                          by j08116
--
-- ============================================================================================================
UNIS-MDC-MIB DEFINITIONS ::= BEGIN

IMPORTS
    entPhysicalIndex
        FROM ENTITY-MIB
    unisCommon
        FROM UNIS-OID-MIB
    Integer32, Unsigned32, OBJECT-TYPE, MODULE-IDENTITY, NOTIFICATION-TYPE
        FROM SNMPv2-SMI
    DisplayString, RowStatus, TruthValue, TEXTUAL-CONVENTION
        FROM SNMPv2-TC;

unisMDC MODULE-IDENTITY
    LAST-UPDATED "201303051448Z"
    ORGANIZATION
        "Unisyue Technologies Co., Ltd."
    CONTACT-INFO
        ""
    DESCRIPTION
        "This MIB contains objects to manage MDC (Multitenant Device Context) operations.

        Such as:
        1. Configure MDCs for a device and display MDCs and their status.
        2. Assign CPU, storage space, and memory space resources to the MDC, and display their status.
        3. Authorize the MDC to use the interface cards, and assign physical interfaces to an MDC.

        Default MDC: A device supporting MDCs is an MDC itself, and it is called the default MDC.
        From the default MDC, administrators can manage the entire physical device, create and delete non-default MDCs,
        and assign interfaces, CPU resources, storage space, and memory space to non-default MDCs.

        Non-default MDC: No MDCs can be created on a non-default MDC.
        Administrators of non-default MDCs can only manage and maintain their respective MDCs.
        A non-default MDC can use only the resources assigned to it."
    REVISION "201303051448Z"
    DESCRIPTION
        "The initial revision of this MIB module."
    ::= { unisCommon 136 }


-- Scalar MIB objects, which are considered as global variables
-- Global Level Configuration
UnisMdcActionValue ::= TEXTUAL-CONVENTION
    STATUS current
    DESCRIPTION
        "start: start the MDC
         stop: stop the MDC"
    SYNTAX INTEGER
        {
            start(1),
            stop(2)
        }

UnisMdcRunStatus ::= TEXTUAL-CONVENTION
    STATUS current
    DESCRIPTION
        "Status of the MDC:
        inactive: The MDC is stopped or not started yet.
        starting: The device is executing the mdc start command to start the MDC.
        active: The MDC is operating properly.
        stopping: The device is executing the undo mdc start command to stop the MDC.
        updating: The device is executing the location command to authorize the MDC to use an interface card."
    SYNTAX INTEGER
        {
            inactive(1),
            starting(2),
            active(3),
            stopping(4),
            updating(5)
        }


-- Node definitions

unisMDCScalarObjects OBJECT IDENTIFIER ::= { unisMDC 1 }

unisMDCMaxMDCNum OBJECT-TYPE
    SYNTAX Integer32
    MAX-ACCESS read-only
    STATUS current
    DESCRIPTION
        "The maximum number of MDCs which the system supported to create."
    ::= { unisMDCScalarObjects 1 }


unisMDCCurrentMDCNum OBJECT-TYPE
    SYNTAX Integer32
    MAX-ACCESS read-only
    STATUS current
    DESCRIPTION
        "The current number of MDCs which the system has created."
    ::= { unisMDCScalarObjects 2 }

unisMDCTables OBJECT IDENTIFIER ::= { unisMDC 2 }

-- The operation and information for MDC.
unisMDCControl OBJECT IDENTIFIER ::= { unisMDCTables 1 }


unisMDCControlTable OBJECT-TYPE
    SYNTAX SEQUENCE OF UnisMDCControlEntry
    MAX-ACCESS not-accessible
    STATUS current
    DESCRIPTION
        "This table is used to configure MDCs for a device and show MDC's status."
    ::= { unisMDCControl 1 }


unisMDCControlEntry OBJECT-TYPE
    SYNTAX UnisMDCControlEntry
    MAX-ACCESS not-accessible
    STATUS current
    DESCRIPTION
        "An entry of the unisMDCControlTable, every entry is corresponding with an MDC."
    INDEX { unisMDCIndex }
    ::= { unisMDCControlTable 1 }


UnisMDCControlEntry ::=
    SEQUENCE
        {
            unisMDCIndex
                Integer32,
            unisMDCName
                DisplayString,
            unisMDCAction
                UnisMdcActionValue,
            unisMDCStatus
                UnisMdcRunStatus,
            unisMDCRowStatus
                RowStatus
        }

unisMDCIndex OBJECT-TYPE
    SYNTAX Integer32 (1..2147483647)
    MAX-ACCESS accessible-for-notify
    STATUS current
    DESCRIPTION
        "MDC ID is used as MDCIndex, the value range of MDC ID depends on the device model.
         MDCIndex cannot be modified after creation."
    ::= { unisMDCControlEntry 1 }


unisMDCName OBJECT-TYPE
    SYNTAX DisplayString (SIZE (1..15))
    MAX-ACCESS read-create
    STATUS current
    DESCRIPTION
        "Specifies the MDC name, a case-sensitive string of 1 to 15 characters.
        The MDC name cannot be modified after creation."
    ::= { unisMDCControlEntry 2 }


unisMDCAction OBJECT-TYPE
    SYNTAX UnisMdcActionValue
    MAX-ACCESS read-write
    STATUS current
    DESCRIPTION
        "State of MDC action: start/stop.
        After an MDC is started, administrators of the MDC can log in to
        the MDC for MDC configuration and maintenance.
        Stopping an MDC interrupts all services on the MDC and logs out
        all users of the MDC.

        Non-default MDC cannot operate."
    DEFVAL { stop }
    ::= { unisMDCControlEntry 3 }


unisMDCStatus OBJECT-TYPE
    SYNTAX UnisMdcRunStatus
    MAX-ACCESS read-only
    STATUS current
    DESCRIPTION
        "Status of MDCs."
    ::= { unisMDCControlEntry 4 }


unisMDCRowStatus OBJECT-TYPE
    SYNTAX RowStatus
    MAX-ACCESS read-create
    STATUS current
    DESCRIPTION
        "The status of this table entry.
        Only support active, createAndGo and destroy."
    ::= { unisMDCControlEntry 5 }


unisMDCResource OBJECT IDENTIFIER ::= { unisMDCTables 2 }


unisMDCDISKResourceTable OBJECT-TYPE
    SYNTAX SEQUENCE OF UnisMDCDISKResourceEntry
    MAX-ACCESS not-accessible
    STATUS current
    DESCRIPTION
        "This table is for disk resource management:
        Specify a disk space percentage for an MDC and display the disk space usage.

        Default: All MDCs share the disk space in the system,
        and an MDC can use all free disk space in the system.

        Non-default MDC can only query the disk space usage."
    ::= { unisMDCResource 1 }


unisMDCDISKResourceEntry OBJECT-TYPE
    SYNTAX UnisMDCDISKResourceEntry
    MAX-ACCESS not-accessible
    STATUS current
    DESCRIPTION
        "An entry of the unisMDCDISKResourceTable, every entry is corresponding to
        disk resource of an MDC.

        Note that only entPhysicalIndex values that represent
        physical boards (i.e., associated entPhysicalClass value is
        'module(9)') are permitted to exist in this table."
    INDEX { entPhysicalIndex, unisMDCIndex, unisMDCDISKResourceInstance }
    ::= { unisMDCDISKResourceTable 1 }


UnisMDCDISKResourceEntry ::=
    SEQUENCE {
        unisMDCDISKResourceInstance
            Integer32,
        unisMDCDISKResourceInstanceName
            DisplayString,
        unisMDCDISKResourceMinLimit
            Integer32,
        unisMDCDISKResourceMaxLimit
            Integer32,
        unisMDCDISKResourceReserve
            Unsigned32,
        unisMDCDISKResourceQuota
            Unsigned32,
        unisMDCDISKResourceUsage
            Unsigned32,
        unisMDCDISKResourceAvailable
            Unsigned32
     }

unisMDCDISKResourceInstance OBJECT-TYPE
    SYNTAX Integer32 (1..2147483647)
    MAX-ACCESS not-accessible
    STATUS current
    DESCRIPTION
        "Instance index of disk resource.
         Different instances for disk: Flash, CF cards."
    ::= { unisMDCDISKResourceEntry 1 }


unisMDCDISKResourceInstanceName OBJECT-TYPE
    SYNTAX DisplayString (SIZE (1..32))
    MAX-ACCESS read-only
    STATUS current
    DESCRIPTION
        "Instance name of disk resource.

        Such as: Flash, CF cards."
    ::= { unisMDCDISKResourceEntry 2 }


unisMDCDISKResourceMinLimit OBJECT-TYPE
    SYNTAX Integer32 (0..100)
    UNITS       "percent"
    MAX-ACCESS read-write
    STATUS current
    DESCRIPTION
        "Limit minimum (reserve resources, must be all 0)."
    ::= { unisMDCDISKResourceEntry 3 }


unisMDCDISKResourceMaxLimit OBJECT-TYPE
    SYNTAX Integer32 (1..100)
    UNITS       "percent"
    MAX-ACCESS read-write
    STATUS current
    DESCRIPTION
        "Maximum of available resources of disk.
        Make sure the disk space amount assigned to an MDC is
        greater than the disk space amount the MDC is using.
        Non-default MDC cannot set"
    ::= { unisMDCDISKResourceEntry 4 }

unisMDCDISKResourceReserve OBJECT-TYPE
    SYNTAX Unsigned32
    UNITS       "KB"
    MAX-ACCESS read-only
    STATUS current
    DESCRIPTION
        "The reserve limit resources of disk."
    ::= { unisMDCDISKResourceEntry 5 }

unisMDCDISKResourceQuota OBJECT-TYPE
    SYNTAX Unsigned32
    UNITS       "KB"
    MAX-ACCESS read-only
    STATUS current
    DESCRIPTION
        "The total limit resources of disk according to unisMDCDiskResourceMaxLimit."
    ::= { unisMDCDISKResourceEntry 6 }


unisMDCDISKResourceUsage OBJECT-TYPE
    SYNTAX Unsigned32
    UNITS       "KB"
    MAX-ACCESS read-only
    STATUS current
    DESCRIPTION
        "Current usage of disk resources."
    ::= { unisMDCDISKResourceEntry 7 }


unisMDCDISKResourceAvailable OBJECT-TYPE
    SYNTAX Unsigned32
    UNITS       "KB"
    MAX-ACCESS read-only
    STATUS current
    DESCRIPTION
        "Current available resources of disk."
    ::= { unisMDCDISKResourceEntry 8 }

unisMDCMemoryResourceTable OBJECT-TYPE
    SYNTAX SEQUENCE OF UnisMDCMemoryResourceEntry
    MAX-ACCESS not-accessible
    STATUS current
    DESCRIPTION
        "This table is for memory resource management:
         Specify a memory space percentage for an MDC and display the memory space usage.
         Default: All MDCs share the memory space in the system, and an MDC can use all free memory.

         Non-default MDC can only query resource message of memory."
    ::= { unisMDCResource 2 }


unisMDCMemoryResourceEntry OBJECT-TYPE
    SYNTAX UnisMDCMemoryResourceEntry
    MAX-ACCESS not-accessible
    STATUS current
    DESCRIPTION
        "An entry of the unisMDCMemoryResourceTable, every entry is corresponding
        with memory resource of an MDC.

        Note that only entPhysicalIndex values that represent
        physical boards (i.e., associated entPhysicalClass value is
        'module(9)') are permitted to exist in this table."
    INDEX { entPhysicalIndex, unisMDCIndex }
    ::= { unisMDCMemoryResourceTable 1 }


UnisMDCMemoryResourceEntry ::=
    SEQUENCE {
        unisMDCMemoryResourceMinLimit
            Integer32,
        unisMDCMemoryResourceMaxLimit
            Integer32,
        unisMDCMemoryResourceReserve
            Unsigned32,
        unisMDCMemoryResourceQuota
            Unsigned32,
        unisMDCMemoryResourceUsage
            Unsigned32,
        unisMDCMemoryResourceAvailable
            Unsigned32
     }

unisMDCMemoryResourceMinLimit OBJECT-TYPE
    SYNTAX Integer32 (0..100)
    UNITS       "percent"
    MAX-ACCESS read-write
    STATUS current
    DESCRIPTION
        "Limit minimum(reserve resources, must be all 0).

        Non-default MDC cannot set."
    ::= { unisMDCMemoryResourceEntry 1 }


unisMDCMemoryResourceMaxLimit OBJECT-TYPE
    SYNTAX Integer32 (1..100)
    UNITS       "percent"
    MAX-ACCESS read-write
    STATUS current
    DESCRIPTION
        "Maximum of available resources of memory,
        it specifies the ratio of the memory space that an MDC can use.
        Make sure this amount is sufficient for the MDC to operate properly.
        Non-default MDC cannot set."
    ::= { unisMDCMemoryResourceEntry 2 }

unisMDCMemoryResourceReserve OBJECT-TYPE
    SYNTAX Unsigned32
    UNITS       "KB"
    MAX-ACCESS read-only
    STATUS current
    DESCRIPTION
        "The reserve limit resources of memory."
    ::= { unisMDCMemoryResourceEntry 3 }

unisMDCMemoryResourceQuota OBJECT-TYPE
    SYNTAX Unsigned32
    UNITS       "KB"
    MAX-ACCESS read-only
    STATUS current
    DESCRIPTION
        "The total limit resources of memory."
    ::= { unisMDCMemoryResourceEntry 4 }

unisMDCMemoryResourceUsage OBJECT-TYPE
    SYNTAX Unsigned32
    UNITS       "KB"
    MAX-ACCESS read-only
    STATUS current
    DESCRIPTION
        "Current usage of memory resources."
    ::= { unisMDCMemoryResourceEntry 5 }

unisMDCMemoryResourceAvailable OBJECT-TYPE
    SYNTAX Unsigned32
    UNITS       "KB"
    MAX-ACCESS read-only
    STATUS current
    DESCRIPTION
        "Current available value of memory resources."
    ::= { unisMDCMemoryResourceEntry 6 }

unisMDCCPUResourceTable OBJECT-TYPE
    SYNTAX SEQUENCE OF UnisMDCCPUResourceEntry
    MAX-ACCESS not-accessible
    STATUS current
    DESCRIPTION
        "This table is for CPU resource management:
        Specify a CPU weight for an MDC and display the CPU usage.
        The amount of CPU resources an MDC can use depends on the CPU weight
        settings for all MDCs that share the same CPU.

        Non-default MDC can only query CPU resources."
    ::= { unisMDCResource 3 }


unisMDCCPUResourceEntry OBJECT-TYPE
    SYNTAX UnisMDCCPUResourceEntry
    MAX-ACCESS not-accessible
    STATUS current
    DESCRIPTION
        "An entry of the unisMDCCPUResourceTable, every entry is corresponding
        with CPU resources of an MDC.

        Note that only entPhysicalIndex values that represent
        physical boards (i.e., associated entPhysicalClass value is
        'module(9)') are permitted to exist in this table."
    INDEX {entPhysicalIndex, unisMDCIndex }
    ::= { unisMDCCPUResourceTable 1 }


UnisMDCCPUResourceEntry ::=
    SEQUENCE {
        unisMDCCPUResourceLimit
            Integer32,
        unisMDCCPUResourceUsage
            Integer32
     }

unisMDCCPUResourceLimit OBJECT-TYPE
    SYNTAX Integer32 (1..10)
    UNITS     "weight"
    MAX-ACCESS read-write
    STATUS current
    DESCRIPTION
        "CPU weight-maximum of available resources of CPU,
        this number specifies a CPU weight for an MDC.
        Non-default MDC cannot set."
    ::= { unisMDCCPUResourceEntry 1 }


unisMDCCPUResourceUsage OBJECT-TYPE
    SYNTAX Integer32 (0..100)
    UNITS    "percent"
    MAX-ACCESS read-only
    STATUS current
    DESCRIPTION
        "the CPU usage"
    ::= { unisMDCCPUResourceEntry 2 }


-- The MDC location status.
unisMDCLocation OBJECT IDENTIFIER ::= { unisMDCTables 3 }

unisMDCLocationTable OBJECT-TYPE
    SYNTAX SEQUENCE OF UnisMDCLocationEntry
    MAX-ACCESS not-accessible
    STATUS current
    DESCRIPTION
        "This table is for location management:
        Authorize an MDC to use an interface card and query state of location.
        To assign physical interfaces to an MDC, administrators must authorize the MDC
        to use the interface cards to which the physical interfaces belong.

        Default: All interface cards of the device belong to the default MDC,
        and a non-default MDC cannot use any interface card.
        Non-default MDC can only query location state."
    ::= { unisMDCLocation 1 }


unisMDCLocationEntry OBJECT-TYPE
    SYNTAX UnisMDCLocationEntry
    MAX-ACCESS not-accessible
    STATUS current
    DESCRIPTION
        "An entry of the unisMDCLocationTable, every entry is the status
        whether an MDC has been Authorized to use the interface cards.

        Note that only entPhysicalIndex values that represent
        physical boards (i.e., associated entPhysicalClass value is
        'module(9)') are permitted to exist in this table."
    INDEX { entPhysicalIndex, unisMDCIndex }
    ::= { unisMDCLocationTable 1 }


UnisMDCLocationEntry ::=
    SEQUENCE {
        unisMDCLocationStatus
            TruthValue
     }

unisMDCLocationStatus OBJECT-TYPE
    SYNTAX TruthValue
    MAX-ACCESS read-write
    STATUS current
    DESCRIPTION
        "To authorize the MDC to use the interface cards, set the value
        of this object to 'true (1)'.  To cancel the authorization, set this
        value to 'false (2)'.

        Note that the return noError means the command is being executed.
        For the execution result, check unisMDCLocationStatus."
    ::= { unisMDCLocationEntry 1 }


-- The interfaces allocate information.
unisMDCAllocate OBJECT IDENTIFIER ::= { unisMDCTables 4 }

unisMDCGroupIfTable OBJECT-TYPE
    SYNTAX SEQUENCE OF UnisMDCGroupIfEntry
    MAX-ACCESS not-accessible
    STATUS current
    DESCRIPTION
        "This table indication of relation between interfaces and groups,
        which helps to realize the allocation, together with unisMDCAllocateTable.

        Non-default MDC cannot operate."
    ::= { unisMDCAllocate 1 }


unisMDCGroupIfEntry OBJECT-TYPE
    SYNTAX UnisMDCGroupIfEntry
    MAX-ACCESS not-accessible
    STATUS current
    DESCRIPTION
        "An entry of the unisMDCGroupIfTable, every entry is the relationship
        between interfaces and groups.

        Due to hardware restrictions, the interfaces on some interface cards are grouped.
        The interfaces in a group must be assigned to the same MDC at the same time or
        removed from an MDC at the same time. Interface grouping depends on the device model.

        This table is used for unisMDCAllocateTable to show interfae group lists.

        Note that only entPhysicalIndex values that represent
        physical ports (i.e., associated entPhysicalClass value is
        'port(10)') are permitted to exist in this table."
    INDEX { entPhysicalIndex }
    ::= { unisMDCGroupIfTable 1 }


UnisMDCGroupIfEntry ::=
    SEQUENCE {
        unisMDCGroupIdentity
            Integer32
     }

unisMDCGroupIdentity OBJECT-TYPE
    SYNTAX Integer32
    MAX-ACCESS read-only
    STATUS current
    DESCRIPTION
        "The interface group ID. There are two parts for this id
         depicted as follows:

         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { unisMDCGroupIfEntry 2 }

unisMDCAllocateTable OBJECT-TYPE
    SYNTAX SEQUENCE OF UnisMDCAllocateEntry
    MAX-ACCESS not-accessible
    STATUS current
    DESCRIPTION
        "This table is used to assigning a physical interface to an MDC.
        It is allowed that allocate interfaces to a non-default MDC from the default MDC,
        and allocate interfaces back to the default MDC from a non-default MDC.

        All physical interfaces on the device belong to the default MDC,
        and a non-default MDC has no physical interfaces to use.
        Multiple physical interfaces can be assigned to a non-default MDC.
        A physical interface must meet the following conditions to be assigned to a non-default MDC:
        1. Belongs to the default MDC.
        2. Not the console or AUX port.
        3. Not the management Ethernet interface.
        4. Not in an interface group with an interface assigned to another MDC.
        5. The default MDC uses only the physical interfaces that are not assigned to a non-default MDC.

        Non-default MDC cannot set this table."
    ::= { unisMDCAllocate 2 }


unisMDCAllocateEntry OBJECT-TYPE
    SYNTAX UnisMDCAllocateEntry
    MAX-ACCESS not-accessible
    STATUS current
    DESCRIPTION
        "An entry of the unisMDCAllocateTable, every entry is the status
        whether physical interfaces have been assigned to an MDC."
    INDEX { unisMDCAllocateGroupIndex }
    ::= { unisMDCAllocateTable 1 }


UnisMDCAllocateEntry ::=
    SEQUENCE {
        unisMDCAllocateGroupIndex
            Integer32,
        unisMDCAllocateGroupDescription
            DisplayString,
        unisMDCAllocateMDCId
            Integer32
     }

unisMDCAllocateGroupIndex OBJECT-TYPE
    SYNTAX Integer32 (-2147483648..2147483647)
    MAX-ACCESS not-accessible
    STATUS current
    DESCRIPTION
        "The interface group ID, the same as unisMDCGroupIdentity.
         There are two parts for this id.

         depicted as follows:
         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { unisMDCAllocateEntry 1 }

unisMDCAllocateGroupDescription OBJECT-TYPE
    SYNTAX DisplayString (SIZE (1..255))
    MAX-ACCESS read-only
    STATUS current
    DESCRIPTION
        "Interfaces list
        Such as:
        GigabitEthernet4/5/0/1 to GigabitEthernet4/5/0/24,
        GigabitEthernet4/5/0/48"
    ::= { unisMDCAllocateEntry 2 }


unisMDCAllocateMDCId OBJECT-TYPE
    SYNTAX Integer32 (1..2147483647)
    MAX-ACCESS read-write
    STATUS current
    DESCRIPTION
        "MDC ID is used as unisMDCAllocateMDCId.
        Default MDC: It is allowed that allocate interfaces to non-default MDC from
        the default MDC, and allocate interfaces back to the default MDC from
        a non-default MDC.
        Non-default MDC cannot set allocation, can only query grouping of own MDC."
    ::= { unisMDCAllocateEntry 3 }


unisMDCNotification OBJECT IDENTIFIER ::= { unisMDC 3 }

unisMDCNotificationObjects OBJECT IDENTIFIER ::= { unisMDCNotification 0 }

unisMDCStateChangeToActive NOTIFICATION-TYPE
    OBJECTS {unisMDCIndex, unisMDCName}
    STATUS current
    DESCRIPTION
        "The unisMDCStateChangeToActive trap indicates that the MDC status has changed to active."
    ::= { unisMDCNotificationObjects 1 }

unisMDCStateChangeToInactive NOTIFICATION-TYPE
    OBJECTS {unisMDCIndex, unisMDCName}
    STATUS current
    DESCRIPTION
        "The unisMDCStateChangeToInactive trap indicates that the MDC status has changed to inactive."
    ::= { unisMDCNotificationObjects 2 }

END
