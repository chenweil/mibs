-- =============================================================================
-- Copyright (c) 2020 Unisyue Technologies Co., Ltd.  All rights reserved.
--
-- Description:
--   The file defines a MIB for the wireless multicast to unicast (WM2U) feature,
--   which is used to improve multicast performance.
-- Reference:
-- Version: V1.1
-- History:
--   V1.0 created by sunanzhi
--     Initial version 2015-04-27
--   V1.1 2016-1-25 updated by sunanzhi
--     Modify UnisDot11WM2UAgingTimeEntry
-- =============================================================================
UNIS-DOT11-WM2U-MIB DEFINITIONS ::= BEGIN

IMPORTS
    TimeTicks, Unsigned32, OBJECT-TYPE, MODULE-IDENTITY
        FROM SNMPv2-SMI
    MacAddress, TEXTUAL-CONVENTION
        FROM SNMPv2-TC
    InetAddress, InetAddressType
        FROM INET-ADDRESS-MIB   -- [RFC4001]
    unisDot11
        FROM UNIS-OID-MIB;

unisDot11WM2U MODULE-IDENTITY
    LAST-UPDATED "201601251020Z"        -- January 25, 2016 at 10:20 GMT
    ORGANIZATION
        "Unisyue Technologies Co., Ltd."
    CONTACT-INFO
        ""
    DESCRIPTION
        "This MIB provides information about the WM2U feature."
    REVISION "201601251020Z"        -- January 25, 2016 at 10:20 GMT
    DESCRIPTION
        "Modify UnisDot11WM2UAgingTimeEntry."
    REVISION "201503311551Z"        -- March 31, 2015 at 13:51 GMT
    DESCRIPTION
        "The initial revision of this MIB module."
    ::= {  unisDot11 16 }

--
-- Textual conventions
--
UnisDot11WM2UEnableStatus ::= TEXTUAL-CONVENTION
        STATUS      current
        DESCRIPTION
            "The enable status values for objects.
            Values include enabled and disbaled."
        SYNTAX      INTEGER { enabled(1), disabled(2) }

UnisDot11WM2UAction ::= TEXTUAL-CONVENTION
        STATUS      current
        DESCRIPTION
            "Action to take when the number of clients exceeds the threshold."
        SYNTAX  INTEGER
            {
            drop(1),
            unicast(2),
            multicast(3)
            }

UnisDot11WM2UGroupVersion ::= TEXTUAL-CONVENTION
        STATUS      current
        DESCRIPTION
            "Multicast protocol version."
        SYNTAX  INTEGER
            {
            igmpv1orv2(1),
            igmpv3(2),
            mldv1(3),
            mldv2(4)
            }

UnisDot11WM2UGroupMode ::= TEXTUAL-CONVENTION
        STATUS      current
        DESCRIPTION
            "Multicast source filtering mode."
        SYNTAX  INTEGER
            {
            include(1),
            exclude(2)
            }


--
-- Node definitions
--
unisDot11WM2UConfigGroup OBJECT IDENTIFIER ::= { unisDot11WM2U 1 }
unisDot11WM2UDataGroup OBJECT IDENTIFIER ::= { unisDot11WM2U 2 }

unisDot11WM2USrvTempStatesTable OBJECT-TYPE
    SYNTAX SEQUENCE OF UnisDot11WM2USrvTempStatesEntry
    MAX-ACCESS not-accessible
    STATUS current
    DESCRIPTION
        "The table contains the enable status of WM2U in service templates."
    ::= { unisDot11WM2UConfigGroup 1 }

unisDot11WM2USrvTempStatesEntry OBJECT-TYPE
    SYNTAX UnisDot11WM2USrvTempStatesEntry
    MAX-ACCESS not-accessible
    STATUS current
    DESCRIPTION
        "Each entry contains the enable status of WM2U in a service template."
    INDEX { unisDot11WM2USrvTempName,  unisDot11WM2USrvTempAddressType}
    ::= { unisDot11WM2USrvTempStatesTable 1 }

UnisDot11WM2USrvTempStatesEntry ::= SEQUENCE {
        unisDot11WM2USrvTempName                    OCTET STRING,
        unisDot11WM2USrvTempAddressType                  InetAddressType,
        unisDot11WM2USrvTempState                   UnisDot11WM2UEnableStatus
     }

unisDot11WM2USrvTempName OBJECT-TYPE
    SYNTAX OCTET STRING (SIZE (1..63))
    MAX-ACCESS not-accessible
    STATUS current
    DESCRIPTION
        "Represents the name of the service template."
    ::= { unisDot11WM2USrvTempStatesEntry 1 }

unisDot11WM2USrvTempAddressType OBJECT-TYPE
    SYNTAX InetAddressType
    MAX-ACCESS not-accessible
    STATUS current
    DESCRIPTION
        "Represents the address type."
    ::= { unisDot11WM2USrvTempStatesEntry 2 }

unisDot11WM2USrvTempState OBJECT-TYPE
    SYNTAX UnisDot11WM2UEnableStatus
    MAX-ACCESS read-write
    STATUS current
    DESCRIPTION
        "The enable status of WM2U."
    ::= { unisDot11WM2USrvTempStatesEntry 3 }

unisDot11WM2UAgingTimeTable OBJECT-TYPE
    SYNTAX SEQUENCE OF UnisDot11WM2UAgingTimeEntry
    MAX-ACCESS not-accessible
    STATUS current
    DESCRIPTION
        "The table contains WM2U entry aging information."
    ::= { unisDot11WM2UConfigGroup 2 }

unisDot11WM2UAgingTimeEntry OBJECT-TYPE
    SYNTAX UnisDot11WM2UAgingTimeEntry
    MAX-ACCESS not-accessible
    STATUS current
    DESCRIPTION
        "Each entry contains the aging time for an address type."
    INDEX { unisDot11WM2UAgingAddressType }
    ::= { unisDot11WM2UAgingTimeTable 1 }

UnisDot11WM2UAgingTimeEntry ::= SEQUENCE {
        unisDot11WM2UAgingAddressType                    InetAddressType,
        unisDot11WM2UAgingTime                           Unsigned32,
        unisDot11WM2UAgingTimeState                      UnisDot11WM2UEnableStatus
     }

unisDot11WM2UAgingAddressType OBJECT-TYPE
    SYNTAX InetAddressType
    MAX-ACCESS not-accessible
    STATUS current
    DESCRIPTION
        "Represents the address type."
    ::= { unisDot11WM2UAgingTimeEntry 1 }

unisDot11WM2UAgingTime OBJECT-TYPE
    SYNTAX Unsigned32 (60..3600)
    UNITS   "seconds"
    MAX-ACCESS read-write
    STATUS current
    DESCRIPTION
        "Represents the aging time."
    ::= { unisDot11WM2UAgingTimeEntry 2 }

unisDot11WM2UAgingTimeState OBJECT-TYPE
    SYNTAX UnisDot11WM2UEnableStatus
    MAX-ACCESS read-write
    STATUS current
    DESCRIPTION
        "The configuration status of the aging time."
    ::= { unisDot11WM2UAgingTimeEntry 3 }

unisDot11WM2UClientEtyLmtTable OBJECT-TYPE
    SYNTAX SEQUENCE OF UnisDot11WM2UClientEtyLmtEntry
    MAX-ACCESS not-accessible
    STATUS current
    DESCRIPTION
        "The table contains the WM2U entry limit for each client."
    ::= { unisDot11WM2UConfigGroup 3 }

unisDot11WM2UClientEtyLmtEntry OBJECT-TYPE
    SYNTAX UnisDot11WM2UClientEtyLmtEntry
    MAX-ACCESS not-accessible
    STATUS current
    DESCRIPTION
        "Each entry contains the WM2U entry limit for each client of an
        address type."
    INDEX { unisDot11WM2UClientEtyAddrType }
    ::= { unisDot11WM2UClientEtyLmtTable 1 }

UnisDot11WM2UClientEtyLmtEntry ::= SEQUENCE {
        unisDot11WM2UClientEtyAddrType                InetAddressType,
        unisDot11WM2UClientValue                         Unsigned32,
        unisDot11WM2UClientState                         UnisDot11WM2UEnableStatus
     }

unisDot11WM2UClientEtyAddrType OBJECT-TYPE
    SYNTAX InetAddressType
    MAX-ACCESS not-accessible
    STATUS current
    DESCRIPTION
        "Represents the address type."
    ::= { unisDot11WM2UClientEtyLmtEntry 1 }

unisDot11WM2UClientValue OBJECT-TYPE
    SYNTAX Unsigned32 (8..1024)
    MAX-ACCESS read-write
    STATUS current
    DESCRIPTION
        "Maximum number of WM2U entries for each client of the address type."
    ::= { unisDot11WM2UClientEtyLmtEntry 2 }

unisDot11WM2UClientState OBJECT-TYPE
    SYNTAX UnisDot11WM2UEnableStatus
    MAX-ACCESS read-write
    STATUS current
    DESCRIPTION
        "The enable status of the per-client WM2U entry limit."
    ::= { unisDot11WM2UClientEtyLmtEntry 3 }

unisDot11WM2UGlobalEtyLmtTable OBJECT-TYPE
    SYNTAX SEQUENCE OF UnisDot11WM2UGlobalEntryLmtsEntry
    MAX-ACCESS not-accessible
    STATUS current
    DESCRIPTION
        "The table contains the WM2U table size."
    ::= { unisDot11WM2UConfigGroup 4 }

unisDot11WM2UGlobalEtyLmtEntry OBJECT-TYPE
    SYNTAX UnisDot11WM2UGlobalEntryLmtsEntry
    MAX-ACCESS not-accessible
    STATUS current
    DESCRIPTION
        "Each entry contains the WM2U table size for an address type."
    INDEX { unisDot11WM2UGlobalEtyAddrType }
    ::= { unisDot11WM2UGlobalEtyLmtTable 1 }

UnisDot11WM2UGlobalEntryLmtsEntry ::= SEQUENCE {
        unisDot11WM2UGlobalEtyAddrType                InetAddressType,
        unisDot11WM2UGlobalValue                         Unsigned32,
        unisDot11WM2UGlobalState                         UnisDot11WM2UEnableStatus
     }

unisDot11WM2UGlobalEtyAddrType OBJECT-TYPE
    SYNTAX InetAddressType
    MAX-ACCESS not-accessible
    STATUS current
    DESCRIPTION
        "Represents the address type."
    ::= { unisDot11WM2UGlobalEtyLmtEntry 1 }

unisDot11WM2UGlobalValue OBJECT-TYPE
    SYNTAX Unsigned32 (8..8192)
    MAX-ACCESS read-write
    STATUS current
    DESCRIPTION
        "WM2U table size(The maximum number of entries that the WM2U table
        can contain)."
    ::= { unisDot11WM2UGlobalEtyLmtEntry 2 }

unisDot11WM2UGlobalState OBJECT-TYPE
    SYNTAX UnisDot11WM2UEnableStatus
    MAX-ACCESS read-write
    STATUS current
    DESCRIPTION
        "The enable status of the WM2U table size setting."
    ::= { unisDot11WM2UGlobalEtyLmtEntry 3 }

unisDot11WM2UFwdClientLmtsTable OBJECT-TYPE
    SYNTAX SEQUENCE OF UnisDot11WM2UFwdClientLmtsEntry
    MAX-ACCESS not-accessible
    STATUS current
    DESCRIPTION
        "The table contains the limit on the number of clients of each address
        type in the WM2U table."
    ::= { unisDot11WM2UConfigGroup 5 }

unisDot11WM2UFwdClientLmtsEntry OBJECT-TYPE
    SYNTAX UnisDot11WM2UFwdClientLmtsEntry
    MAX-ACCESS not-accessible
    STATUS current
    DESCRIPTION
        "Each entry contains the limit on the number of clients of an address
        type in the WM2U table."
    INDEX { unisDot11WM2UFwdClientAddrType }
    ::= { unisDot11WM2UFwdClientLmtsTable 1 }

UnisDot11WM2UFwdClientLmtsEntry ::= SEQUENCE {
        unisDot11WM2UFwdClientAddrType                InetAddressType,
        unisDot11WM2UFwdClientValue                      Unsigned32,
        unisDot11WM2UFwdClientAction                     UnisDot11WM2UAction,
        unisDot11WM2UFwdClientState                      UnisDot11WM2UEnableStatus
     }

unisDot11WM2UFwdClientAddrType OBJECT-TYPE
    SYNTAX InetAddressType
    MAX-ACCESS not-accessible
    STATUS current
    DESCRIPTION
        "Represents the address type."
    ::= { unisDot11WM2UFwdClientLmtsEntry 1 }

unisDot11WM2UFwdClientValue OBJECT-TYPE
    SYNTAX Unsigned32 (1..256)
    MAX-ACCESS read-write
    STATUS current
    DESCRIPTION
        "Limit on the number of clients of the address type."
    ::= { unisDot11WM2UFwdClientLmtsEntry 2 }

unisDot11WM2UFwdClientAction OBJECT-TYPE
    SYNTAX UnisDot11WM2UAction
    MAX-ACCESS read-write
    STATUS current
    DESCRIPTION
        "Action to take when the number of clients exceeds the limit."
    ::= { unisDot11WM2UFwdClientLmtsEntry 3 }

unisDot11WM2UFwdClientState OBJECT-TYPE
    SYNTAX UnisDot11WM2UEnableStatus
    MAX-ACCESS read-write
    STATUS current
    DESCRIPTION
        "The enable status of the client limit."
    ::= { unisDot11WM2UFwdClientLmtsEntry 4 }

unisDot11WM2URateLimitsTable OBJECT-TYPE
    SYNTAX SEQUENCE OF UnisDot11WM2URateLimitsEntry
    MAX-ACCESS not-accessible
    STATUS current
    DESCRIPTION
        "The table contains multicast packet rate limit information."
    ::= { unisDot11WM2UConfigGroup 6 }

unisDot11WM2URateLimitsEntry OBJECT-TYPE
    SYNTAX UnisDot11WM2URateLimitsEntry
    MAX-ACCESS not-accessible
    STATUS current
    DESCRIPTION
        "Each entry contains the packet rate limit for an address type."
    INDEX { unisDot11WM2URateLmtsAddrType }
    ::= { unisDot11WM2URateLimitsTable 1 }

UnisDot11WM2URateLimitsEntry ::= SEQUENCE {
        unisDot11WM2URateLmtsAddrType                 InetAddressType,
        unisDot11WM2UInterval                            Unsigned32,
        unisDot11WM2UThreshold                           Unsigned32,
        unisDot11WM2URateLmtsState                       UnisDot11WM2UEnableStatus
     }

unisDot11WM2URateLmtsAddrType OBJECT-TYPE
    SYNTAX InetAddressType
    MAX-ACCESS not-accessible
    STATUS current
    DESCRIPTION
        "Represents the address type."
    ::= { unisDot11WM2URateLimitsEntry 1 }

unisDot11WM2UInterval OBJECT-TYPE
    SYNTAX Unsigned32 (60..3600)
    UNITS  "seconds"
    MAX-ACCESS read-write
    STATUS current
    DESCRIPTION
        "Interval for calculating the incoming multicast packet rate,
         unit for seconds."
    ::= { unisDot11WM2URateLimitsEntry 2 }

unisDot11WM2UThreshold OBJECT-TYPE
    SYNTAX Unsigned32 (1..100000)
    MAX-ACCESS read-write
    STATUS current
    DESCRIPTION
        "Threshold on the number of multicast packets received over the
        specified interval."
    ::= { unisDot11WM2URateLimitsEntry 3 }

unisDot11WM2URateLmtsState OBJECT-TYPE
    SYNTAX UnisDot11WM2UEnableStatus
    MAX-ACCESS read-write
    STATUS current
    DESCRIPTION
        "The enable status of IGMP packet rate limiting."
    ::= { unisDot11WM2URateLimitsEntry 4 }

unisDot11WM2UClientsTable OBJECT-TYPE
    SYNTAX SEQUENCE OF UnisDot11WM2UClientsEntry
    MAX-ACCESS not-accessible
    STATUS current
    DESCRIPTION
        "The table contains WM2U client information."
    ::= { unisDot11WM2UDataGroup 1 }

unisDot11WM2UClientsEntry OBJECT-TYPE
    SYNTAX UnisDot11WM2UClientsEntry
    MAX-ACCESS not-accessible
    STATUS current
    DESCRIPTION
        "Each entry contains information about a client."
    INDEX { unisDot11WM2UClientMacAddress }
    ::= { unisDot11WM2UClientsTable 1 }

UnisDot11WM2UClientsEntry ::= SEQUENCE {
        unisDot11WM2UClientMacAddress                    MacAddress,
        unisDot11WM2UDuration                            TimeTicks,
        unisDot11WM2UGroupNum4                           Unsigned32,
        unisDot11WM2UGroupNum6                           Unsigned32
     }

unisDot11WM2UClientMacAddress OBJECT-TYPE
    SYNTAX MacAddress
    MAX-ACCESS not-accessible
    STATUS current
    DESCRIPTION
        "Client MAC address."
    ::= { unisDot11WM2UClientsEntry 1 }

unisDot11WM2UDuration OBJECT-TYPE
    SYNTAX TimeTicks
    MAX-ACCESS read-only
    STATUS current
    DESCRIPTION
        "The amount of time that has elapsed since the client was discovered."
    ::= { unisDot11WM2UClientsEntry 2 }

unisDot11WM2UGroupNum4 OBJECT-TYPE
    SYNTAX Unsigned32
    MAX-ACCESS read-only
    STATUS current
    DESCRIPTION
        "The number of IGMP multicast groups that the client has joined."
    ::= { unisDot11WM2UClientsEntry 3 }

unisDot11WM2UGroupNum6 OBJECT-TYPE
    SYNTAX Unsigned32
    MAX-ACCESS read-only
    STATUS current
    DESCRIPTION
        "The number of MLD multicast groups that the client has joined."
    ::= { unisDot11WM2UClientsEntry 4 }

unisDot11WM2UGroupsTable OBJECT-TYPE
    SYNTAX SEQUENCE OF UnisDot11WM2UGroupsEntry
    MAX-ACCESS not-accessible
    STATUS current
    DESCRIPTION
        "The table contains WM2U group information."
    ::= { unisDot11WM2UDataGroup 2 }

unisDot11WM2UGroupsEntry OBJECT-TYPE
    SYNTAX UnisDot11WM2UGroupsEntry
    MAX-ACCESS not-accessible
    STATUS current
    DESCRIPTION
        "Each entry contains information about each group."
    INDEX { unisDot11WM2UGrpMacAddress, unisDot11WM2UGrpAddressType, unisDot11WM2UAddress }
    ::= { unisDot11WM2UGroupsTable 1 }

UnisDot11WM2UGroupsEntry ::= SEQUENCE {
        unisDot11WM2UGrpMacAddress                       MacAddress,
        unisDot11WM2UGrpAddressType                      InetAddressType,
        unisDot11WM2UAddress                             InetAddress,
        unisDot11WM2UVersion                             UnisDot11WM2UGroupVersion,
        unisDot11WM2UMode                                UnisDot11WM2UGroupMode,
        unisDot11WM2USourceNum                           Unsigned32,
        unisDot11WM2UGrpDurLastRefTime                   TimeTicks
     }

unisDot11WM2UGrpMacAddress OBJECT-TYPE
    SYNTAX MacAddress
    MAX-ACCESS not-accessible
    STATUS current
    DESCRIPTION
        "Client MAC address."
    ::= { unisDot11WM2UGroupsEntry 1 }

unisDot11WM2UGrpAddressType OBJECT-TYPE
    SYNTAX InetAddressType
    MAX-ACCESS not-accessible
    STATUS current
    DESCRIPTION
        "Represents the address type."
    ::= { unisDot11WM2UGroupsEntry 2 }

unisDot11WM2UAddress OBJECT-TYPE
    SYNTAX InetAddress
    MAX-ACCESS not-accessible
    STATUS current
    DESCRIPTION
        "Multicast group address."
    ::= { unisDot11WM2UGroupsEntry 3 }

unisDot11WM2UVersion OBJECT-TYPE
    SYNTAX UnisDot11WM2UGroupVersion
    MAX-ACCESS read-only
    STATUS current
    DESCRIPTION
        "The version of the group."
    ::= { unisDot11WM2UGroupsEntry 4 }

unisDot11WM2UMode OBJECT-TYPE
    SYNTAX UnisDot11WM2UGroupMode
    MAX-ACCESS read-only
    STATUS current
    DESCRIPTION
        "The source filtering mode of the group."
    ::= { unisDot11WM2UGroupsEntry 5 }

unisDot11WM2USourceNum OBJECT-TYPE
    SYNTAX Unsigned32
    MAX-ACCESS read-only
    STATUS current
    DESCRIPTION
        "The number of multicast sources."
    ::= { unisDot11WM2UGroupsEntry 6 }

unisDot11WM2UGrpDurLastRefTime OBJECT-TYPE
    SYNTAX TimeTicks
    MAX-ACCESS read-only
    STATUS current
    DESCRIPTION
        "The amount of time that has elapsed since the multicast group
        entry was created."
    ::= { unisDot11WM2UGroupsEntry 7 }

unisDot11WM2USourcesTable OBJECT-TYPE
    SYNTAX SEQUENCE OF UnisDot11WM2USourcesEntry
    MAX-ACCESS not-accessible
    STATUS current
    DESCRIPTION
        "The table contains WM2U source information."
    ::= { unisDot11WM2UDataGroup 3 }

unisDot11WM2USourcesEntry OBJECT-TYPE
    SYNTAX UnisDot11WM2USourcesEntry
    MAX-ACCESS not-accessible
    STATUS current
    DESCRIPTION
        "Each entry contains information about a multicast source."
    INDEX { unisDot11WM2USrcMacAddress, unisDot11WM2USrcAddressType, unisDot11WM2UGroupAddress, unisDot11WM2USourceAddress }
    ::= { unisDot11WM2USourcesTable 1 }

UnisDot11WM2USourcesEntry ::= SEQUENCE {
        unisDot11WM2USrcMacAddress                       MacAddress,
        unisDot11WM2USrcAddressType                      InetAddressType,
        unisDot11WM2UGroupAddress                        InetAddress,
        unisDot11WM2USourceAddress                       InetAddress,
        unisDot11WM2USrcDurLastRefTime                   TimeTicks
     }

unisDot11WM2USrcMacAddress OBJECT-TYPE
    SYNTAX MacAddress
    MAX-ACCESS not-accessible
    STATUS current
    DESCRIPTION
        "Client MAC address."
    ::= { unisDot11WM2USourcesEntry 1 }

unisDot11WM2USrcAddressType OBJECT-TYPE
    SYNTAX InetAddressType
    MAX-ACCESS not-accessible
    STATUS current
    DESCRIPTION
        "Represents the address type."
    ::= { unisDot11WM2USourcesEntry 2 }

unisDot11WM2UGroupAddress OBJECT-TYPE
    SYNTAX InetAddress
    MAX-ACCESS not-accessible
    STATUS current
    DESCRIPTION
        "Multicast group address."
    ::= { unisDot11WM2USourcesEntry 3 }

unisDot11WM2USourceAddress OBJECT-TYPE
    SYNTAX InetAddress
    MAX-ACCESS not-accessible
    STATUS current
    DESCRIPTION
        "Source address."
    ::= { unisDot11WM2USourcesEntry 4 }

unisDot11WM2USrcDurLastRefTime OBJECT-TYPE
    SYNTAX TimeTicks
    MAX-ACCESS read-only
    STATUS current
    DESCRIPTION
        "The amount of time that has elapsed since the source was added
        to the multicast group."
    ::= { unisDot11WM2USourcesEntry 5 }

END
