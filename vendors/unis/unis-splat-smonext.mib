-- ==================================================================
-- Copyright (c) 2020 Unisyue Technologies Co., Ltd.  All rights reserved.
-- 
-- Description: Rmon alarm Information MIB
-- Reference:
-- Version: V1.1
-- History:
--(1) Created by Qizhenglin, 2002.8.15
-- V1.1 2004-10-12 updated by gaolong
--      Change MAX-ACCESS to ACCESS.
--      Change current to mandatory.
-- ==================================================================

-- ==================================================================
-- 
-- Varibles and types be imported
--
-- ==================================================================

UNIS-LswSMON-MIB DEFINITIONS ::= BEGIN

              IMPORTS
                  OBJECT-TYPE
                      FROM RFC-1212
                  unisRhw
                      FROM UNIS-OID-MIB;

-- ==================================================================
--
-- ======================= definition begin =========================
--
-- ==================================================================

unisSmonExtend         OBJECT IDENTIFIER ::= { unisRhw 26 }

unissmonExtendObject        OBJECT IDENTIFIER ::= { unisSmonExtend 1 }

 
unisdot1qVlanStatNumber OBJECT-TYPE
     SYNTAX  INTEGER
     ACCESS  read-only
     STATUS  mandatory
     DESCRIPTION
         "The number of vlans that can collect statistics of packets."
     ::= { unissmonExtendObject 1 }
     
-- ==================================================================
--
-- VLAN statistics status table (for SMON)
--
-- ==================================================================
 unisdot1qVlanStatStatusTable OBJECT-TYPE
     SYNTAX     SEQUENCE OF Unisdot1qVlanStatStatusEntry
     ACCESS     not-accessible
     STATUS     mandatory
     DESCRIPTION
         "VLAN statistics status table."
     ::= { unissmonExtendObject 2 }

 unisdot1qVlanStatStatusEntry OBJECT-TYPE
     SYNTAX     Unisdot1qVlanStatStatusEntry
     ACCESS	not-accessible
     STATUS     mandatory
     DESCRIPTION
         " VLAN statistics status table entry."
     INDEX { unisdot1qVlanStatEnableIndex }
     ::= { unisdot1qVlanStatStatusTable 1 }

      
    Unisdot1qVlanStatStatusEntry ::= SEQUENCE {
        unisdot1qVlanStatEnableIndex                INTEGER,
        unisdot1qVlanStatEnableStatus               INTEGER
    }
        
        
    unisdot1qVlanStatEnableIndex  OBJECT-TYPE
        SYNTAX     INTEGER
        ACCESS 	    read-only
        STATUS      mandatory
        DESCRIPTION
        "Vlan index ."
        ::= { unisdot1qVlanStatStatusEntry 1 }  
        
    unisdot1qVlanStatEnableStatus  OBJECT-TYPE
        SYNTAX     INTEGER
        {
            enabled(1),
            disabled(2)
        }
        ACCESS read-write
        STATUS      mandatory
        DESCRIPTION
        "VLAN Statistics Status.It represent the current VLAN supports statistic or not."
        ::= { unisdot1qVlanStatStatusEntry 2 } 

   END
