-- ============================================================================
-- Copyright (c) 2020 Unisyue Technologies Co., Ltd.  All rights reserved.
--
-- Description:
-- Reference:
-- Version: V3.4
-- History:
-- V1.0 created by yuhui.
-- V2.0 2004-10-12 updated by gaolong
--     Define MODULE-IDENTITY for unisAcl
--     Remove chinese characters
--     Add limitation(0..65535) for some table index
--     Fix a default value error of unisAclAdvancedEstablish
-- V2.1 2004-11-18 updated by yubo
--     Add 'unisAclIDSTable' for IDS
-- V2.2 2004-12-13
--     Fix syntax bugs and adjust format of the whole file by jinyi
--     Modify description of unisAclAdvancedDscp by zhuangyu
-- V2.3 2005-1-26 updated by WuZhao02557
--     Change MAX-ACCESS from read-create to not-accessible for the
--     following MIB nodes:
--       unisAclNumGroupAclNum, unisAclNameGroupIndex, unisAclBasicAclNum,
--       unisAclBasicSubitem, unisAclAdvancedAclNum, unisAclAdvancedSubitem
--       unisAclIfAclNum, unisAclIfSubitem, unisAclLinkAclNum, unisAclLinkSubitem
--       unisAclUserAclNum, unisAclUserSubitem, unisAclActiveAclIndex,
--       unisAclActiveIfIndex, unisAclActiveVlanID, unisAclActiveDirection
--     Adjust format of whole file.
--     2005-01-27   updated by zhangyinxi
--     1. Add objects unisAclLinkL2LabelRangeOp, unisAclLinkL2LabelRangeBegin
--        unisAclLinkL2LabelRangeEnd and unisAclLinkMplsExp in unisAclLinkTable
--     2. Add an enumeration mpls(34887) to object unisAclLinkProtocol
--     3. Expand the range of object unisAclActiveVlanID to Integer32
-- V2.4 2005-2-24
--     Make the index of unisAclIDSTable IMPLIED by fuzhenyu because IDS devices
--     require fixed length index to be used. IDS devices only provide index
--     with no sub-identifier indicating the length of the string.
--     Modify enum name(value is 4) of unisAclLinkFormatType to ieee802Dot3 by daishijun
-- V2.5 2005-7-25
--     Add objects unisAclMib2Mode, unisAclVersion, unisAclMib2ObjectsCapabilities,
--      unisAclIPAclNumGroupTable, unisAclIPAclBasicTable, unisAclIPAclAdvancedTable,
--      unisAclMACTable, unisAclEnUserTable by tangshun.
-- V2.6 2006-01-03
--     Add objects unisAclIPAclBasicComment, unisAclIPAclAdvancedComment,
--      unisAclMACComment, unisAclEnUserComment by tangshun.
-- V2.7 2006-03-09 updated by changhuifeng
--     Add object unisAclIPAclAdvancedReflective in unisAclIPAclAdvancedTable.
--     Modify the description of object unisAclIPAclAdvancedFragmentFlag.
--     Modify the description of object unisAclMib2Version.
--     Modify the description of object unisAclLinkDestAny for text error.
--     Modify the description of object unisAclMib2CharacteristicsValue.
-- V2.8 2006-07-06 updated by xialei
--     Modify the description of unisAclIPAclAdvancedIcmpType
--     and unisAclIPAclAdvancedIcmpCode.
--     Change value range of unisAclIPAclAdvancedIcmpCode.
-- V2.9 2006-08-08 updated by chenzhaojie
--     Add enumeration value to unisAclActiveDirection.
-- V3.0 2010-09-01 updated by zhaixiaoxiang
--     Add unisAclResourceUsageTable.
-- V3.1 2012-02-06 updated by wangchenxiao
--     Add unisPacketfilterTrapObjects
--     Add unisPacketfilterTrap
--     2012-02-14 updated by mouxuanli
--     Add unisAclMib2ProcessingStatus of object unisAclMib2NodesGroup
--     Add unisAclNumberGroupName of object unisAclNumberGroupTable
--     Add unisAclIPAclBasicCounting of object unisAclIPAclBasicTable
--     Add unisAclIPAclBasicRouteTypeAny of object unisAclIPAclBasicTable
--     Add unisAclIPAclBasicRouteTypeValue of object unisAclIPAclBasicTable
--     Add unisAclIPAclAdvancedCounting of object unisAclIPAclAdvancedTable
--     Add unisAclIPAclAdvancedTCPFlagMask of object unisAclIPAclAdvancedTable
--     Add unisAclIPAclAdvancedTCPFlagValue of object unisAclIPAclAdvancedTable
--     Add unisAclIPAclAdvancedRouteTypeAny of object unisAclIPAclAdvancedTable
--     Add unisAclIPAclAdvancedRouteTypeValue of object unisAclIPAclAdvancedTable
--     Add unisAclIPAclAdvancedFlowLabel of object unisAclIPAclAdvancedTable
--     Add unisAclMACLog of object unisAclMACTable
--     Add unisAclMACCounting of object unisAclMACTable
--     Add unisAclEnUserLog of object unisAclEnUserTable
--     Add unisAclEnUserCounting of object unisAclEnUserTable
--     Modify the description of unisAclResourceType
--     Add unisAclResourceTypeDescription of object unisAclResourceUsageTable
--     Add unisAclPacketFilterObjects
-- V3.2 2012-11-30 updated by gaoyu
--     Add unisPfilterRunApplyObjType of object unisPfilterAclGroupRunInfoTable
--     Add unisPfilterRunApplyObjIndex of object unisPfilterAclGroupRunInfoTable
--     Add unisPfilterRunApplyDirection of object unisPfilterAclGroupRunInfoTable
--     Add unisPfilterRunApplyAclType of object unisPfilterAclGroupRunInfoTable
--     Add unisPfilterRunApplyAclIndex of object unisPfilterAclGroupRunInfoTable
--     modify the unisPfilterRunApplyObjType of object unisPfilterAclRuleRunInfoTable
--     modify the unisPfilterRunApplyObjIndex of object unisPfilterAclRuleRunInfoTable
--     modify the unisPfilterRunApplyDirection of object unisPfilterAclRuleRunInfoTable
--     modify the unisPfilterRunApplyAclType of object unisPfilterAclRuleRunInfoTable
--     modify the unisPfilterRunApplyAclIndex of object unisPfilterAclRuleRunInfoTable
-- V3.3 2013-11-30 updated by gaoyu
--     Add unisAclNamedGroupTable to object unisAclMib2GlobalGroup
--     Add unisAclIPAclNamedBscTable to object unisAclIPAclGroup
--     Add unisAclIPAclNamedAdvTable to object unisAclIPAclGroup
--     Add unisAclNamedMACTable to object unisAclMACAclGroup
--     Add unisAclIntervalGroup to object unisAclMib2Objects
--     Modify unisPfilterApplyAclType of object unisPfilterApplyTable
--     Modify unisPfilterRunApplyAclType of object unisPfilterAclGroupRunInfoTable
--     Modify unisPfilterSumAclType of object unisPfilterStatisticSumTable
--     Add unisPfilter2ApplyTable to object unisAclPacketFilterObjects
--     Add unisPfilter2AclGroupRunInfoTable to object unisAclPacketFilterObjects
--     Add unisPfilter2AclRuleRunInfoTable to object unisAclPacketFilterObjects
--     Add unisPfilter2StatisticSumTable to object unisAclPacketFilterObjects
--     Add unisAclPacketIfName to object unisAclPacketfilterTrapObjects
--     Add unisAclPacketDirection  to object unisAclPacketfilterTrapObjects
--     Add unisAclPacketBAGG to object unisAclPacketfilterTrapObjects
--     Add unisAclPacketVlanID to object unisAclPacketfilterTrapObjects
--     Add unisAclPacketSrcIP to object unisAclPacketfilterTrapObjects
--     Add unisAclPacketDstIP to object unisAclPacketfilterTrapObjects
--     Add unisAclPacketProtocol to object unisAclPacketfilterTrapObjects
--     Add unisAclPacketDscp to object unisAclPacketfilterTrapObjects
--     Add unisAclPacketFlowLabel to object unisAclPacketfilterTrapObjects
--     Add unisAclPacketIcmpIgmpType to object unisAclPacketfilterTrapObjects
--     Add unisAclPacketIcmpIgmpCode to object unisAclPacketfilterTrapObjects
--     Add unisAclPacketTcpFlags to object unisAclPacketfilterTrapObjects
--     Add unisAclPacketSrcPort to object unisAclPacketfilterTrapObjects
--     Add unisAclPacketDstPort to object unisAclPacketfilterTrapObjects
--     Add unisAclPacketSrcMacAddr to object unisAclPacketfilterTrapObjects
--     Add unisAclPacketDstMacAddr to object unisAclPacketfilterTrapObjects
--     Add unisAclPacketMacTypeLen to object unisAclPacketfilterTrapObjects
--     Add unisAclPacketVlanPCP to object unisAclPacketfilterTrapObjects
--     Add unisAclRuleMatchCount to object unisPfilterTrapPrefix
--     Add unisAclFirstIPv4PktCaptured to object unisPfilterTrapPrefix
--     Add unisAclFirstIPv6PktCaptured to object unisPfilterTrapPrefix
--     Add unisAclFirstEthernetPktCaptured to object unisPfilterTrapPrefix
--     2014-2-20 updated by gaoyu
--     Add unisAclNamedUserTable to object unisAclEnUserAclGroup
--     2014-07-08 updated by gaoyu
--     Add unisAclIPAclAdvancedSrcSuffix to object unisAclIPAclAdvancedTable
--     Add unisAclIPAclAdvancedDestSuffix to object unisAclIPAclAdvancedTable
--     Add unisAclIPAclNamedAdvSrcSuffix to object unisAclIPAclNamedAdvTable
--     Add unisAclIPAclNamedAdvDstSuffix to object unisAclIPAclNamedAdvTable
-- V3.4 2014-10-20 updated by gaoyu
--     Add unisAclMib2ResourceThreshold to object unisAclMib2NodesGroup
--     Add unisAclMib2ResourceLogInterval to object unisAclMib2NodesGroup
--     Add unisAclResourceTypeName to object unisAclTrapObjects
--     Add unisAclResourceUsage to object unisAclTrapObjects
--     Add unisAclResourceUsedEntries to object unisAclTrapObjects
--     Add unisAclResourceTotalEntries to object unisAclTrapObjects
--     Add unisAclResourceChassisID to object unisAclTrapObjects
--     Add unisAclResourceSlotID to object unisAclTrapObjects
--     Add unisAclResourceTrap to object unisAclTrapPrefix
-- ============================================================================
UNIS-ACL-MIB DEFINITIONS ::= BEGIN

        IMPORTS
            unisCommon
                FROM  UNIS-OID-MIB
            IpAddress, Integer32, Counter32, OBJECT-TYPE, MODULE-IDENTITY,
            NOTIFICATION-TYPE, Unsigned32, Counter64
                FROM SNMPv2-SMI
            InetAddressType, InetAddress, InetAddressPrefixLength
                FROM INET-ADDRESS-MIB
            RowStatus, TruthValue, MacAddress, TEXTUAL-CONVENTION
                FROM SNMPv2-TC;

--
-- Node definitions
--

        unisAcl MODULE-IDENTITY
            LAST-UPDATED "201410201000Z"        -- Oct 20, 2014 at 10:00 GMT
            ORGANIZATION
                "Unisyue Technologies Co., Ltd."
            CONTACT-INFO
                ""
            DESCRIPTION
                "ACL management information base for managing devices
                that support access control list and packet filtering.
                "
            REVISION "201410201000Z"            -- Oct 22, 2014 at 10:00 GMT
            DESCRIPTION
                "Added 2 ndoes to configure TCAM function and 6 nodes to show trap info."
            ::= { unisCommon 8 }

-- Rule action value
        RuleAction ::= TEXTUAL-CONVENTION
            STATUS current
            DESCRIPTION
                "The value of rule's action.
                 permit: The packet matching the rule will be permitted to forward.
                 deny: The packet matching the rule will be denied.
                "
            SYNTAX INTEGER
            {
                invalid(1),
                permit(2),
                deny(3)
            }

-- CounterClear value
        CounterClear ::= TEXTUAL-CONVENTION
            STATUS  current
            DESCRIPTION
                "cleared: Reset the value of the rule's counter.
                 nouse: 'nouse' will be returned when getting.
                "
            SYNTAX INTEGER
            {
                cleared(1),
                nouse(2)
            }

-- PortOp value
        PortOp ::= TEXTUAL-CONVENTION
            STATUS current
            DESCRIPTION
                "The operation type of TCP and UDP.
                 lt : Less than given port number.
                 eq : Equal to given port number.
                 gt : Greater than given port number.
                 neq : Not equal to given port number.
                 range : Between two port numbers.
                 Default value is 'invalid'.
                "
            SYNTAX INTEGER
            {
                invalid(0),
                lt(1),
                eq(2),
                gt(3),
                neq(4),
                range(5)
            }

-- DSCP value
        DSCPValue ::= TEXTUAL-CONVENTION
            DISPLAY-HINT "d"
            STATUS current
            DESCRIPTION
                "The value of DSCP.
                 <0-63>  Value of DSCP
                 af11    Specify Assured Forwarding 11 service(10)
                 af12    Specify Assured Forwarding 12 service(12)
                 af13    Specify Assured Forwarding 13 service(14)
                 af21    Specify Assured Forwarding 21 service(18)
                 af22    Specify Assured Forwarding 22 service(20)
                 af23    Specify Assured Forwarding 23 service(22)
                 af31    Specify Assured Forwarding 31 service(26)
                 af32    Specify Assured Forwarding 32 service(28)
                 af33    Specify Assured Forwarding 33 service(30)
                 af41    Specify Assured Forwarding 41 service(34)
                 af42    Specify Assured Forwarding 42 service(36)
                 af43    Specify Assured Forwarding 43 service(38)
                 be      Specify Best Effort service(0)
                 cs1     Specify Class Selector 1 service(8)
                 cs2     Specify Class Selector 2 service(16)
                 cs3     Specify Class Selector 3 service(24)
                 cs4     Specify Class Selector 4 service(32)
                 cs5     Specify Class Selector 5 service(40)
                 cs6     Specify Class Selector 6 service(48)
                 cs7     Specify Class Selector 7 service(56)
                 ef      Specify Expedited Forwarding service(46)
                "
            SYNTAX Integer32 (0..63|255)

-- TCP Flags
        TCPFlag ::= TEXTUAL-CONVENTION
            STATUS current
            DESCRIPTION
                "Type of TCP.
                 invalid(0)
                 tcpack(1)  TCP protocol ACK Packet
                 tcpfin(2)  TCP protocol PIN Packet
                 tcppsh(3)  TCP protocol PUSH Packet
                 tcprst(4)  TCP protocol RST Packet
                 tcpsyn(5)  TCP protocol SYN Packet
                 tcpurg(6)  TCP protocol URG Packet
                 Default value is 'invalid'.
                "
            SYNTAX INTEGER
            {
                invalid(0),
                tcpack(1),
                tcpfin(2),
                tcppsh(3),
                tcprst(4),
                tcpsyn(5),
                tcpurg(6)
            }

-- Fragment Flags
        FragmentFlag ::= TEXTUAL-CONVENTION
            STATUS current
            DESCRIPTION
                "Type of fragment.
                 invalid(0)
                 fragment(1)       Frag-Type Fragment
                 fragmentSubseq(2) Frag-Type Fragment-subsequent
                 nonFragment(3)    Frag-Type non-Fragment
                 nonSubseq(4)      Frag-Type non-subsequent
                 Default value is 'invalid'.
                "
            SYNTAX INTEGER
            {
                invalid(0),
                fragment(1),
                fragmentSubseq(2),
                nonFragment(3),
                nonSubseq(4)
            }

-- Address Flags
        AddressFlag ::= TEXTUAL-CONVENTION
            STATUS current
            DESCRIPTION
                "Address flag to select IPv6 Address.
                 Default value is 'invalid'.

                 t64SrcAddrPre64DestAddrPre(1):
                 The mean of the enumeration 't64SrcAddrPre64DestAddrPre' is
                 that system gets the 64 bits prefix of source address and
                 the 64 bits prefix of destination address.

                 t64SrcAddrPre64DestAddrSuf(2):
                 The mean of the enumeration 't64SrcAddrPre64DestAddrSuf' is
                 that system gets the 64 bits prefix of source address and
                 the 64 bits suffix of destination address.

                 t64SrcAddrSuf64DestAddrPre(3):
                 The mean of the enumeration 't64SrcAddrSuf64DestAddrPre' is
                 that system gets the 64 bits suffix of source address and
                 the 64 bits prefix of destination address.

                 t64SrcAddrSuf64DestAddrSuf(4):
                 The mean of the enumeration 't64SrcAddrSuf64DestAddrSuf' is
                 that system gets the 64 bits suffix of source address and
                 the 64 bits suffix of destination address.

                 t128SourceAddress(5):
                 The mean of the enumeration 't128SourceAddress' is that
                 system gets the 128 bits of source address.

                 t128DestinationAddress(6):
                 The mean of the enumeration 't128SourceAddress' is that
                 system gets the 128 bits of destination address.
                "
            SYNTAX INTEGER
            {
                invalid(0),
                t64SrcAddrPre64DestAddrPre(1),
                t64SrcAddrPre64DestAddrSuf(2),
                t64SrcAddrSuf64DestAddrPre(3),
                t64SrcAddrSuf64DestAddrSuf(4),
                t128SourceAddress(5),
                t128DestinationAddress(6)
            }

-- Direction type
        DirectionType ::= TEXTUAL-CONVENTION
            STATUS  current
            DESCRIPTION
                "The direction: inbound or outbound."
            SYNTAX INTEGER
            {
                inbound(1),
                outbound(2)
            }

--
-- nodes defined
--
        unisAclMibObjects OBJECT IDENTIFIER ::= { unisAcl 1 }

        unisAclMode OBJECT-TYPE
            SYNTAX INTEGER
            {
                linkBased(1),
                ipBased(2)
            }
            MAX-ACCESS read-write
            STATUS current
            DESCRIPTION
                "Access-list mode."
            DEFVAL { ipBased }
            ::= { unisAclMibObjects 1 }

--
-- Node of unisAclNumGroupTable
--
        unisAclNumGroupTable OBJECT-TYPE
            SYNTAX SEQUENCE OF UnisAclNumGroupEntry
            MAX-ACCESS not-accessible
            STATUS current
            DESCRIPTION
                "Configure the match-order of number-acl group."
            ::= { unisAclMibObjects 2 }

        unisAclNumGroupEntry OBJECT-TYPE
            SYNTAX UnisAclNumGroupEntry
            MAX-ACCESS not-accessible
            STATUS current
            DESCRIPTION
                "Define the index of unisAclNumGroupTable."
            INDEX { unisAclNumGroupAclNum }
            ::= { unisAclNumGroupTable 1 }

        UnisAclNumGroupEntry ::=
            SEQUENCE
            {
                unisAclNumGroupAclNum
                    Integer32,
                unisAclNumGroupMatchOrder
                    INTEGER,
                unisAclNumGroupSubitemNum
                    Integer32,
                unisAclNumGroupDescription
                    OCTET STRING,
                unisAclNumGroupCountClear
                    INTEGER,
                unisAclNumGroupRowStatus
                    RowStatus
             }

        unisAclNumGroupAclNum OBJECT-TYPE
            SYNTAX Integer32 (1000..5999)
            MAX-ACCESS not-accessible
            STATUS current
            DESCRIPTION
                "The index of number-acl group
                 Interface type:1000..1999
                 Basic type:2000..2999
                 Advance type:3000..3999
                 Link type:4000..4999
                 User type:5000..5999"
            ::= { unisAclNumGroupEntry 1 }

        unisAclNumGroupMatchOrder OBJECT-TYPE
            SYNTAX INTEGER
            {
                config(1),
                auto(2)
            }
            MAX-ACCESS read-create
            STATUS current
            DESCRIPTION
                "The match-order of number-acl group."
            DEFVAL { config }
            ::= { unisAclNumGroupEntry 2 }

        unisAclNumGroupSubitemNum OBJECT-TYPE
            SYNTAX Integer32
            MAX-ACCESS read-only
            STATUS current
            DESCRIPTION
                "The number of number-acl group's node."
            ::= { unisAclNumGroupEntry 3 }

        unisAclNumGroupDescription OBJECT-TYPE
            SYNTAX OCTET STRING (SIZE(0..127))
            MAX-ACCESS read-write
            STATUS current
            DESCRIPTION
                "The description of this acl group."
            ::= { unisAclNumGroupEntry 4 }

        unisAclNumGroupCountClear OBJECT-TYPE
            SYNTAX INTEGER
            {
                cleared(1),
                nouse(2)
            }
            MAX-ACCESS read-create
            STATUS current
            DESCRIPTION
                "Reset the value of rules' counter, which belong to this group."
            ::= { unisAclNumGroupEntry 5 }

        unisAclNumGroupRowStatus OBJECT-TYPE
            SYNTAX RowStatus
            MAX-ACCESS read-create
            STATUS current
            DESCRIPTION
                "RowStatus, now support three state: CreateAndGo, Active, Destroy."
            ::= { unisAclNumGroupEntry 6 }

--
-- Node of unisAclNameGroupTable
--
        unisAclNameGroupTable OBJECT-TYPE
            SYNTAX SEQUENCE OF UnisAclNameGroupEntry
            MAX-ACCESS not-accessible
            STATUS current
            DESCRIPTION
                "Create acl-group that identified by name."
            ::= { unisAclMibObjects 3 }

        unisAclNameGroupEntry OBJECT-TYPE
            SYNTAX UnisAclNameGroupEntry
            MAX-ACCESS not-accessible
            STATUS current
            DESCRIPTION
                "Define the index of unisAclNameGroupTable."
            INDEX { unisAclNameGroupIndex }
            ::= { unisAclNameGroupTable 1 }

        UnisAclNameGroupEntry ::=
            SEQUENCE {
                unisAclNameGroupIndex
                    Integer32,
                unisAclNameGroupCreateName
                    OCTET STRING,
                unisAclNameGroupTypes
                    INTEGER,
                unisAclNameGroupMatchOrder
                    INTEGER,
                unisAclNameGroupSubitemNum
                    Integer32,
                unisAclNameGroupRowStatus
                    RowStatus
             }

        unisAclNameGroupIndex OBJECT-TYPE
            SYNTAX Integer32 (10000..12999)
            MAX-ACCESS not-accessible
            STATUS current
            DESCRIPTION
                "The index of name-acl group."
            ::= { unisAclNameGroupEntry 1 }

        unisAclNameGroupCreateName OBJECT-TYPE
            SYNTAX OCTET STRING (SIZE (0..32))
            MAX-ACCESS read-create
            STATUS current
            DESCRIPTION
                "The name of name-acl group."
            ::= { unisAclNameGroupEntry 2 }

        unisAclNameGroupTypes OBJECT-TYPE
            SYNTAX INTEGER
            {
                basic(1),
                advanced(2),
                ifBased(3),
                link(4),
                user(5)
            }
            MAX-ACCESS read-create
            STATUS current
            DESCRIPTION
                "The type of name-acl group."
            ::= { unisAclNameGroupEntry 3 }

        unisAclNameGroupMatchOrder OBJECT-TYPE
            SYNTAX INTEGER
            {
                config(1),
                auto(2)
            }
            MAX-ACCESS read-create
            STATUS current
            DESCRIPTION
                "The match-order of name-acl group."
            DEFVAL { config }
            ::= { unisAclNameGroupEntry 4 }

        unisAclNameGroupSubitemNum OBJECT-TYPE
            SYNTAX Integer32 (0..128)
            MAX-ACCESS read-only
            STATUS current
            DESCRIPTION
                "The number of name-acl group's node."
            ::= { unisAclNameGroupEntry 5 }

        unisAclNameGroupRowStatus OBJECT-TYPE
            SYNTAX RowStatus
            MAX-ACCESS read-create
            STATUS current
            DESCRIPTION
                "RowStatus, now support three state: CreateAndGo, Active, Destroy."
            ::= { unisAclNameGroupEntry 6 }

--
-- unisAclBasicRuleTable
--
        unisAclBasicRuleTable OBJECT-TYPE
            SYNTAX SEQUENCE OF UnisAclBasicRuleEntry
            MAX-ACCESS not-accessible
            STATUS current
            DESCRIPTION
                "Configure the rule for basic acl group."
            ::= { unisAclMibObjects 4 }

        unisAclBasicRuleEntry OBJECT-TYPE
            SYNTAX UnisAclBasicRuleEntry
            MAX-ACCESS not-accessible
            STATUS current
            DESCRIPTION
                "Define the index of unisAclBasicRuleTable."
            INDEX { unisAclBasicAclNum, unisAclBasicSubitem }
            ::= { unisAclBasicRuleTable 1 }

        UnisAclBasicRuleEntry ::=
            SEQUENCE {
                unisAclBasicAclNum
                    Integer32,
                unisAclBasicSubitem
                    Integer32,
                unisAclBasicAct
                    INTEGER,
                unisAclBasicSrcIp
                    IpAddress,
                unisAclBasicSrcWild
                    IpAddress,
                unisAclBasicTimeRangeName
                    OCTET STRING,
                unisAclBasicFragments
                    TruthValue,
                unisAclBasicLog
                    TruthValue,
                unisAclBasicEnable
                    TruthValue,
                unisAclBasicCount
                    Counter32,
                unisAclBasicCountClear
                    INTEGER,
                unisAclBasicRowStatus
                    RowStatus
             }

        unisAclBasicAclNum OBJECT-TYPE
            SYNTAX Integer32 (0|2000..2999|10000..12999)
            MAX-ACCESS not-accessible
            STATUS current
            DESCRIPTION
                "The index of basic acl group."
            ::= { unisAclBasicRuleEntry 1 }

        unisAclBasicSubitem OBJECT-TYPE
            SYNTAX Integer32 (0..65535)
            MAX-ACCESS not-accessible
            STATUS current
            DESCRIPTION
                "The subindex of basic acl group."
            ::= { unisAclBasicRuleEntry 2 }

        unisAclBasicAct OBJECT-TYPE
            SYNTAX INTEGER
            {
                permit(1),
                deny(2)
            }
            MAX-ACCESS read-create
            STATUS current
            DESCRIPTION
                "The action of basic acl rule."
            ::= { unisAclBasicRuleEntry 3 }

        unisAclBasicSrcIp OBJECT-TYPE
            SYNTAX IpAddress
            MAX-ACCESS read-create
            STATUS current
            DESCRIPTION
                "Source IP-address of basic acl rule."
            ::= { unisAclBasicRuleEntry 4 }

        unisAclBasicSrcWild OBJECT-TYPE
            SYNTAX IpAddress
            MAX-ACCESS read-create
            STATUS current
            DESCRIPTION
                "Source IP-address wild of basic acl rule."
            ::= { unisAclBasicRuleEntry 5 }

        unisAclBasicTimeRangeName OBJECT-TYPE
            SYNTAX OCTET STRING (SIZE (0..32))
            MAX-ACCESS read-create
            STATUS current
            DESCRIPTION
                "The Time-range of basic acl rule."
            ::= { unisAclBasicRuleEntry 6 }

        unisAclBasicFragments OBJECT-TYPE
            SYNTAX TruthValue
            MAX-ACCESS read-create
            STATUS current
            DESCRIPTION
                "The flag of matching fragmented packet."
            ::= { unisAclBasicRuleEntry 7 }

        unisAclBasicLog OBJECT-TYPE
            SYNTAX TruthValue
            MAX-ACCESS read-create
            STATUS current
            DESCRIPTION
                "The flag of log."
            ::= { unisAclBasicRuleEntry 8 }

        unisAclBasicEnable OBJECT-TYPE
            SYNTAX TruthValue
            MAX-ACCESS read-only
            STATUS current
            DESCRIPTION
                "The rule is active or not.
                 true : active
                 false : inactive
                "
            ::= { unisAclBasicRuleEntry 9 }

        unisAclBasicCount OBJECT-TYPE
            SYNTAX Counter32
            MAX-ACCESS read-only
            STATUS current
            DESCRIPTION
                "The count of matched by basic rule."
            ::= { unisAclBasicRuleEntry 10 }

        unisAclBasicCountClear OBJECT-TYPE
            SYNTAX INTEGER
            {
                cleared(1),
                nouse(2)
            }
            MAX-ACCESS read-create
            STATUS current
            DESCRIPTION
                "Reset the value of counter."
            ::= { unisAclBasicRuleEntry 11 }

        unisAclBasicRowStatus OBJECT-TYPE
            SYNTAX RowStatus
            MAX-ACCESS read-create
            STATUS current
            DESCRIPTION
                "RowStatus, now support three state: CreateAndGo, Active, Destroy."
            ::= { unisAclBasicRuleEntry 12 }

--
-- unisAclAdvancedRuleTable
--
        unisAclAdvancedRuleTable OBJECT-TYPE
            SYNTAX SEQUENCE OF UnisAclAdvancedRuleEntry
            MAX-ACCESS not-accessible
            STATUS current
            DESCRIPTION
                "Configure the rule for advanced acl group."
            ::= { unisAclMibObjects 5 }

        unisAclAdvancedRuleEntry OBJECT-TYPE
            SYNTAX UnisAclAdvancedRuleEntry
            MAX-ACCESS not-accessible
            STATUS current
            DESCRIPTION
                "Define the index of unisAclAdvancedRuleTable."
            INDEX { unisAclAdvancedAclNum, unisAclAdvancedSubitem }
            ::= { unisAclAdvancedRuleTable 1 }

        UnisAclAdvancedRuleEntry ::=
            SEQUENCE {
                unisAclAdvancedAclNum
                    Integer32,
                unisAclAdvancedSubitem
                    Integer32,
                unisAclAdvancedAct
                    INTEGER,
                unisAclAdvancedProtocol
                    Integer32,
                unisAclAdvancedSrcIp
                    IpAddress,
                unisAclAdvancedSrcWild
                    IpAddress,
                unisAclAdvancedSrcOp
                    INTEGER,
                unisAclAdvancedSrcPort1
                    Integer32,
                unisAclAdvancedSrcPort2
                    Integer32,
                unisAclAdvancedDestIp
                    IpAddress,
                unisAclAdvancedDestWild
                    IpAddress,
                unisAclAdvancedDestOp
                    INTEGER,
                unisAclAdvancedDestPort1
                    Integer32,
                unisAclAdvancedDestPort2
                    Integer32,
                unisAclAdvancedPrecedence
                    Integer32,
                unisAclAdvancedTos
                    Integer32,
                unisAclAdvancedDscp
                    Integer32,
                unisAclAdvancedEstablish
                    TruthValue,
                unisAclAdvancedTimeRangeName
                    OCTET STRING,
                unisAclAdvancedIcmpType
                    Integer32,
                unisAclAdvancedIcmpCode
                    Integer32,
                unisAclAdvancedFragments
                    TruthValue,
                unisAclAdvancedLog
                    TruthValue,
                unisAclAdvancedEnable
                    TruthValue,
                unisAclAdvancedCount
                    Counter32,
                unisAclAdvancedCountClear
                    INTEGER,
                unisAclAdvancedRowStatus
                    RowStatus
             }

        unisAclAdvancedAclNum OBJECT-TYPE
            SYNTAX Integer32 (0|3000..3999|10000..12999)
            MAX-ACCESS not-accessible
            STATUS current
            DESCRIPTION
                "The index of advanced acl group."
            ::= { unisAclAdvancedRuleEntry 1 }

        unisAclAdvancedSubitem OBJECT-TYPE
            SYNTAX Integer32 (0..65535)
            MAX-ACCESS not-accessible
            STATUS current
            DESCRIPTION
                "The subindex of advanced acl group."
            ::= { unisAclAdvancedRuleEntry 2 }

        unisAclAdvancedAct OBJECT-TYPE
            SYNTAX INTEGER
            {
                permit(1),
                deny(2)
            }
            MAX-ACCESS read-create
            STATUS current
            DESCRIPTION
                "The action of Advance acl rule."

            ::= { unisAclAdvancedRuleEntry 3 }

        unisAclAdvancedProtocol OBJECT-TYPE
            SYNTAX Integer32 (0..255)
            MAX-ACCESS read-create
            STATUS current
            DESCRIPTION
                "The protocol-type of advanced acl group.
                 <1-255>  Protocol number
                  gre      GRE tunneling(47)
                  icmp     Internet Control Message Protocol(1)
                  igmp     Internet Group Management Protocol(2)
                  ip       Any IP protocol
                  ipinip   IP in IP tunneling(4)
                  ospf     OSPF routing protocol(89)
                  tcp      Transmission Control Protocol (6)
                  udp      User Datagram Protocol (17)"
            ::= { unisAclAdvancedRuleEntry 4 }

        unisAclAdvancedSrcIp OBJECT-TYPE
            SYNTAX IpAddress
            MAX-ACCESS read-create
            STATUS current
            DESCRIPTION
                "Source IP-address of advanced acl group."
            ::= { unisAclAdvancedRuleEntry 5 }

        unisAclAdvancedSrcWild OBJECT-TYPE
            SYNTAX IpAddress
            MAX-ACCESS read-create
            STATUS current
            DESCRIPTION
                "Source IP-address wild of advanced acl group."
            ::= { unisAclAdvancedRuleEntry 6 }

        unisAclAdvancedSrcOp OBJECT-TYPE
            SYNTAX INTEGER
            {
                invalid(0),
                lt(1),
                eq(2),
                gt(3),
                neq(4),
                range(5)
            }
            MAX-ACCESS read-create
            STATUS current
            DESCRIPTION
                "The source IP-address's operator of advanced acl group."
            ::= { unisAclAdvancedRuleEntry 7 }

        unisAclAdvancedSrcPort1 OBJECT-TYPE
            SYNTAX Integer32 (0..65535)
            MAX-ACCESS read-create
            STATUS current
            DESCRIPTION
                "The fourth layer source port1."
            ::= { unisAclAdvancedRuleEntry 8 }

        unisAclAdvancedSrcPort2 OBJECT-TYPE
            SYNTAX Integer32 (0..65535)
            MAX-ACCESS read-create
            STATUS current
            DESCRIPTION
                "The fourth layer source port2."
            ::= { unisAclAdvancedRuleEntry 9 }

        unisAclAdvancedDestIp OBJECT-TYPE
            SYNTAX IpAddress
            MAX-ACCESS read-create
            STATUS current
            DESCRIPTION
                "Destination IP-address of advanced acl group."
            ::= { unisAclAdvancedRuleEntry 10 }

        unisAclAdvancedDestWild OBJECT-TYPE
            SYNTAX IpAddress
            MAX-ACCESS read-create
            STATUS current
            DESCRIPTION
                "Destination IP-address wild of advanced acl group."
            ::= { unisAclAdvancedRuleEntry 11 }

        unisAclAdvancedDestOp OBJECT-TYPE
            SYNTAX INTEGER
            {
                invalid(0),
                lt(1),
                eq(2),
                gt(3),
                neq(4),
                range(5)
            }
            MAX-ACCESS read-create
            STATUS current
            DESCRIPTION
                "The destination IP-address's operator of advanced acl group."
            ::= { unisAclAdvancedRuleEntry 12 }

        unisAclAdvancedDestPort1 OBJECT-TYPE
            SYNTAX Integer32 (0..65535)
            MAX-ACCESS read-create
            STATUS current
            DESCRIPTION
                "The fourth layer destination port1."
            ::= { unisAclAdvancedRuleEntry 13 }

        unisAclAdvancedDestPort2 OBJECT-TYPE
            SYNTAX Integer32 (0..65535)
            MAX-ACCESS read-create
            STATUS current
            DESCRIPTION
                "The fourth layer destination port2."
            ::= { unisAclAdvancedRuleEntry 14 }

        unisAclAdvancedPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7) "
            ::= { unisAclAdvancedRuleEntry 15 }

        unisAclAdvancedTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0) "
            ::= { unisAclAdvancedRuleEntry 16 }

        unisAclAdvancedDscp OBJECT-TYPE
            SYNTAX Integer32 (0..63|255)
            MAX-ACCESS read-create
            STATUS current
            DESCRIPTION
                "The value of DSCP.
                <0-63>  Value of DSCP
                af11    Specify Assured Forwarding 11 service(10)
                af12    Specify Assured Forwarding 12 service(12)
                af13    Specify Assured Forwarding 13 service(14)
                af21    Specify Assured Forwarding 21 service(18)
                af22    Specify Assured Forwarding 22 service(20)
                af23    Specify Assured Forwarding 23 service(22)
                af31    Specify Assured Forwarding 31 service(26)
                af32    Specify Assured Forwarding 32 service(28)
                af33    Specify Assured Forwarding 33 service(30)
                af41    Specify Assured Forwarding 41 service(34)
                af42    Specify Assured Forwarding 42 service(36)
                af43    Specify Assured Forwarding 43 service(38)
                be      Specify Best Effort service(0)
                cs1     Specify Class Selector 1 service(8)
                cs2     Specify Class Selector 2 service(16)
                cs3     Specify Class Selector 3 service(24)
                cs4     Specify Class Selector 4 service(32)
                cs5     Specify Class Selector 5 service(40)
                cs6     Specify Class Selector 6 service(48)
                cs7     Specify Class Selector 7 service(56)
                ef      Specify Expedited Forwarding service(46)"
            ::= { unisAclAdvancedRuleEntry 17 }

        unisAclAdvancedEstablish OBJECT-TYPE
            SYNTAX TruthValue
            MAX-ACCESS read-create
            STATUS current
            DESCRIPTION
                "Establish flag."
            DEFVAL { false }
            ::= { unisAclAdvancedRuleEntry 18 }

        unisAclAdvancedTimeRangeName OBJECT-TYPE
            SYNTAX OCTET STRING (SIZE (0..32))
            MAX-ACCESS read-create
            STATUS current
            DESCRIPTION
                "The Time-range of advanced acl rule."
            ::= { unisAclAdvancedRuleEntry 19 }

        unisAclAdvancedIcmpType OBJECT-TYPE
            SYNTAX Integer32 (0..255|65535)
            MAX-ACCESS read-create
            STATUS current
            DESCRIPTION
                "The type of ICMP packet.
                Integer32               ICMP type
                echo                  Type=8, Code=0
                echo-reply            Type=0, Code=0
                fragmentneed-DFset    Type=3, Code=4
                host-redirect         Type=5, Code=1
                host-tos-redirect     Type=5, Code=3
                host-unreachable      Type=3, Code=1
                information-reply     Type=16, Code=0
                information-request   Type=15, Code=0
                net-redirect          Type=5, Code=0
                net-tos-redirect      Type=5, Code=2
                net-unreachable       Type=3, Code=0
                parameter-problem     Type=12, Code=0
                port-unreachable      Type=3, Code=3
                protocol-unreachable  Type=3, Code=2
                reassembly-timeout    Type=11, Code=1
                source-quench         Type=4, Code=0
                source-route-failed   Type=3, Code=5
                timestamp-reply       Type=14, Code=0
                timestamp-request     Type=13, Code=0
                ttl-exceeded          Type=11, Code=0  "
            ::= { unisAclAdvancedRuleEntry 20 }

        unisAclAdvancedIcmpCode OBJECT-TYPE
            SYNTAX Integer32 (0..255|65535)
            MAX-ACCESS read-create
            STATUS current
            DESCRIPTION
                "The code of ICMP packet."
            ::= { unisAclAdvancedRuleEntry 21 }

        unisAclAdvancedFragments OBJECT-TYPE
            SYNTAX TruthValue
            MAX-ACCESS read-create
            STATUS current
            DESCRIPTION
                "The flag of matching fragmented packet."
            ::= { unisAclAdvancedRuleEntry 22 }

        unisAclAdvancedLog OBJECT-TYPE
            SYNTAX TruthValue
            MAX-ACCESS read-create
            STATUS current
            DESCRIPTION
                "The flag of log."
            ::= { unisAclAdvancedRuleEntry 23 }

        unisAclAdvancedEnable OBJECT-TYPE
            SYNTAX TruthValue
            MAX-ACCESS read-only
            STATUS current
            DESCRIPTION
                "The rule is active or not.
                 true : active
                 false : inactive
                "
            ::= { unisAclAdvancedRuleEntry 24 }

        unisAclAdvancedCount OBJECT-TYPE
            SYNTAX Counter32
            MAX-ACCESS read-only
            STATUS current
            DESCRIPTION
                "The count of matched by advanced rule."
            ::= { unisAclAdvancedRuleEntry 25 }

        unisAclAdvancedCountClear OBJECT-TYPE
            SYNTAX INTEGER
            {
                cleared(1),
                nouse(2)
            }
            MAX-ACCESS read-create
            STATUS current
            DESCRIPTION
                "Reset the value of counter."
            ::= { unisAclAdvancedRuleEntry 26 }

        unisAclAdvancedRowStatus OBJECT-TYPE
            SYNTAX RowStatus
            MAX-ACCESS read-create
            STATUS current
            DESCRIPTION
                "RowStatus, now support three state: CreateAndGo, Active, Destroy."
            ::= { unisAclAdvancedRuleEntry 27 }
--
-- unisAclIfRuleTable
--
        unisAclIfRuleTable OBJECT-TYPE
            SYNTAX SEQUENCE OF UnisAclIfRuleEntry
            MAX-ACCESS not-accessible
            STATUS current
            DESCRIPTION
                "Configure the rule for interface-based acl group."
            ::= { unisAclMibObjects 6 }

        unisAclIfRuleEntry OBJECT-TYPE
            SYNTAX UnisAclIfRuleEntry
            MAX-ACCESS not-accessible
            STATUS current
            DESCRIPTION
                "Define the index of unisAclIfRuleTable."
            INDEX { unisAclIfAclNum, unisAclIfSubitem }
            ::= { unisAclIfRuleTable 1 }

        UnisAclIfRuleEntry ::=
            SEQUENCE {
                unisAclIfAclNum
                    Integer32,
                unisAclIfSubitem
                    Integer32,
                unisAclIfAct
                    INTEGER,
                unisAclIfIndex
                    Integer32,
                unisAclIfAny
                    TruthValue,
                unisAclIfTimeRangeName
                    OCTET STRING,
                unisAclIfLog
                    TruthValue,
                unisAclIfEnable
                    TruthValue,
                unisAclIfCount
                    Counter32,
                unisAclIfCountClear
                    INTEGER,
                unisAclIfRowStatus
                    RowStatus
             }

        unisAclIfAclNum OBJECT-TYPE
            SYNTAX Integer32 (0|1000..1999|10000..12999)
            MAX-ACCESS not-accessible
            STATUS current
            DESCRIPTION
                "The index of interface-based acl group."
            ::= { unisAclIfRuleEntry 1 }

        unisAclIfSubitem OBJECT-TYPE
            SYNTAX Integer32 (0..65535)
            MAX-ACCESS not-accessible
            STATUS current
            DESCRIPTION
                "The subindex of interface-based acl group."
            ::= { unisAclIfRuleEntry 2 }

        unisAclIfAct OBJECT-TYPE
            SYNTAX INTEGER
            {
                permit(1),
                deny(2)
            }
            MAX-ACCESS read-create
            STATUS current
            DESCRIPTION
                "The action of interface-based acl group."
            ::= { unisAclIfRuleEntry 3 }

        unisAclIfIndex OBJECT-TYPE
            SYNTAX Integer32 (0..2147483647)
            MAX-ACCESS read-create
            STATUS current
            DESCRIPTION
                "The index of interface."
            ::= { unisAclIfRuleEntry 4 }

        unisAclIfAny OBJECT-TYPE
            SYNTAX TruthValue
            MAX-ACCESS read-create
            STATUS current
            DESCRIPTION
                "The flag of matching any interface."
            ::= { unisAclIfRuleEntry 5 }

        unisAclIfTimeRangeName OBJECT-TYPE
            SYNTAX OCTET STRING (SIZE (0..32))
            MAX-ACCESS read-create
            STATUS current
            DESCRIPTION
                "The Time-range of interface-based acl rule."
            ::= { unisAclIfRuleEntry 6 }

        unisAclIfLog OBJECT-TYPE
            SYNTAX TruthValue
            MAX-ACCESS read-create
            STATUS current
            DESCRIPTION
                "The flag of log."
            ::= { unisAclIfRuleEntry 7 }

        unisAclIfEnable OBJECT-TYPE
            SYNTAX TruthValue
            MAX-ACCESS read-only
            STATUS current
            DESCRIPTION
                "The rule is active or not.
                 true : active
                 false : inactive
                "
            ::= { unisAclIfRuleEntry 8 }

        unisAclIfCount OBJECT-TYPE
            SYNTAX Counter32
            MAX-ACCESS read-only
            STATUS current
            DESCRIPTION
                "The count of matched by basic rule."
            ::= { unisAclIfRuleEntry 9 }

        unisAclIfCountClear OBJECT-TYPE
            SYNTAX INTEGER
            {
                cleared(1),
                nouse(2)
            }
            MAX-ACCESS read-create
            STATUS current
            DESCRIPTION
                "Reset the value of the rule's counter."
            ::= { unisAclIfRuleEntry 10 }

        unisAclIfRowStatus OBJECT-TYPE
            SYNTAX RowStatus
            MAX-ACCESS read-create
            STATUS current
            DESCRIPTION
                "RowStatus, now support three state: CreateAndGo, Active, Destroy."
            ::= { unisAclIfRuleEntry 11 }

--
-- unisAclLinkTable
--
        unisAclLinkTable OBJECT-TYPE
            SYNTAX SEQUENCE OF UnisAclLinkEntry
            MAX-ACCESS not-accessible
            STATUS current
            DESCRIPTION
                "Create link acl."
            ::= { unisAclMibObjects 7 }

        unisAclLinkEntry OBJECT-TYPE
            SYNTAX UnisAclLinkEntry
            MAX-ACCESS not-accessible
            STATUS current
            DESCRIPTION
                "The entry of the link acl table."
            INDEX { unisAclLinkAclNum, unisAclLinkSubitem }
            ::= { unisAclLinkTable 1 }

        UnisAclLinkEntry ::=
            SEQUENCE {
                unisAclLinkAclNum
                    Integer32,
                unisAclLinkSubitem
                    Integer32,
                unisAclLinkAct
                    INTEGER,
                unisAclLinkProtocol
                    INTEGER,
                unisAclLinkFormatType
                    INTEGER,
                unisAclLinkVlanTag
                    INTEGER,
                unisAclLinkVlanPri
                    Integer32,
                unisAclLinkSrcVlanId
                    Integer32,
                unisAclLinkSrcMac
                    MacAddress,
                unisAclLinkSrcMacWild
                    MacAddress,
                unisAclLinkSrcIfIndex
                    Integer32,
                unisAclLinkSrcAny
                    TruthValue,
                unisAclLinkDestVlanId
                    Integer32,
                unisAclLinkDestMac
                    MacAddress,
                unisAclLinkDestMacWild
                    MacAddress,
                unisAclLinkDestIfIndex
                    Integer32,
                unisAclLinkDestAny
                    TruthValue,
                unisAclLinkTimeRangeName
                    OCTET STRING,
                unisAclLinkEnable
                    TruthValue,
                unisAclLinkRowStatus
                    RowStatus,
                unisAclLinkTypeCode
                    OCTET STRING,
                unisAclLinkTypeMask
                    OCTET STRING,
                unisAclLinkLsapCode
                    OCTET STRING,
                unisAclLinkLsapMask
                    OCTET STRING,
                unisAclLinkL2LabelRangeOp
                    INTEGER,
                unisAclLinkL2LabelRangeBegin
                    Integer32,
                unisAclLinkL2LabelRangeEnd
                    Integer32,
                unisAclLinkMplsExp
                    Integer32
             }

        unisAclLinkAclNum OBJECT-TYPE
            SYNTAX Integer32 (0|4000..4999|10000..12999)
            MAX-ACCESS not-accessible
            STATUS current
            DESCRIPTION
                "The index of link-based acl group."
            ::= { unisAclLinkEntry 1 }

        unisAclLinkSubitem OBJECT-TYPE
            SYNTAX Integer32 (0..65535)
            MAX-ACCESS not-accessible
            STATUS current
            DESCRIPTION
                "The subindex of link-based acl group."
            ::= { unisAclLinkEntry 2 }

        unisAclLinkAct OBJECT-TYPE
            SYNTAX INTEGER
            {
                permit(1),
                deny(2)
            }
            MAX-ACCESS read-create
            STATUS current
            DESCRIPTION
                "The action of link-based acl group."
            ::= { unisAclLinkEntry 3 }

        unisAclLinkProtocol OBJECT-TYPE
            SYNTAX INTEGER
            {
                invalid(0),
                ip(2048),
                arp(2054),
                rarp(32821),
                mpls(34887),
                pppoeControl(34915),
                pppoeData(34916)
            }
            MAX-ACCESS read-create
            STATUS current
            DESCRIPTION
                "The layer 2 protocol-type of link acl rule."
            DEFVAL { invalid }
            ::= { unisAclLinkEntry 4 }

        unisAclLinkFormatType OBJECT-TYPE
            SYNTAX INTEGER
            {
                invalid(0),
                ethernetII(1),
                snap(2),
                ieee802Dot3And2(3),
                ieee802Dot3(4)
            }
            MAX-ACCESS read-create
            STATUS current
            DESCRIPTION
                "Format type of link acl rule."
            ::= { unisAclLinkEntry 5 }

        unisAclLinkVlanTag OBJECT-TYPE
            SYNTAX INTEGER
            {
                invalid(0),
                tagged(1),
                untagged(2)
            }
            MAX-ACCESS read-create
            STATUS current
            DESCRIPTION
                "The flag of vlan tag of link acl rule."
            ::= { unisAclLinkEntry 6 }

        unisAclLinkVlanPri OBJECT-TYPE
            SYNTAX Integer32 (0..7 | 255)
            MAX-ACCESS read-create
            STATUS current
            DESCRIPTION
                "Vlan priority of link acl rule."
            ::= { unisAclLinkEntry 7 }

        unisAclLinkSrcVlanId OBJECT-TYPE
            SYNTAX Integer32 (0..4094)
            MAX-ACCESS read-create
            STATUS current
            DESCRIPTION
                "Source vlan ID of link acl rule."
            ::= { unisAclLinkEntry 8 }

        unisAclLinkSrcMac OBJECT-TYPE
            SYNTAX MacAddress
            MAX-ACCESS read-create
            STATUS current
            DESCRIPTION
                "Source mac of link acl rule."
            ::= { unisAclLinkEntry 9 }

        unisAclLinkSrcMacWild OBJECT-TYPE
            SYNTAX MacAddress
            MAX-ACCESS read-create
            STATUS current
            DESCRIPTION
                "Source mac wildzard of link acl rule."
            ::= { unisAclLinkEntry 10 }

        unisAclLinkSrcIfIndex OBJECT-TYPE
            SYNTAX Integer32 (0..2147483647)
            MAX-ACCESS read-create
            STATUS current
            DESCRIPTION
                "Source IfIndex of link acl rule."
            ::= { unisAclLinkEntry 11 }

        unisAclLinkSrcAny OBJECT-TYPE
            SYNTAX TruthValue
            MAX-ACCESS read-create
            STATUS current
            DESCRIPTION
                "The flag of matching any source."
            ::= { unisAclLinkEntry 12 }

        unisAclLinkDestVlanId OBJECT-TYPE
            SYNTAX Integer32 (0..4094)
            MAX-ACCESS read-create
            STATUS current
            DESCRIPTION
                "Destination vlan ID of link acl rule."
            ::= { unisAclLinkEntry 13 }

        unisAclLinkDestMac OBJECT-TYPE
            SYNTAX MacAddress
            MAX-ACCESS read-create
            STATUS current
            DESCRIPTION
                "Destination mac of link acl rule."
            ::= { unisAclLinkEntry 14 }

        unisAclLinkDestMacWild OBJECT-TYPE
            SYNTAX MacAddress
            MAX-ACCESS read-create
            STATUS current
            DESCRIPTION
                "Destination mac wildzard of link acl rule."
            ::= { unisAclLinkEntry 15 }

        unisAclLinkDestIfIndex OBJECT-TYPE
            SYNTAX Integer32 (0..2147483647)
            MAX-ACCESS read-create
            STATUS current
            DESCRIPTION
                "Destination IfIndex of link acl rule."
            ::= { unisAclLinkEntry 16 }

        unisAclLinkDestAny OBJECT-TYPE
            SYNTAX TruthValue
            MAX-ACCESS read-create
            STATUS current
            DESCRIPTION
                "The flag of matching any destination."
            ::= { unisAclLinkEntry 17 }

        unisAclLinkTimeRangeName OBJECT-TYPE
            SYNTAX OCTET STRING (SIZE (0..32))
            MAX-ACCESS read-create
            STATUS current
            DESCRIPTION
                "The Time-range of link-based acl rule."
            ::= { unisAclLinkEntry 18 }

        unisAclLinkEnable OBJECT-TYPE
            SYNTAX TruthValue
            MAX-ACCESS read-only
            STATUS current
            DESCRIPTION
                "The rule is active or not.
                 true : active
                 false : inactive
                "
            ::= { unisAclLinkEntry 19 }

        unisAclLinkRowStatus OBJECT-TYPE
            SYNTAX RowStatus
            MAX-ACCESS read-create
            STATUS current
            DESCRIPTION
                "RowStatus, now support three state: CreateAndGo, Active, Destroy."
            ::= { unisAclLinkEntry 20 }

            unisAclLinkTypeCode   OBJECT-TYPE
            SYNTAX OCTET STRING ( SIZE(0..32) )
            MAX-ACCESS read-create
            STATUS current
            DESCRIPTION
                "The type of layer 2 protocol.0x0000...0xffff."
            ::= { unisAclLinkEntry 21 }

            unisAclLinkTypeMask   OBJECT-TYPE
            SYNTAX OCTET STRING ( SIZE(0..32) )
            MAX-ACCESS read-create
            STATUS current
            DESCRIPTION
                "The mask of layer 2 protocol.0x0000...0xffff."
            ::= { unisAclLinkEntry 22 }

            unisAclLinkLsapCode   OBJECT-TYPE
            SYNTAX     OCTET STRING (SIZE(0..32))
            MAX-ACCESS read-create
            STATUS current
            DESCRIPTION
                "The type of LSAP.0x0000...0xffff."
            ::= { unisAclLinkEntry 23 }

        unisAclLinkLsapMask   OBJECT-TYPE
            SYNTAX OCTET STRING (SIZE(0..32))
            MAX-ACCESS read-create
            STATUS current
            DESCRIPTION
                "The mask of LSAP.0x0000...0xffff."
            ::= { unisAclLinkEntry 24 }

        unisAclLinkL2LabelRangeOp OBJECT-TYPE
            SYNTAX INTEGER
            {
                invalid(0),
                lt(1),
                eq(2),
                gt(3),
                neq(4),
                range(5)
            }
            MAX-ACCESS read-create
            STATUS current
            DESCRIPTION
                "Operation symbol of the MPLS label.
                 If the symbol is range(5), the objects unisAclLinkL2LabelRangeBegin and
                 unisAclLinkL2LabelRangeEnd should have different values indicating a range.
                 Otherwise, only unisAclLinkL2LabelRangeBegin counts,
                 object unisAclLinkL2LabelRangeEnd is ignored.

                 invalid(0) -- unavailable
                 lt(1) -- less than
                 eq(2) -- equal
                 gt(3) -- great than
                 neq(4) -- not equal
                 range(5) -- a range with two ends included
                "
            ::= { unisAclLinkEntry 25 }

        unisAclLinkL2LabelRangeBegin OBJECT-TYPE
            SYNTAX Integer32
            MAX-ACCESS read-create
            STATUS current
            DESCRIPTION
                "The beginning of VPLS VC label."
            ::= { unisAclLinkEntry 26 }

        unisAclLinkL2LabelRangeEnd OBJECT-TYPE
            SYNTAX Integer32
            MAX-ACCESS read-create
            STATUS current
            DESCRIPTION
                "The end of VPLS VC label."
            ::= { unisAclLinkEntry 27 }

        unisAclLinkMplsExp OBJECT-TYPE
            SYNTAX Integer32
            MAX-ACCESS read-create
            STATUS current
            DESCRIPTION
                "The value of MPLS-packet's Exp."
            ::= { unisAclLinkEntry 28 }
--
-- unisAclUserTable
--
        unisAclUserTable OBJECT-TYPE
            SYNTAX SEQUENCE OF UnisAclUserEntry
            MAX-ACCESS not-accessible
            STATUS current
            DESCRIPTION
                "Create user acl."
            ::= { unisAclMibObjects 8 }

        unisAclUserEntry OBJECT-TYPE
            SYNTAX UnisAclUserEntry
            MAX-ACCESS not-accessible
            STATUS current
            DESCRIPTION
                "The entry of user acl table."
            INDEX { unisAclUserAclNum, unisAclUserSubitem }
            ::= { unisAclUserTable 1 }

        UnisAclUserEntry ::=
            SEQUENCE {
                unisAclUserAclNum
                    Integer32,
                unisAclUserSubitem
                    Integer32,
                unisAclUserAct
                    INTEGER,
                unisAclUserFormatType
                    INTEGER,
                unisAclUserVlanTag
                    INTEGER,
                unisAclUserRuleStr
                    OCTET STRING,
                unisAclUserRuleMask
                    OCTET STRING,
                unisAclUserTimeRangeName
                    OCTET STRING,
                unisAclUserEnable
                    TruthValue,
                unisAclUserRowStatus
                    RowStatus
             }

        unisAclUserAclNum OBJECT-TYPE
            SYNTAX Integer32 (0|5000..5999|10000..12999)
            MAX-ACCESS not-accessible
            STATUS current
            DESCRIPTION
                "The number of the user acl."
            ::= { unisAclUserEntry 1 }

        unisAclUserSubitem OBJECT-TYPE
            SYNTAX Integer32 (0..65535)
            MAX-ACCESS not-accessible
            STATUS current
            DESCRIPTION
                "The subitem of the user acl."
            ::= { unisAclUserEntry 2 }

        unisAclUserAct OBJECT-TYPE
            SYNTAX INTEGER
            {
                permit(1),
                deny(2)
            }
            MAX-ACCESS read-create
            STATUS current
            DESCRIPTION
                "The action of the user acl."
            ::= { unisAclUserEntry 3 }

        unisAclUserFormatType OBJECT-TYPE
            SYNTAX INTEGER
            {
                invalid(0),
                ethernetII(1),
                snap(2),
                ieee802Dot2And3(3),
                ieee802Dot4(4)
            }
            MAX-ACCESS read-create
            STATUS current
            DESCRIPTION
                "Format type."
            DEFVAL { invalid }
            ::= { unisAclUserEntry 4 }

        unisAclUserVlanTag OBJECT-TYPE
            SYNTAX INTEGER
            {
                invalid(0),
                tagged(1),
                untagged(2)
            }
            MAX-ACCESS read-create
            STATUS current
            DESCRIPTION
                "Vlan tag exits or not."
            DEFVAL { invalid }
            ::= { unisAclUserEntry 5 }

        unisAclUserRuleStr OBJECT-TYPE
            SYNTAX OCTET STRING (SIZE (1..80))
            MAX-ACCESS read-create
            STATUS current
            DESCRIPTION
                "Rule string."
            ::= { unisAclUserEntry 6 }

        unisAclUserRuleMask OBJECT-TYPE
            SYNTAX OCTET STRING (SIZE (1..80))
            MAX-ACCESS read-create
            STATUS current
            DESCRIPTION
                "Rule mask."
            ::= { unisAclUserEntry 7 }

        unisAclUserTimeRangeName OBJECT-TYPE
            SYNTAX OCTET STRING (SIZE (0..32))
            MAX-ACCESS read-create
            STATUS current
            DESCRIPTION
                "The Time-range of the user defined acl."
            ::= { unisAclUserEntry 8 }

        unisAclUserEnable OBJECT-TYPE
            SYNTAX TruthValue
            MAX-ACCESS read-only
            STATUS current
            DESCRIPTION
                "The rule is active or not.
                 true : active
                 false : inactive
                "
            ::= { unisAclUserEntry 9 }

        unisAclUserRowStatus OBJECT-TYPE
            SYNTAX RowStatus
            MAX-ACCESS read-create
            STATUS current
            DESCRIPTION
                "RowStatus, now support three state: CreateAndGo, Active, Destroy."
            ::= { unisAclUserEntry 10 }
--
-- unisAclActiveTable
--
        unisAclActiveTable OBJECT-TYPE
            SYNTAX SEQUENCE OF UnisAclActiveEntry
            MAX-ACCESS not-accessible
            STATUS current
            DESCRIPTION
                "Active acl."
            ::= { unisAclMibObjects 9 }

        unisAclActiveEntry OBJECT-TYPE
            SYNTAX UnisAclActiveEntry
            MAX-ACCESS not-accessible
            STATUS current
            DESCRIPTION
                "The entry of active acl table."
            INDEX { unisAclActiveAclIndex,
                    unisAclActiveIfIndex,
                    unisAclActiveVlanID,
                    unisAclActiveDirection
                  }
            ::= { unisAclActiveTable 1 }

        UnisAclActiveEntry ::=
            SEQUENCE {
                unisAclActiveAclIndex
                    Integer32,
                unisAclActiveIfIndex
                    Integer32,
                unisAclActiveVlanID
                    Integer32,
                unisAclActiveDirection
                    INTEGER,
                unisAclActiveUserAclNum
                    Integer32,
                unisAclActiveUserAclSubitem
                    Integer32,
                unisAclActiveIpAclNum
                    Integer32,
                unisAclActiveIpAclSubitem
                    Integer32,
                unisAclActiveLinkAclNum
                    Integer32,
                unisAclActiveLinkAclSubitem
                    Integer32,
                unisAclActiveRuntime
                    TruthValue,
                unisAclActiveRowStatus
                    RowStatus
             }

        unisAclActiveAclIndex OBJECT-TYPE
            SYNTAX Integer32 (0|1..5999|10000..12999)
            MAX-ACCESS not-accessible
            STATUS current
            DESCRIPTION
                "Acl index."
            ::= { unisAclActiveEntry 1 }

        unisAclActiveIfIndex OBJECT-TYPE
            SYNTAX Integer32 (0..2147483647)
            MAX-ACCESS not-accessible
            STATUS current
            DESCRIPTION
                "IfIndex."
            ::= { unisAclActiveEntry 2 }

        unisAclActiveVlanID OBJECT-TYPE
            SYNTAX Integer32
            MAX-ACCESS not-accessible
            STATUS current
            DESCRIPTION
                "The lower 16 bits is Vlan ID, the higher 16 bits,
                 if not zero, it describes the slot ID of the L3plus board.
                "
            ::= { unisAclActiveEntry 3 }

        unisAclActiveDirection OBJECT-TYPE
            SYNTAX INTEGER
            {
                invalid(0),
                input(1),
                output(2),
                both(3)
            }
            MAX-ACCESS not-accessible
            STATUS current
            DESCRIPTION
                "Direction."
            ::= { unisAclActiveEntry 4 }

        unisAclActiveUserAclNum OBJECT-TYPE
            SYNTAX Integer32 (0|5000..5999|10000..12999)
            MAX-ACCESS read-create
            STATUS current
            DESCRIPTION
                "The number of the user acl."
            ::= { unisAclActiveEntry 5 }

        unisAclActiveUserAclSubitem OBJECT-TYPE
            SYNTAX Integer32 (0..65535)
            MAX-ACCESS read-create
            STATUS current
            DESCRIPTION
                "The subitem of the user acl."
            ::= { unisAclActiveEntry 6 }

        unisAclActiveIpAclNum OBJECT-TYPE
            SYNTAX Integer32 (0|2000..3999|10000..12999)
            MAX-ACCESS read-create
            STATUS current
            DESCRIPTION
                "The number of the IP acl."
            ::= { unisAclActiveEntry 7 }

        unisAclActiveIpAclSubitem OBJECT-TYPE
            SYNTAX Integer32 (0..65535)
            MAX-ACCESS read-create
            STATUS current
            DESCRIPTION
                "The subitem of the IP acl."
            ::= { unisAclActiveEntry 8 }

        unisAclActiveLinkAclNum OBJECT-TYPE
            SYNTAX Integer32 (0|4000..4999|10000..12999)
            MAX-ACCESS read-create
            STATUS current
            DESCRIPTION
                "The num of the link acl."
            ::= { unisAclActiveEntry 9 }

        unisAclActiveLinkAclSubitem OBJECT-TYPE
            SYNTAX Integer32 (0..65535)
            MAX-ACCESS read-create
            STATUS current
            DESCRIPTION
                "The subitem of the link acl."
            ::= { unisAclActiveEntry 10 }

        unisAclActiveRuntime OBJECT-TYPE
            SYNTAX TruthValue
            MAX-ACCESS read-only
            STATUS current
            DESCRIPTION
                "Is run or not."
            ::= { unisAclActiveEntry 11 }

        unisAclActiveRowStatus OBJECT-TYPE
            SYNTAX RowStatus
            MAX-ACCESS read-create
            STATUS current
            DESCRIPTION
                "RowStatus, now support three state: CreateAndGo, Active, Destroy."
            ::= { unisAclActiveEntry 12 }

--
-- unisAclIDSTable
--
        unisAclIDSTable OBJECT-TYPE
            SYNTAX SEQUENCE OF UnisAclIDSEntry
            MAX-ACCESS not-accessible
            STATUS current
            DESCRIPTION
                "Configure the rule for IDS."
            ::= { unisAclMibObjects 10 }

        unisAclIDSEntry OBJECT-TYPE
            SYNTAX UnisAclIDSEntry
            MAX-ACCESS not-accessible
            STATUS current
            DESCRIPTION
                "The entry of acl ids table."
            INDEX { IMPLIED unisAclIDSName}
            ::= { unisAclIDSTable 1 }

        UnisAclIDSEntry ::=
            SEQUENCE {
                unisAclIDSName
                    OCTET STRING,
                unisAclIDSSrcMac
                    MacAddress,
                unisAclIDSDestMac
                    MacAddress,
                unisAclIDSSrcIp
                    IpAddress,
                unisAclIDSSrcWild
                    IpAddress,
                unisAclIDSDestIp
                    IpAddress,
                unisAclIDSDestWild
                    IpAddress,
                unisAclIDSSrcPort
                    Integer32,
                unisAclIDSDestPort
                    Integer32,
                unisAclIDSProtocol
                    Integer32,
                unisAclIDSDenyTime
                    Unsigned32,
                unisAclIDSAct
                    INTEGER,
                unisAclIDSRowStatus
                    RowStatus
             }

        unisAclIDSName OBJECT-TYPE
            SYNTAX OCTET STRING (SIZE (1..32))
            MAX-ACCESS not-accessible
            STATUS current
            DESCRIPTION
                "The name index of the IDS table."
            ::= { unisAclIDSEntry 1 }

        unisAclIDSSrcMac OBJECT-TYPE
            SYNTAX MacAddress
            MAX-ACCESS read-create
            STATUS current
            DESCRIPTION
                "Source mac of IDS acl rule."
            ::= { unisAclIDSEntry 2 }


        unisAclIDSDestMac OBJECT-TYPE
            SYNTAX MacAddress
            MAX-ACCESS read-create
            STATUS current
            DESCRIPTION
                "Destination mac of IDS acl rule."
            ::= { unisAclIDSEntry 3 }

           unisAclIDSSrcIp OBJECT-TYPE
            SYNTAX IpAddress
            MAX-ACCESS read-create
            STATUS current
            DESCRIPTION
                "Source IP-address of IDS acl rule."
            ::= { unisAclIDSEntry 4 }

        unisAclIDSSrcWild OBJECT-TYPE
            SYNTAX IpAddress
            MAX-ACCESS read-create
            STATUS current
            DESCRIPTION
                "Source IP-address wild of IDS acl rule."
            ::= { unisAclIDSEntry 5 }

           unisAclIDSDestIp OBJECT-TYPE
            SYNTAX IpAddress
            MAX-ACCESS read-create
            STATUS current
            DESCRIPTION
                "Destination IP-address of IDS acl rule."
            ::= { unisAclIDSEntry 6 }

        unisAclIDSDestWild OBJECT-TYPE
            SYNTAX IpAddress
            MAX-ACCESS read-create
            STATUS current
            DESCRIPTION
                "Destination IP-address wild of IDS acl rule."
            ::= { unisAclIDSEntry 7 }

            unisAclIDSSrcPort OBJECT-TYPE
            SYNTAX Integer32 (0..65535)
            MAX-ACCESS read-create
            STATUS current
            DESCRIPTION
                "The fourth layer source port."
            ::= { unisAclIDSEntry 8 }

        unisAclIDSDestPort OBJECT-TYPE
            SYNTAX Integer32 (0..65535)
            MAX-ACCESS read-create
            STATUS current
            DESCRIPTION
                "The fourth layer destination port."
            ::= { unisAclIDSEntry 9 }

            unisAclIDSProtocol OBJECT-TYPE
            SYNTAX Integer32 (0..255)
            MAX-ACCESS read-create
            STATUS current
            DESCRIPTION
                "The protocol-type of advanced acl group.
                 <1-255>  Protocol number
                  gre      GRE tunneling(47)
                  icmp     Internet Control Message Protocol(1)
                  igmp     Internet Group Management Protocol(2)
                  ip       Any IP protocol
                  ipinip   IP in IP tunneling(4)
                  ospf     OSPF routing protocol(89)
                  tcp      Transmission Control Protocol (6)
                  udp      User Datagram Protocol (17)
                 "
            ::= { unisAclIDSEntry 10 }

        unisAclIDSDenyTime OBJECT-TYPE
            SYNTAX Unsigned32
            MAX-ACCESS read-create
            STATUS current
            DESCRIPTION
                "The maximum number of seconds which deny for this acl rule."
            DEFVAL { 0 }
            ::= { unisAclIDSEntry 11 }


        unisAclIDSAct OBJECT-TYPE
            SYNTAX INTEGER
            {
                permit(1),
                deny(2)
            }
            MAX-ACCESS read-create
            STATUS current
            DESCRIPTION
                "The action of IDS acl rule."
            ::= { unisAclIDSEntry 12 }

        unisAclIDSRowStatus OBJECT-TYPE
            SYNTAX RowStatus
            MAX-ACCESS read-create
            STATUS current
            DESCRIPTION
                "RowStatus, now supports three states:  CreateAndGo, Active, and Destroy."
            ::= { unisAclIDSEntry 13 }
--
-- Nodes of unisAclMib2Objects
--
        unisAclMib2Objects OBJECT IDENTIFIER ::= { unisAcl 2 }
--
-- Nodes of unisAclMib2GlobalGroup
--
        unisAclMib2GlobalGroup OBJECT IDENTIFIER ::= { unisAclMib2Objects 1 }

        unisAclMib2NodesGroup OBJECT IDENTIFIER ::= { unisAclMib2GlobalGroup 1 }

        unisAclMib2Mode OBJECT-TYPE
            SYNTAX INTEGER
            {
                linkBased(1),
                ipBased(2)
            }
            MAX-ACCESS read-write
            STATUS current
            DESCRIPTION
                "The applying mode of ACL."
            ::= { unisAclMib2NodesGroup 1 }

        unisAclMib2Version OBJECT-TYPE
            SYNTAX Integer32
            MAX-ACCESS read-only
            STATUS current
            DESCRIPTION
                "The version of this file.
                 The output value has the format of 'xx'or 'xxx'.
                 For example: 10 means 1.0; 125 means 12.5.
                "
            ::= { unisAclMib2NodesGroup 2 }

        unisAclMib2ObjectsCapabilities OBJECT-TYPE
            SYNTAX BITS
            {
                unisAclMib2Mode(0),
                unisAclVersion(1),
                unisAclMib2ObjectsCapabilities(2),
                unisAclMib2CapabilityTable(3),
                unisAclNumberGroupTable(4),
                unisAclIPAclBasicTable(5),
                unisAclIPAclAdvancedTable(6),
                unisAclMACTable(7),
                unisAclEnUserTable(8),
                unisAclMib2ProcessingStatus(9)
            }
            MAX-ACCESS read-only
            STATUS current
            DESCRIPTION
                "The objects of unisAclMib2Objects."
            ::= { unisAclMib2NodesGroup 3 }

        unisAclMib2ProcessingStatus OBJECT-TYPE
            SYNTAX INTEGER
            {
                processing(1),
                done(2)
            }
            MAX-ACCESS read-only
            STATUS current
            DESCRIPTION
                "The processing status of ACL operation."
            ::= { unisAclMib2NodesGroup 4 }

        unisAclMib2ResourceThreshold OBJECT-TYPE
            SYNTAX Integer32 (0..100)
            MAX-ACCESS read-write
            STATUS current
            DESCRIPTION
                "The threshold of TCAM resources.
                 The value 0 indicates that cancelling the TCAM resource notification function."
            ::= { unisAclMib2NodesGroup 5 }

        unisAclMib2ResourceLogInterval OBJECT-TYPE
            SYNTAX Integer32 (1..60)
            MAX-ACCESS read-write
            STATUS current
            DESCRIPTION
                "The value of interval.  It must be in the range of 1 to 60.
                 Default value is 5."
            ::= { unisAclMib2NodesGroup 6 }

        unisAclMib2CapabilityTable OBJECT-TYPE
            SYNTAX SEQUENCE OF UnisAclMib2CapabilityEntry
            MAX-ACCESS not-accessible
            STATUS current
            DESCRIPTION
                "The capability of mib2."
            ::= { unisAclMib2GlobalGroup 2 }

        unisAclMib2CapabilityEntry OBJECT-TYPE
            SYNTAX UnisAclMib2CapabilityEntry
            MAX-ACCESS not-accessible
            STATUS current
            DESCRIPTION
                "The information of Capability of mib2."
            INDEX { unisAclMib2EntityType,
                    unisAclMib2EntityIndex,
                    unisAclMib2ModuleIndex,
                    unisAclMib2CharacteristicsIndex
                  }
            ::= { unisAclMib2CapabilityTable 1 }

        UnisAclMib2CapabilityEntry ::=
            SEQUENCE
            {
                unisAclMib2EntityType
                    INTEGER,
                unisAclMib2EntityIndex
                    Integer32,
                unisAclMib2ModuleIndex
                    INTEGER,
                unisAclMib2CharacteristicsIndex
                    Integer32,
                unisAclMib2CharacteristicsDesc
                    OCTET STRING,
                unisAclMib2CharacteristicsValue
                    Unsigned32
            }

        unisAclMib2EntityType OBJECT-TYPE
            SYNTAX INTEGER
            {
                system(1),
                interface(2)
            }
            MAX-ACCESS not-accessible
            STATUS current
            DESCRIPTION
                "The type of entity.
                 system: The entity is systemic level.
                 interface: The entity is interface level.
                "
            ::= { unisAclMib2CapabilityEntry 1 }

        unisAclMib2EntityIndex OBJECT-TYPE
            SYNTAX Integer32 (0..2147483647)
            MAX-ACCESS not-accessible
            STATUS current
            DESCRIPTION
                "The index of entity.
                 If unisAclMib2EntityType is system, the value of this object is 0.

                 If unisAclMib2EntityType is interface,
                 the value of this object is equal to 'ifIndex'.
                "
            ::= { unisAclMib2CapabilityEntry 2 }

        unisAclMib2ModuleIndex OBJECT-TYPE
            SYNTAX INTEGER
            {
                layer3(1),
                layer2(2),
                userDefined(3)
            }
            MAX-ACCESS not-accessible
            STATUS current
            DESCRIPTION
                "The module index of ACL."
            ::= { unisAclMib2CapabilityEntry 3 }

        unisAclMib2CharacteristicsIndex OBJECT-TYPE
            SYNTAX Integer32 (0..2147483647)
            MAX-ACCESS not-accessible
            STATUS current
            DESCRIPTION
                "The characteristics index of mib2.
                 See DESCRIPTION of unisAclMib2CharacteristicsValue
                 to get detail information about the value of this object.
                "
            ::= { unisAclMib2CapabilityEntry 4 }

        unisAclMib2CharacteristicsDesc OBJECT-TYPE
            SYNTAX OCTET STRING (SIZE(0..255))
            MAX-ACCESS read-only
            STATUS current
            DESCRIPTION
                "The description of characteristics."
            ::= { unisAclMib2CapabilityEntry 5 }

        unisAclMib2CharacteristicsValue OBJECT-TYPE
            SYNTAX Unsigned32
            MAX-ACCESS read-only
            STATUS current
            DESCRIPTION
                "The value of capability of this object.
                 TypeOfRuleStringValue : notSupport(0) and the length of
                 RuleString.

                 TypeOfCodeValue : OnlyOneNotSupport(0),
                                   MoreThanOneNotSupport(1)
                 If unisAclMib2CharacteristicsValue is 'moreThanOneNotSupport',
                 unisAclMib2CharacteristicsDesc must be used to depict which
                 protocols are not supported.  The output value of
                 unisAclMib2CharacteristicsDesc has the format of 'a,b'.
                 For example, 'ip,rarp'.

                 layer3 Module:
                 Index    Characteristics           value
                 1        SourceIPAddress           notSupport(0)
                 2        DestinationIPAddress      notSupport(0)
                 3        SourcePort                notSupport(0)
                 4        DestinationPort           notSupport(0)
                 5        IPPrecedence              notSupport(0)
                 6        TOS                       notSupport(0)
                 7        DSCP                      notSupport(0)
                 8        TCPFlag                   notSupport(0)
                 9        FragmentFlag              notSupport(0)
                 10       Log                       notSupport(0)
                 11       RuleMatchCounter          notSupport(0)
                 12       ResetRuleMatchCounter     notSupport(0)
                 13       VPN                       notSupport(0)
                 15       protocol                  notSupport(0)
                 16       AddressFlag               notSupport(0)

                 layer2 Module:
                 Index    Characteristics           value
                 1        ProtocolType              TypeOfCodeValue
                 2        SourceMAC                 notSupport(0)
                 3        DestinationMAC            notSupport(0)
                 4        LSAPType                  TypeOfCodeValue
                 5        CoS                       notSupport(0)

                 UserDefined Module:
                 Index    Characteristics           value
                 1        UserDefaultOffset         TypeOfRuleStringValue
                 2        UserL2RuleOffset          TypeOfRuleStringValue
                 3        UserMplsOffset            TypeOfRuleStringValue
                 4        UserIPv4Offset            TypeOfRuleStringValue
                 5        UserIPv6Offset            TypeOfRuleStringValue
                 6        UserL4Offset              TypeOfRuleStringValue
                 7        UserL5Offset              TypeOfRuleStringValue
                "
            ::= { unisAclMib2CapabilityEntry 6 }

--
-- Nodes of number group
--
        unisAclNumberGroupTable OBJECT-TYPE
            SYNTAX SEQUENCE OF UnisAclNumberGroupEntry
            MAX-ACCESS not-accessible
            STATUS current
            DESCRIPTION
                "A table of the number acl group information."
            ::= { unisAclMib2GlobalGroup 3 }

        unisAclNumberGroupEntry OBJECT-TYPE
            SYNTAX UnisAclNumberGroupEntry
            MAX-ACCESS not-accessible
            STATUS current
            DESCRIPTION
                "Number acl group information entry."
            INDEX { unisAclNumberGroupType, unisAclNumberGroupIndex }
            ::= { unisAclNumberGroupTable 1 }

        UnisAclNumberGroupEntry ::=
            SEQUENCE
            {
                unisAclNumberGroupType
                    INTEGER,
                unisAclNumberGroupIndex
                    Integer32,
                unisAclNumberGroupRowStatus
                    RowStatus,
                unisAclNumberGroupMatchOrder
                    INTEGER,
                unisAclNumberGroupStep
                    Integer32,
                unisAclNumberGroupDescription
                    OCTET STRING,
                unisAclNumberGroupCountClear
                    CounterClear,
                unisAclNumberGroupRuleCounter
                    Counter32,
                unisAclNumberGroupName
                    OCTET STRING
            }
        unisAclNumberGroupType OBJECT-TYPE
            SYNTAX INTEGER
            {
                ipv4(1),
                ipv6(2),
                mac(3),
                user(4)
            }
            MAX-ACCESS not-accessible
            STATUS current
            DESCRIPTION
                "The type of number group.
                 Basic ACL and Advanced ACL support ipv4 and ipv6.
                 The range of Basic ACL is from 2000 to 2999.
                 The range of Advanced ACL is from 3000 to 3999.

                 Simple ACL supports ipv6 only.
                 The range of Simple ACL is from 10000 to 42767.

                 MAC ACL support mac only.
                 The range of MAC ACL is from 4000 to 4999.

                 User-defined ACL support user only.
                 The range of user-defined ACL is from 5000 to 5999.
                "
            ::= { unisAclNumberGroupEntry 1 }

        unisAclNumberGroupIndex OBJECT-TYPE
            SYNTAX Integer32 (2000..5999|10000..42767)
            MAX-ACCESS not-accessible
            STATUS current
            DESCRIPTION
                "The group index of number acl.
                 Basic type:2000..2999
                 Advanced type:3000..3999
                 MAC type:4000..4999
                 User type:5000..5999
                 Simple type:10000..42767
                "
            ::= { unisAclNumberGroupEntry 2 }

        unisAclNumberGroupRowStatus OBJECT-TYPE
            SYNTAX RowStatus
            MAX-ACCESS read-create
            STATUS current
            DESCRIPTION
                "RowStatus."
            ::= { unisAclNumberGroupEntry 3 }

        unisAclNumberGroupMatchOrder OBJECT-TYPE
            SYNTAX INTEGER
            {
                config(1),
                auto(2)
            }
            MAX-ACCESS read-create
            STATUS current
            DESCRIPTION
                "The match-order of number acl group."
            DEFVAL { config }
            ::= { unisAclNumberGroupEntry 4 }

        unisAclNumberGroupStep OBJECT-TYPE
            SYNTAX Integer32 (1..20)
            MAX-ACCESS read-create
            STATUS current
            DESCRIPTION
                "The step of rule index."
            DEFVAL { 5 }
            ::= { unisAclNumberGroupEntry 5 }

        unisAclNumberGroupDescription OBJECT-TYPE
            SYNTAX OCTET STRING (SIZE(0..127))
            MAX-ACCESS read-create
            STATUS current
            DESCRIPTION
                "Description of this acl group."
            ::= { unisAclNumberGroupEntry 6 }

        unisAclNumberGroupCountClear OBJECT-TYPE
            SYNTAX CounterClear
            MAX-ACCESS read-write
            STATUS current
            DESCRIPTION
                "Reset the value of counters of this group."
            DEFVAL { nouse }
            ::= { unisAclNumberGroupEntry 7 }

        unisAclNumberGroupRuleCounter OBJECT-TYPE
            SYNTAX Counter32
            MAX-ACCESS read-only
            STATUS current
            DESCRIPTION
                "The rule count of number acl group."
            ::= { unisAclNumberGroupEntry 8 }

        unisAclNumberGroupName OBJECT-TYPE
            SYNTAX OCTET STRING (SIZE(0..63))
            MAX-ACCESS read-create
            STATUS current
            DESCRIPTION
                "Name of this acl group."
            ::= { unisAclNumberGroupEntry 9 }

--
-- Nodes of named ACL group
--
       unisAclNamedGroupTable OBJECT-TYPE
            SYNTAX SEQUENCE OF UnisAclNamedGroupEntry
            MAX-ACCESS not-accessible
            STATUS current
            DESCRIPTION
                "A table of the named ACL group."
            ::= { unisAclMib2GlobalGroup 4 }

        unisAclNamedGroupEntry OBJECT-TYPE
            SYNTAX UnisAclNamedGroupEntry
            MAX-ACCESS not-accessible
            STATUS current
            DESCRIPTION
                "Named ACL group entry."
            INDEX
            {
                unisAclNumberGroupType,
                unisAclNamedGroupCategory,
                unisAclNamedGroupName
            }
            ::= { unisAclNamedGroupTable 1 }

        UnisAclNamedGroupEntry ::=
            SEQUENCE
            {
                unisAclNamedGroupCategory
                    INTEGER,
                unisAclNamedGroupName
                    OCTET STRING,
                unisAclNamedGroupRowStatus
                    RowStatus,
                unisAclNamedGroupMatchOrder
                    INTEGER,
                unisAclNamedGroupStep
                    Integer32,
                unisAclNamedGroupDescription
                    OCTET STRING,
                unisAclNamedGroupCountClear
                    CounterClear,
                unisAclNamedGroupRuleCounter
                    Counter32
            }

        unisAclNamedGroupCategory OBJECT-TYPE
            SYNTAX INTEGER
            {
                invalid(0),
                basic(1),
                advanced(2)
            }
            MAX-ACCESS not-accessible
            STATUS current
            DESCRIPTION
                "The category of number group.  1 indicates basic ACL, 2 indicates
                advanced ACL."
            ::= { unisAclNamedGroupEntry 1 }

        unisAclNamedGroupName OBJECT-TYPE
            SYNTAX OCTET STRING (SIZE(1..63))
            MAX-ACCESS not-accessible
            STATUS current
            DESCRIPTION
                "Name of an ACL group, a case-insensitive string of 1 to 63
                characters.  It must start with an English letter.
                "
            ::= { unisAclNamedGroupEntry 2 }

        unisAclNamedGroupRowStatus OBJECT-TYPE
            SYNTAX RowStatus
            MAX-ACCESS read-create
            STATUS current
            DESCRIPTION
                "RowStatus."
            ::= { unisAclNamedGroupEntry 3 }

        unisAclNamedGroupMatchOrder OBJECT-TYPE
            SYNTAX INTEGER
            {
                config(1),
                auto(2)
            }
            MAX-ACCESS read-create
            STATUS current
            DESCRIPTION
                "The match-order of name acl group."
            DEFVAL { config }
            ::= { unisAclNamedGroupEntry 4 }

       unisAclNamedGroupStep OBJECT-TYPE
            SYNTAX Integer32 (1..20)
            MAX-ACCESS read-create
            STATUS current
            DESCRIPTION
                "The numbering step of the increment of the rule index."
            DEFVAL { 5 }
            ::= { unisAclNamedGroupEntry 5 }

        unisAclNamedGroupDescription OBJECT-TYPE
            SYNTAX OCTET STRING (SIZE(0..127))
            MAX-ACCESS read-create
            STATUS current
            DESCRIPTION
                "Description of this ACL group."
            ::= { unisAclNamedGroupEntry 6 }

        unisAclNamedGroupCountClear OBJECT-TYPE
            SYNTAX CounterClear
            MAX-ACCESS read-write
            STATUS current
            DESCRIPTION
                "Reset the statistics counter of this group."
            DEFVAL { nouse }
            ::= { unisAclNamedGroupEntry 7 }

        unisAclNamedGroupRuleCounter OBJECT-TYPE
            SYNTAX Counter32
            MAX-ACCESS read-only
            STATUS current
            DESCRIPTION
                "The amount of rules of this group."
            ::= { unisAclNamedGroupEntry 8 }

--
-- Node of unisAclIPv6Group
--
        unisAclIPAclGroup OBJECT IDENTIFIER ::= { unisAclMib2Objects 2 }

--
-- Nodes of unisAclIPAclBasicTable
--

        unisAclIPAclBasicTable OBJECT-TYPE
            SYNTAX SEQUENCE OF UnisAclIPAclBasicEntry
            MAX-ACCESS not-accessible
            STATUS current
            DESCRIPTION
                "A table of basic rule group.
                 If some objects of this table are not supported by some products,
                 these objects can't be created, changed or applied.
                 Default value of these objects will be returned when they are read.
                "
            ::= { unisAclIPAclGroup 2 }

        unisAclIPAclBasicEntry OBJECT-TYPE
            SYNTAX UnisAclIPAclBasicEntry
            MAX-ACCESS not-accessible
            STATUS current
            DESCRIPTION
                "Basic rule group information."
            INDEX { unisAclNumberGroupType,
                    unisAclNumberGroupIndex,
                    unisAclIPAclBasicRuleIndex
                  }
            ::= { unisAclIPAclBasicTable 1 }

        UnisAclIPAclBasicEntry ::=
            SEQUENCE
            {
                unisAclIPAclBasicRuleIndex
                    Integer32,
                unisAclIPAclBasicRowStatus
                    RowStatus,
                unisAclIPAclBasicAct
                    RuleAction,
                unisAclIPAclBasicSrcAddrType
                    InetAddressType,
                unisAclIPAclBasicSrcAddr
                    InetAddress,
                unisAclIPAclBasicSrcPrefix
                    InetAddressPrefixLength,
                unisAclIPAclBasicSrcAny
                    TruthValue,
                unisAclIPAclBasicSrcWild
                    IpAddress,
                unisAclIPAclBasicTimeRangeName
                    OCTET STRING,
                unisAclIPAclBasicFragmentFlag
                    FragmentFlag,
                unisAclIPAclBasicLog
                    TruthValue,
                unisAclIPAclBasicCount
                    Unsigned32,
                unisAclIPAclBasicCountClear
                    CounterClear,
                unisAclIPAclBasicEnable
                    TruthValue,
                unisAclIPAclBasicVpnInstanceName
                    OCTET STRING,
                unisAclIPAclBasicComment
                    OCTET STRING,
                unisAclIPAclBasicCounting
                    TruthValue,
                unisAclIPAclBasicRouteTypeAny
                    TruthValue,
                unisAclIPAclBasicRouteTypeValue
                    Integer32
            }

        unisAclIPAclBasicRuleIndex OBJECT-TYPE
            SYNTAX Integer32 (0..65534)
            MAX-ACCESS not-accessible
            STATUS current
            DESCRIPTION
                "The rule index of basic acl group."
            ::= { unisAclIPAclBasicEntry 1 }

        unisAclIPAclBasicRowStatus OBJECT-TYPE
            SYNTAX RowStatus
            MAX-ACCESS read-create
            STATUS current
            DESCRIPTION
                "RowStatus."
            ::= { unisAclIPAclBasicEntry 2 }

        unisAclIPAclBasicAct OBJECT-TYPE
            SYNTAX RuleAction
            MAX-ACCESS read-create
            STATUS current
            DESCRIPTION
                "The action of basic acl rule."
            ::= { unisAclIPAclBasicEntry 3 }

        unisAclIPAclBasicSrcAddrType OBJECT-TYPE
            SYNTAX InetAddressType
            MAX-ACCESS read-create
            STATUS current
            DESCRIPTION
                "The IP addresses type of IP pool."
            ::= { unisAclIPAclBasicEntry 4 }

        unisAclIPAclBasicSrcAddr OBJECT-TYPE
            SYNTAX InetAddress
            MAX-ACCESS read-create
            STATUS current
            DESCRIPTION
                "The value of a local IP address is available for this association.

                 The type of this address is determined by the value of
                 unisAclIPAclBasicSrcAddrType.
                "
            ::= { unisAclIPAclBasicEntry 5 }

        unisAclIPAclBasicSrcPrefix OBJECT-TYPE
            SYNTAX InetAddressPrefixLength
            MAX-ACCESS read-create
            STATUS current
            DESCRIPTION
                "Denotes the length of a generic Internet network address prefix.
                 A value of n corresponds to an IP address mask
                 that has n contiguous 1-bits from the most significant bit (MSB)
                 and all other bits set to 0.
                "
            ::= { unisAclIPAclBasicEntry 6 }

        unisAclIPAclBasicSrcAny OBJECT-TYPE
            SYNTAX TruthValue
            MAX-ACCESS read-create
            STATUS current
            DESCRIPTION
                "The flag of matching any IP address."
            DEFVAL { true }
            ::= { unisAclIPAclBasicEntry 7 }

        unisAclIPAclBasicSrcWild OBJECT-TYPE
            SYNTAX IpAddress
            MAX-ACCESS read-create
            STATUS current
            DESCRIPTION
                "Source IPv4 address wildcard mask.
                 Only IPv4 Basic Rule supports this object.
                 Default value is '0.0.0.0'.
                "
            ::= { unisAclIPAclBasicEntry 8 }

        unisAclIPAclBasicTimeRangeName OBJECT-TYPE
            SYNTAX OCTET STRING (SIZE(0..32))
            MAX-ACCESS read-create
            STATUS current
            DESCRIPTION
                "The Time-range of basic acl rule.
                 Default value is zero-length.
                "
            ::= { unisAclIPAclBasicEntry 9 }

        unisAclIPAclBasicFragmentFlag OBJECT-TYPE
            SYNTAX FragmentFlag
            MAX-ACCESS read-create
            STATUS current
            DESCRIPTION
                "The flag of matching fragmented packets."
            DEFVAL { invalid }
            ::= { unisAclIPAclBasicEntry 10 }

        unisAclIPAclBasicLog OBJECT-TYPE
            SYNTAX TruthValue
            MAX-ACCESS read-create
            STATUS current
            DESCRIPTION
                "The packet will be logged when it matches the rule."
            DEFVAL { false }
            ::= { unisAclIPAclBasicEntry 11 }

        unisAclIPAclBasicCount OBJECT-TYPE
            SYNTAX Unsigned32
            MAX-ACCESS read-only
            STATUS current
            DESCRIPTION
                "The count of matches by the rule."
            ::= { unisAclIPAclBasicEntry 12 }

        unisAclIPAclBasicCountClear OBJECT-TYPE
            SYNTAX CounterClear
            MAX-ACCESS read-write
            STATUS current
            DESCRIPTION
                "Reset the value of counter."
            DEFVAL { nouse }
            ::= { unisAclIPAclBasicEntry 13 }

        unisAclIPAclBasicEnable OBJECT-TYPE
            SYNTAX TruthValue
            MAX-ACCESS read-only
            STATUS current
            DESCRIPTION
                "The rule is active or not.
                 true : active
                 false : inactive
                "
            DEFVAL { false }
            ::= { unisAclIPAclBasicEntry 14 }

        unisAclIPAclBasicVpnInstanceName OBJECT-TYPE
            SYNTAX OCTET STRING (SIZE(0..32))
            MAX-ACCESS read-create
            STATUS current
            DESCRIPTION
                "The VPN name, to which the rule will be applied.
                 Default value is zero-length.
                "
            ::= { unisAclIPAclBasicEntry 15 }

        unisAclIPAclBasicComment OBJECT-TYPE
            SYNTAX OCTET STRING (SIZE(0..127))
            MAX-ACCESS read-create
            STATUS current
            DESCRIPTION
                "The description of ACL rule.
                 Default value is Zero-length String.
                "
            ::= { unisAclIPAclBasicEntry 16 }

        unisAclIPAclBasicCounting OBJECT-TYPE
            SYNTAX TruthValue
            MAX-ACCESS read-create
            STATUS current
            DESCRIPTION
                "The packet will be counted when it matches the rule.
                 It is disabled by default.
                "
            DEFVAL { false }
            ::= { unisAclIPAclBasicEntry 17 }

        unisAclIPAclBasicRouteTypeAny OBJECT-TYPE
            SYNTAX TruthValue
            MAX-ACCESS read-create
            STATUS current
            DESCRIPTION
                "The flag of matching any type of routing header of IPv6 packet.
                "
            DEFVAL { false }
            ::= { unisAclIPAclBasicEntry 18 }

        unisAclIPAclBasicRouteTypeValue OBJECT-TYPE
            SYNTAX Integer32 (0..255|65535)
            MAX-ACCESS read-create
            STATUS current
            DESCRIPTION
                "Match specific type of routing header of IPv6 packet."
            DEFVAL { 65535 }
            ::= { unisAclIPAclBasicEntry 19 }

--
-- Notes of unisAclIPAclAdvancedTable
--
        unisAclIPAclAdvancedTable OBJECT-TYPE
            SYNTAX SEQUENCE OF UnisAclIPAclAdvancedEntry
            MAX-ACCESS not-accessible
            STATUS current
            DESCRIPTION
                "A table of advanced and simple acl group.
                 If some objects of this table are not supported by some products,
                 these objects can't be created, changed and applied.
                 Default value of these objects will be returned when they are read.
                "
            ::= { unisAclIPAclGroup 3 }

        unisAclIPAclAdvancedEntry OBJECT-TYPE
            SYNTAX UnisAclIPAclAdvancedEntry
            MAX-ACCESS not-accessible
            STATUS current
            DESCRIPTION
                "Advanced acl group information."
            INDEX { unisAclNumberGroupType,
                    unisAclNumberGroupIndex,
                    unisAclIPAclAdvancedRuleIndex
                  }
            ::= { unisAclIPAclAdvancedTable 1  }

        UnisAclIPAclAdvancedEntry ::=
            SEQUENCE
            {
                unisAclIPAclAdvancedRuleIndex
                    Integer32,
                unisAclIPAclAdvancedRowStatus
                    RowStatus,
                unisAclIPAclAdvancedAct
                    RuleAction,
                unisAclIPAclAdvancedProtocol
                    Integer32,
                unisAclIPAclAdvancedAddrFlag
                    AddressFlag,
                unisAclIPAclAdvancedSrcAddrType
                    InetAddressType,
                unisAclIPAclAdvancedSrcAddr
                    InetAddress,
                unisAclIPAclAdvancedSrcPrefix
                    InetAddressPrefixLength,
                unisAclIPAclAdvancedSrcAny
                    TruthValue,
                unisAclIPAclAdvancedSrcWild
                    IpAddress,
                unisAclIPAclAdvancedSrcOp
                    PortOp,
                unisAclIPAclAdvancedSrcPort1
                    Integer32,
                unisAclIPAclAdvancedSrcPort2
                    Integer32,
                unisAclIPAclAdvancedDestAddrType
                    InetAddressType,
                unisAclIPAclAdvancedDestAddr
                    InetAddress,
                unisAclIPAclAdvancedDestPrefix
                    InetAddressPrefixLength,
                unisAclIPAclAdvancedDestAny
                    TruthValue,
                unisAclIPAclAdvancedDestWild
                    IpAddress,
                unisAclIPAclAdvancedDestOp
                    PortOp,
                unisAclIPAclAdvancedDestPort1
                    Integer32,
                unisAclIPAclAdvancedDestPort2
                    Integer32,
                unisAclIPAclAdvancedIcmpType
                    Integer32,
                unisAclIPAclAdvancedIcmpCode
                    Integer32,
                unisAclIPAclAdvancedPrecedence
                    Integer32,
                unisAclIPAclAdvancedTos
                    Integer32,
                unisAclIPAclAdvancedDscp
                    DSCPValue,
                unisAclIPAclAdvancedTimeRangeName
                    OCTET STRING,
                unisAclIPAclAdvancedTCPFlag
                    TCPFlag,
                unisAclIPAclAdvancedFragmentFlag
                    FragmentFlag,
                unisAclIPAclAdvancedLog
                    TruthValue,
                unisAclIPAclAdvancedCount
                    Unsigned32,
                unisAclIPAclAdvancedCountClear
                    CounterClear,
                unisAclIPAclAdvancedEnable
                    TruthValue,
                unisAclIPAclAdvancedVpnInstanceName
                    OCTET STRING,
                unisAclIPAclAdvancedComment
                    OCTET STRING,
                unisAclIPAclAdvancedReflective
                    TruthValue,
                unisAclIPAclAdvancedCounting
                    TruthValue,
                unisAclIPAclAdvancedTCPFlagMask
                    BITS,
                unisAclIPAclAdvancedTCPFlagValue
                    BITS,
                unisAclIPAclAdvancedRouteTypeAny
                    TruthValue,
                unisAclIPAclAdvancedRouteTypeValue
                    Integer32,
                unisAclIPAclAdvancedFlowLabel
                    Unsigned32,
                unisAclIPAclAdvancedSrcSuffix
                    Unsigned32,
                unisAclIPAclAdvancedDestSuffix
                    Unsigned32
            }

        unisAclIPAclAdvancedRuleIndex OBJECT-TYPE
            SYNTAX Integer32 (0..65534)
            MAX-ACCESS not-accessible
            STATUS current
            DESCRIPTION
                "The rule index of advanced acl group.
                 As a Simple ACL group, the value of this object must be 0.
                 As an Advanced ACL group, the value of this object is ranging
                 from 0 to 65534.
                "
            ::= { unisAclIPAclAdvancedEntry 1 }

        unisAclIPAclAdvancedRowStatus OBJECT-TYPE
            SYNTAX RowStatus
            MAX-ACCESS read-create
            STATUS current
            DESCRIPTION
                "RowStatus."
            ::= { unisAclIPAclAdvancedEntry 2 }

        unisAclIPAclAdvancedAct OBJECT-TYPE
            SYNTAX RuleAction
            MAX-ACCESS read-create
            STATUS current
            DESCRIPTION
                "The action of advanced acl rule."
            ::= { unisAclIPAclAdvancedEntry 3 }

        unisAclIPAclAdvancedProtocol OBJECT-TYPE
            SYNTAX Integer32 (0..255)
            MAX-ACCESS read-create
            STATUS current
            DESCRIPTION
                "The protocol-type of advanced acl group.  0 indicates any IPv4 or
                IPv6 protocol.
                  <1-255>  Protocol number
                  gre      GRE tunneling(47)
                  icmp     Internet Control Message Protocol(1)
                  icmpv6   Internet Control Message Protocol6(58)
                  igmp     Internet Group Management Protocol(2)
                  ipinip   IP in IP tunneling(4)
                  ospf     OSPF routing protocol(89)
                  tcp      Transmission Control Protocol (6)
                  udp      User Datagram Protocol (17)
                  ipv6-ah  IPv6 Authentication Header(51)
                  ipv6-esp IPv6 Encapsulating Security Payload(50)
                "
            ::= { unisAclIPAclAdvancedEntry 4 }

        unisAclIPAclAdvancedAddrFlag OBJECT-TYPE
            SYNTAX AddressFlag
            MAX-ACCESS read-create
            STATUS current
            DESCRIPTION
                "Address flag to select address."
            DEFVAL { invalid }
            ::= { unisAclIPAclAdvancedEntry 5 }

        unisAclIPAclAdvancedSrcAddrType OBJECT-TYPE
            SYNTAX InetAddressType
            MAX-ACCESS read-create
            STATUS current
            DESCRIPTION
                "The IP addresses type of IP pool."
            ::= { unisAclIPAclAdvancedEntry 6 }

        unisAclIPAclAdvancedSrcAddr OBJECT-TYPE
            SYNTAX InetAddress
            MAX-ACCESS read-create
            STATUS current
            DESCRIPTION
                "The value of a local IP address available for this association.

                 The type of this address is determined by the value of
                 unisAclIPAclAdvancedSrcAddrType.
                "
            ::= { unisAclIPAclAdvancedEntry 7 }

        unisAclIPAclAdvancedSrcPrefix OBJECT-TYPE
            SYNTAX InetAddressPrefixLength
            MAX-ACCESS read-create
            STATUS current
            DESCRIPTION
                "Denotes the length of a generic Internet network address prefix.
                 A value of n corresponds to an IP address mask
                 which has n contiguous 1-bits from the most significant bit (MSB)
                 and all other bits set to 0.
                "
            ::= { unisAclIPAclAdvancedEntry 8 }

        unisAclIPAclAdvancedSrcAny OBJECT-TYPE
            SYNTAX TruthValue
            MAX-ACCESS read-create
            STATUS current
            DESCRIPTION
                "The flag of matching any IP address."
            DEFVAL { true }
            ::= { unisAclIPAclAdvancedEntry 9 }

        unisAclIPAclAdvancedSrcWild OBJECT-TYPE
            SYNTAX IpAddress
            MAX-ACCESS read-create
            STATUS current
            DESCRIPTION
                "Source IPv4 address wildcard mask.
                 Only IPv4 Advanced Rule supports this object.
                 Default value is '0.0.0.0'.
                "
            ::= { unisAclIPAclAdvancedEntry 10 }

        unisAclIPAclAdvancedSrcOp OBJECT-TYPE
            SYNTAX PortOp
            MAX-ACCESS read-create
            STATUS current
            DESCRIPTION
                "Source port operation symbol of advanced acl group."
            DEFVAL { invalid }
            ::= { unisAclIPAclAdvancedEntry 11 }

        unisAclIPAclAdvancedSrcPort1 OBJECT-TYPE
            SYNTAX Integer32 (0..65535)
            MAX-ACCESS read-create
            STATUS current
            DESCRIPTION
                "The fourth layer source port1."
            DEFVAL { 0 }
            ::= { unisAclIPAclAdvancedEntry 12 }

        unisAclIPAclAdvancedSrcPort2 OBJECT-TYPE
            SYNTAX Integer32 (0..65535)
            MAX-ACCESS read-create
            STATUS current
            DESCRIPTION
                "The fourth layer source port2."
            DEFVAL { 65535 }
            ::= { unisAclIPAclAdvancedEntry 13 }

        unisAclIPAclAdvancedDestAddrType OBJECT-TYPE
            SYNTAX InetAddressType
            MAX-ACCESS read-create
            STATUS current
            DESCRIPTION
                "The IP addresses type of IP pool."
            ::= { unisAclIPAclAdvancedEntry 14 }

        unisAclIPAclAdvancedDestAddr OBJECT-TYPE
            SYNTAX InetAddress
            MAX-ACCESS read-create
            STATUS current
            DESCRIPTION
                "The value of a local IP address available for this association.

                 The type of this address is determined by the value of
                 unisAclIPAclAdvancedDestAddrType.
                "
            ::= { unisAclIPAclAdvancedEntry 15 }

        unisAclIPAclAdvancedDestPrefix OBJECT-TYPE
            SYNTAX InetAddressPrefixLength
            MAX-ACCESS read-create
            STATUS current
            DESCRIPTION
                "Denotes the length of a generic Internet network address prefix.
                 A value of n corresponds to an IP address mask
                 which has n contiguous 1-bits from the most significant bit (MSB)
                 and all other bits set to 0.
                "
            ::= { unisAclIPAclAdvancedEntry 16 }

        unisAclIPAclAdvancedDestAny OBJECT-TYPE
            SYNTAX TruthValue
            MAX-ACCESS read-create
            STATUS current
            DESCRIPTION
                "The flag of matching any IP address."
            DEFVAL { true }
            ::= { unisAclIPAclAdvancedEntry 17 }

        unisAclIPAclAdvancedDestWild OBJECT-TYPE
            SYNTAX IpAddress
            MAX-ACCESS read-create
            STATUS current
            DESCRIPTION
                "Destination IPv4 address wildcard mask.
                 Only IPv4 Advanced Rule supports this object.
                 Default value is '0.0.0.0'.
                "
            ::= { unisAclIPAclAdvancedEntry 18 }

        unisAclIPAclAdvancedDestOp OBJECT-TYPE
            SYNTAX PortOp
            MAX-ACCESS read-create
            STATUS current
            DESCRIPTION
                "Destination port operation symbol of advanced acl group."
            DEFVAL { invalid }
            ::= { unisAclIPAclAdvancedEntry 19 }

        unisAclIPAclAdvancedDestPort1 OBJECT-TYPE
            SYNTAX Integer32 (0..65535)
            MAX-ACCESS read-create
            STATUS current
            DESCRIPTION
                "The fourth layer destination port1."
            DEFVAL { 0 }
            ::= { unisAclIPAclAdvancedEntry 20 }

        unisAclIPAclAdvancedDestPort2 OBJECT-TYPE
            SYNTAX Integer32 (0..65535)
            MAX-ACCESS read-create
            STATUS current
            DESCRIPTION
                "The fourth layer destination port2."
            DEFVAL { 65535 }
            ::= { unisAclIPAclAdvancedEntry 21 }

        unisAclIPAclAdvancedIcmpType OBJECT-TYPE
            SYNTAX Integer32 (0..255|65535)
            MAX-ACCESS read-create
            STATUS current
            DESCRIPTION
                "The type of ICMP packet."
            DEFVAL { 65535 }
            ::= { unisAclIPAclAdvancedEntry 22 }

        unisAclIPAclAdvancedIcmpCode OBJECT-TYPE
            SYNTAX Integer32 (0..255|65535)
            MAX-ACCESS read-create
            STATUS current
            DESCRIPTION
                "The code of ICMP packet."
            DEFVAL { 65535 }
            ::= { unisAclIPAclAdvancedEntry 23 }

        unisAclIPAclAdvancedPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7)
                "
            DEFVAL { 255 }
            ::= { unisAclIPAclAdvancedEntry 24 }

        unisAclIPAclAdvancedTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0)
                "
            DEFVAL { 255 }
            ::= { unisAclIPAclAdvancedEntry 25 }

        unisAclIPAclAdvancedDscp OBJECT-TYPE
            SYNTAX DSCPValue
            MAX-ACCESS read-create
            STATUS current
            DESCRIPTION
                "The value of DSCP of IP packet."
            DEFVAL { 255 }
            ::= { unisAclIPAclAdvancedEntry 26 }

        unisAclIPAclAdvancedTimeRangeName OBJECT-TYPE
            SYNTAX OCTET STRING (SIZE(0..32))
            MAX-ACCESS read-create
            STATUS current
            DESCRIPTION
                "The Time-range of advanced acl rule.
                 Default value is zero-length.
                "
            ::= { unisAclIPAclAdvancedEntry 27 }

        unisAclIPAclAdvancedTCPFlag OBJECT-TYPE
            SYNTAX TCPFlag
            MAX-ACCESS read-create
            STATUS current
            DESCRIPTION
                "The packet type of TCP protocol."
            DEFVAL { invalid }
            ::= { unisAclIPAclAdvancedEntry 28 }

        unisAclIPAclAdvancedFragmentFlag OBJECT-TYPE
            SYNTAX FragmentFlag
            MAX-ACCESS read-create
            STATUS current
            DESCRIPTION
                "The flag of matching fragmented packet,
                 and now support two value: 0 or 2."
            DEFVAL { invalid }
            ::= { unisAclIPAclAdvancedEntry 29 }

        unisAclIPAclAdvancedLog OBJECT-TYPE
            SYNTAX TruthValue
            MAX-ACCESS read-create
            STATUS current
            DESCRIPTION
                "Log matched packets."
            DEFVAL { false }
            ::= { unisAclIPAclAdvancedEntry 30 }

        unisAclIPAclAdvancedCount OBJECT-TYPE
            SYNTAX Unsigned32
            MAX-ACCESS read-only
            STATUS current
            DESCRIPTION
                "The count of matched by the rule."
            ::= { unisAclIPAclAdvancedEntry 31 }

        unisAclIPAclAdvancedCountClear OBJECT-TYPE
            SYNTAX CounterClear
            MAX-ACCESS read-write
            STATUS current
            DESCRIPTION
                "Reset the value of counter."
            DEFVAL { nouse }
            ::= { unisAclIPAclAdvancedEntry 32 }

        unisAclIPAclAdvancedEnable OBJECT-TYPE
            SYNTAX TruthValue
            MAX-ACCESS read-only
            STATUS current
            DESCRIPTION
                "The rule is active or not.
                 true : active
                 false : inactive
                "
            DEFVAL { false }
            ::= { unisAclIPAclAdvancedEntry 33 }

        unisAclIPAclAdvancedVpnInstanceName OBJECT-TYPE
            SYNTAX OCTET STRING (SIZE(0..32))
            MAX-ACCESS read-create
            STATUS current
            DESCRIPTION
                "The VPN name that the rule will be applied.
                 Default value is zero-length.
                "
            ::= { unisAclIPAclAdvancedEntry 34 }

        unisAclIPAclAdvancedComment OBJECT-TYPE
            SYNTAX OCTET STRING (SIZE(0..127))
            MAX-ACCESS read-create
            STATUS current
            DESCRIPTION
                "The description of ACL rule.
                 Default value is Zero-length String.
                "
            ::= { unisAclIPAclAdvancedEntry 35 }

        unisAclIPAclAdvancedReflective OBJECT-TYPE
            SYNTAX TruthValue
            MAX-ACCESS read-create
            STATUS current
            DESCRIPTION
                "The flag of reflective."
            ::= { unisAclIPAclAdvancedEntry 36 }

        unisAclIPAclAdvancedCounting OBJECT-TYPE
            SYNTAX TruthValue
            MAX-ACCESS read-create
            STATUS current
            DESCRIPTION
                "The packet will be counted when it matches the rule.
                 It is disabled by default.
                "
            DEFVAL { false }
            ::= { unisAclIPAclAdvancedEntry 37 }

        unisAclIPAclAdvancedTCPFlagMask OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Mask.  This is a bit-map of possible conditions.
                The various bit positions are:
                |0        |tcpack                 |
                |1        |tcpfin                 |
                |2        |tcppsh                 |
                |3        |tcprst                 |
                |4        |tcpsyn                 |
                |5        |tcpurg                 |
                "
            DEFVAL { { } }
            ::= { unisAclIPAclAdvancedEntry 38 }

        unisAclIPAclAdvancedTCPFlagValue OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Value.  This is a bit-map of possible conditions.
                The various bit positions are:
                |0        |tcpack                 |
                |1        |tcpfin                 |
                |2        |tcppsh                 |
                |3        |tcprst                 |
                |4        |tcpsyn                 |
                |5        |tcpurg                 |
                "
            DEFVAL { { } }
            ::= { unisAclIPAclAdvancedEntry 39 }

        unisAclIPAclAdvancedRouteTypeAny OBJECT-TYPE
            SYNTAX TruthValue
            MAX-ACCESS read-create
            STATUS current
            DESCRIPTION
                "The flag of matching any type of routing header of IPv6 packet.
                "
            DEFVAL { false }
            ::= { unisAclIPAclAdvancedEntry 40 }

        unisAclIPAclAdvancedRouteTypeValue OBJECT-TYPE
            SYNTAX Integer32 (0..255|65535)
            MAX-ACCESS read-create
            STATUS current
            DESCRIPTION
                "The type of routing header of IPv6 packet."
            DEFVAL { 65535 }
            ::= { unisAclIPAclAdvancedEntry 41 }

        unisAclIPAclAdvancedFlowLabel OBJECT-TYPE
            SYNTAX Unsigned32 (0..1048575|4294967295)
            MAX-ACCESS read-create
            STATUS current
            DESCRIPTION
                "The value of flow label of IPv6 packet header."
            DEFVAL { 4294967295 }
            ::= { unisAclIPAclAdvancedEntry 42 }

        unisAclIPAclAdvancedSrcSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { unisAclIPAclAdvancedEntry 43 }

        unisAclIPAclAdvancedDestSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { unisAclIPAclAdvancedEntry 44 }

--
--Nodes of unisAclIPAclNamedBscTable
--

        unisAclIPAclNamedBscTable OBJECT-TYPE
            SYNTAX SEQUENCE OF UnisAclIPAclNamedBscEntry
            MAX-ACCESS not-accessible
            STATUS current
            DESCRIPTION
                "A table of basic rule of named ACL.
                 The name of ACL group will be used as an index in this table,
                 which differs from the table unisAclIPAclBasicTable.
                 If some objects of this table are not supported by some
                 products, these objects can't be created, changed or applied.
                 Default value of these objects will be returned when they are
                 read.
                "
            ::= { unisAclIPAclGroup 4 }

        unisAclIPAclNamedBscEntry OBJECT-TYPE
            SYNTAX UnisAclIPAclNamedBscEntry
            MAX-ACCESS not-accessible
            STATUS current
            DESCRIPTION
                "Basic named ACL rule entry."
            INDEX
            {
                unisAclNumberGroupType,
                unisAclNamedGroupName,
                unisAclIPAclBasicRuleIndex
            }
            ::= { unisAclIPAclNamedBscTable 1 }

        UnisAclIPAclNamedBscEntry ::=
            SEQUENCE
            {
                unisAclIPAclNamedBscRowStatus
                    RowStatus,
                unisAclIPAclNamedBscAct
                    RuleAction,
                unisAclIPAclNamedBscSrcAddrType
                    InetAddressType,
                unisAclIPAclNamedBscSrcAddr
                    InetAddress,
                unisAclIPAclNamedBscSrcPrefix
                    InetAddressPrefixLength,
                unisAclIPAclNamedBscSrcAny
                    TruthValue,
                unisAclIPAclNamedBscSrcWild
                    IpAddress,
                unisAclIPAclNamedBscTRangeName
                    OCTET STRING,
                unisAclIPAclNamedBscFragmentFlag
                    FragmentFlag,
                unisAclIPAclNamedBscLog
                    TruthValue,
                unisAclIPAclNamedBscCount
                    Unsigned32,
                unisAclIPAclNamedBscCountClear
                    CounterClear,
                unisAclIPAclNamedBscEnable
                    TruthValue,
                unisAclIPAclNamedBscVpnInstName
                    OCTET STRING,
                unisAclIPAclNamedBscComment
                    OCTET STRING,
                unisAclIPAclNamedBscCounting
                    TruthValue,
                unisAclIPAclNamedBscRouteTypeAny
                    TruthValue,
                unisAclIPAclNamedBscRouteTypeValue
                    Integer32
            }

        unisAclIPAclNamedBscRowStatus OBJECT-TYPE
            SYNTAX RowStatus
            MAX-ACCESS read-create
            STATUS current
            DESCRIPTION
                "RowStatus."
            ::= { unisAclIPAclNamedBscEntry 1 }

        unisAclIPAclNamedBscAct OBJECT-TYPE
            SYNTAX RuleAction
            MAX-ACCESS read-create
            STATUS current
            DESCRIPTION
                "The action of basic ACL rule."
            ::= { unisAclIPAclNamedBscEntry 2 }

        unisAclIPAclNamedBscSrcAddrType OBJECT-TYPE
            SYNTAX InetAddressType
            MAX-ACCESS read-create
            STATUS current
            DESCRIPTION
                "The IP addresses type of IP pool."
            ::= { unisAclIPAclNamedBscEntry 3 }

        unisAclIPAclNamedBscSrcAddr OBJECT-TYPE
            SYNTAX InetAddress
            MAX-ACCESS read-create
            STATUS current
            DESCRIPTION
                "The specified source IP address.
                 The type of this address is determined by the value of
                 unisAclIPAclNamedBscSrcAddrType.
                "
            ::= { unisAclIPAclNamedBscEntry 4 }

        unisAclIPAclNamedBscSrcPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { unisAclIPAclNamedBscEntry 5 }

        unisAclIPAclNamedBscSrcAny OBJECT-TYPE
            SYNTAX TruthValue
            MAX-ACCESS read-create
            STATUS current
            DESCRIPTION
                "The flag of matching any source IP address."
            DEFVAL { true }
            ::= { unisAclIPAclNamedBscEntry 6 }

        unisAclIPAclNamedBscSrcWild OBJECT-TYPE
            SYNTAX IpAddress
            MAX-ACCESS read-create
            STATUS current
            DESCRIPTION
                "Source IPv4 address wildcard mask.
                 Only IPv4 Basic Rule supports this object.
                 Default value is '0.0.0.0'.
                "
            ::= { unisAclIPAclNamedBscEntry 7 }

       unisAclIPAclNamedBscTRangeName OBJECT-TYPE
            SYNTAX OCTET STRING (SIZE(0..32))
            MAX-ACCESS read-create
            STATUS current
            DESCRIPTION
                "The Time-range of basic acl rule.
                 Default value is zero-length.
                "
            ::= { unisAclIPAclNamedBscEntry 8 }

        unisAclIPAclNamedBscFragmentFlag OBJECT-TYPE
            SYNTAX FragmentFlag
            MAX-ACCESS read-create
            STATUS current
            DESCRIPTION
                "The flag of matching fragmented packets."
            DEFVAL { invalid }
            ::= { unisAclIPAclNamedBscEntry 9 }

        unisAclIPAclNamedBscLog OBJECT-TYPE
            SYNTAX TruthValue
            MAX-ACCESS read-create
            STATUS current
            DESCRIPTION
                "The packet will be logged when it matches the rule."
            DEFVAL { false }
            ::= { unisAclIPAclNamedBscEntry 10 }

        unisAclIPAclNamedBscCount OBJECT-TYPE
            SYNTAX Unsigned32
            MAX-ACCESS read-only
            STATUS current
            DESCRIPTION
                "The count of matches by the rule."
            ::= { unisAclIPAclNamedBscEntry 11 }

        unisAclIPAclNamedBscCountClear OBJECT-TYPE
            SYNTAX CounterClear
            MAX-ACCESS read-write
            STATUS current
            DESCRIPTION
                "Reset the statistics counter of the rule."
            DEFVAL { nouse }
            ::= { unisAclIPAclNamedBscEntry 12 }

        unisAclIPAclNamedBscEnable OBJECT-TYPE
            SYNTAX TruthValue
            MAX-ACCESS read-only
            STATUS current
            DESCRIPTION
                "The rule is active or not.
                 true : active
                 false : inactive
                "
            DEFVAL { false }
            ::= { unisAclIPAclNamedBscEntry 13 }

        unisAclIPAclNamedBscVpnInstName OBJECT-TYPE
            SYNTAX OCTET STRING (SIZE(0..32))
            MAX-ACCESS read-create
            STATUS current
            DESCRIPTION
                "The VPN name, to which the rule will be applied.
                 Default value is zero-length.
                "
            ::= { unisAclIPAclNamedBscEntry 14 }

        unisAclIPAclNamedBscComment OBJECT-TYPE
            SYNTAX OCTET STRING (SIZE(0..127))
            MAX-ACCESS read-create
            STATUS current
            DESCRIPTION
                "The description of ACL rule.
                 Default value is Zero-length String.
                "
            ::= { unisAclIPAclNamedBscEntry 15 }

        unisAclIPAclNamedBscCounting OBJECT-TYPE
            SYNTAX TruthValue
            MAX-ACCESS read-create
            STATUS current
            DESCRIPTION
                "The packet will be counted when it matches the rule.
                 It is disabled by default.
                "
            DEFVAL { false }
            ::= { unisAclIPAclNamedBscEntry 16 }

        unisAclIPAclNamedBscRouteTypeAny OBJECT-TYPE
            SYNTAX TruthValue
            MAX-ACCESS read-create
            STATUS current
            DESCRIPTION
                "The flag of matching any type of routing header of IPv6 packet.
                "
            DEFVAL { false }
            ::= { unisAclIPAclNamedBscEntry 17 }

        unisAclIPAclNamedBscRouteTypeValue OBJECT-TYPE
            SYNTAX Integer32 (0..255|65535)
            MAX-ACCESS read-create
            STATUS current
            DESCRIPTION
                "Value of the routing header type of IPv6 packet,
                in the range of 0 to 255.
                "
            DEFVAL { 65535 }
            ::= { unisAclIPAclNamedBscEntry 18 }

--
-- Notes of unisAclIPAclNamedAdvTable
--
        unisAclIPAclNamedAdvTable OBJECT-TYPE
            SYNTAX SEQUENCE OF UnisAclIPAclNamedAdvEntry
            MAX-ACCESS not-accessible
            STATUS current
            DESCRIPTION
                "A table of advanced rule of named ACL.
                 The name of ACL group will be used as an index in this table,
                 which differs from the table unisAclIPAclAdvancedTable.
                 If some objects of this table are not supported by some
                 products, these objects can't be created, changed or applied.
                 Default value of these objects will be returned when they are
                 read.
                "
            ::= { unisAclIPAclGroup 5 }

        unisAclIPAclNamedAdvEntry OBJECT-TYPE
            SYNTAX UnisAclIPAclNamedAdvEntry
            MAX-ACCESS not-accessible
            STATUS current
            DESCRIPTION
                "Advanced ACL rule information entry."
            INDEX
            {
                unisAclNumberGroupType,
                unisAclNamedGroupName,
                unisAclIPAclAdvancedRuleIndex
            }
            ::= { unisAclIPAclNamedAdvTable 1 }

        UnisAclIPAclNamedAdvEntry ::=
            SEQUENCE
            {
                unisAclIPAclNamedAdvRowStatus
                    RowStatus,
                unisAclIPAclNamedAdvAct
                    RuleAction,
                unisAclIPAclNamedAdvProtocol
                    Integer32,
                unisAclIPAclNamedAdvAddrFlag
                    AddressFlag,
                unisAclIPAclNamedAdvSrcAddrType
                    InetAddressType,
                unisAclIPAclNamedAdvSrcAddr
                    InetAddress,
                unisAclIPAclNamedAdvSrcPrefix
                    InetAddressPrefixLength,
                unisAclIPAclNamedAdvSrcAny
                    TruthValue,
                unisAclIPAclNamedAdvSrcWild
                    IpAddress,
                unisAclIPAclNamedAdvSrcOp
                    PortOp,
                unisAclIPAclNamedAdvSrcPort1
                    Integer32,
                unisAclIPAclNamedAdvSrcPort2
                    Integer32,
                unisAclIPAclNamedAdvDstAddrType
                    InetAddressType,
                unisAclIPAclNamedAdvDstAddr
                    InetAddress,
                unisAclIPAclNamedAdvDstPrefix
                    InetAddressPrefixLength,
                unisAclIPAclNamedAdvDstAny
                    TruthValue,
                unisAclIPAclNamedAdvDstWild
                    IpAddress,
                unisAclIPAclNamedAdvDstOp
                    PortOp,
                unisAclIPAclNamedAdvDstPort1
                    Integer32,
                unisAclIPAclNamedAdvDstPort2
                    Integer32,
                unisAclIPAclNamedAdvIcmpType
                    Integer32,
                unisAclIPAclNamedAdvIcmpCode
                    Integer32,
                unisAclIPAclNamedAdvPrecedence
                    Integer32,
                unisAclIPAclNamedAdvTos
                    Integer32,
                unisAclIPAclNamedAdvDscp
                    DSCPValue,
                unisAclIPAclNamedAdvTRangeName
                    OCTET STRING,
                unisAclIPAclNamedAdvTCPFlag
                    TCPFlag,
                unisAclIPAclNamedAdvFragmentFlag
                    FragmentFlag,
                unisAclIPAclNamedAdvLog
                    TruthValue,
                unisAclIPAclNamedAdvCount
                    Unsigned32,
                unisAclIPAclNamedAdvCountClear
                    CounterClear,
                unisAclIPAclNamedAdvEnable
                    TruthValue,
                unisAclIPAclNamedAdvVpnInstName
                    OCTET STRING,
                unisAclIPAclNamedAdvComment
                    OCTET STRING,
                unisAclIPAclNamedAdvReflective
                    TruthValue,
                unisAclIPAclNamedAdvCounting
                    TruthValue,
                unisAclIPAclNamedAdvTCPFlagMask
                    BITS,
                unisAclIPAclNamedAdvTCPFlagValue
                    BITS,
                unisAclIPAclNamedAdvRouteTypeAny
                    TruthValue,
                unisAclIPAclNamedAdvRouteTypeValue
                    Integer32,
                unisAclIPAclNamedAdvFlowLabel
                    Unsigned32,
                unisAclIPAclNamedAdvSrcSuffix
                    Unsigned32,
                unisAclIPAclNamedAdvDstSuffix
                    Unsigned32
            }

        unisAclIPAclNamedAdvRowStatus OBJECT-TYPE
            SYNTAX RowStatus
            MAX-ACCESS read-create
            STATUS current
            DESCRIPTION
                "RowStatus."
            ::= { unisAclIPAclNamedAdvEntry 1 }

        unisAclIPAclNamedAdvAct OBJECT-TYPE
            SYNTAX RuleAction
            MAX-ACCESS read-create
            STATUS current
            DESCRIPTION
                "The action of advanced ACL rule."
            ::= { unisAclIPAclNamedAdvEntry 2 }

        unisAclIPAclNamedAdvProtocol OBJECT-TYPE
            SYNTAX Integer32 (0..255)
            MAX-ACCESS read-create
            STATUS current
            DESCRIPTION
                "The protocol-type of advanced ACL rule.  0 indicates any IPv4 or
                IPv6 protocol.
                  <1-255>  Protocol number
                  gre      GRE tunneling(47)
                  icmp     Internet Control Message Protocol(1)
                  icmpv6   Internet Control Message Protocol6(58)
                  igmp     Internet Group Management Protocol(2)
                  ipinip   IP in IP tunneling(4)
                  ospf     OSPF routing protocol(89)
                  tcp      Transmission Control Protocol (6)
                  udp      User Datagram Protocol (17)
                  ipv6-ah  IPv6 Authentication Header(51)
                  ipv6-esp IPv6 Encapsulating Security Payload(50)
                "
            ::= { unisAclIPAclNamedAdvEntry 3 }

        unisAclIPAclNamedAdvAddrFlag OBJECT-TYPE
            SYNTAX AddressFlag
            MAX-ACCESS read-create
            STATUS current
            DESCRIPTION
                "Address flag to select address."
            DEFVAL { invalid }
            ::= { unisAclIPAclNamedAdvEntry 4 }

        unisAclIPAclNamedAdvSrcAddrType OBJECT-TYPE
            SYNTAX InetAddressType
            MAX-ACCESS read-create
            STATUS current
            DESCRIPTION
                "The type of source IP address.
                "
            ::= { unisAclIPAclNamedAdvEntry 5 }

        unisAclIPAclNamedAdvSrcAddr OBJECT-TYPE
            SYNTAX InetAddress
            MAX-ACCESS read-create
            STATUS current
            DESCRIPTION
                "The specified source IP address.
                 The type of this address is determined by the value of
                 unisAclIPAclNamedAdvSrcAddrType.
                "
            ::= { unisAclIPAclNamedAdvEntry 6 }

        unisAclIPAclNamedAdvSrcPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { unisAclIPAclNamedAdvEntry 7 }

        unisAclIPAclNamedAdvSrcAny OBJECT-TYPE
            SYNTAX TruthValue
            MAX-ACCESS read-create
            STATUS current
            DESCRIPTION
                "The flag of matching any IP address."
            DEFVAL { true }
            ::= { unisAclIPAclNamedAdvEntry 8 }

        unisAclIPAclNamedAdvSrcWild OBJECT-TYPE
            SYNTAX IpAddress
            MAX-ACCESS read-create
            STATUS current
            DESCRIPTION
                "Source IPv4 address wildcard mask.
                 Only IPv4 Advanced Rule supports this object.
                 Default value is '0.0.0.0'.
                "
            ::= { unisAclIPAclNamedAdvEntry 9 }

        unisAclIPAclNamedAdvSrcOp OBJECT-TYPE
            SYNTAX PortOp
            MAX-ACCESS read-create
            STATUS current
            DESCRIPTION
                "Source port operation symbol of advanced acl group."
            DEFVAL { invalid }
            ::= { unisAclIPAclNamedAdvEntry 10 }

        unisAclIPAclNamedAdvSrcPort1 OBJECT-TYPE
            SYNTAX Integer32 (0..65535)
            MAX-ACCESS read-create
            STATUS current
            DESCRIPTION
                "The fourth layer source port1."
            DEFVAL { 0 }
            ::= { unisAclIPAclNamedAdvEntry 11 }

        unisAclIPAclNamedAdvSrcPort2 OBJECT-TYPE
            SYNTAX Integer32 (0..65535)
            MAX-ACCESS read-create
            STATUS current
            DESCRIPTION
                "The fourth layer source port2."
            DEFVAL { 65535 }
            ::= { unisAclIPAclNamedAdvEntry 12 }

        unisAclIPAclNamedAdvDstAddrType OBJECT-TYPE
            SYNTAX InetAddressType
            MAX-ACCESS read-create
            STATUS current
            DESCRIPTION
                "The type of destination IP address.
                "
            ::= { unisAclIPAclNamedAdvEntry 13 }

        unisAclIPAclNamedAdvDstAddr OBJECT-TYPE
            SYNTAX InetAddress
            MAX-ACCESS read-create
            STATUS current
            DESCRIPTION
                "The specified destination IP address.
                 The type of this address is determined by the value of
                 unisAclIPAclNamedAdvDstAddrType.
                "
            ::= { unisAclIPAclNamedAdvEntry 14 }

        unisAclIPAclNamedAdvDstPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { unisAclIPAclNamedAdvEntry 15 }

        unisAclIPAclNamedAdvDstAny OBJECT-TYPE
            SYNTAX TruthValue
            MAX-ACCESS read-create
            STATUS current
            DESCRIPTION
                "The flag of matching any IP address."
            DEFVAL { true }
            ::= { unisAclIPAclNamedAdvEntry 16 }

        unisAclIPAclNamedAdvDstWild OBJECT-TYPE
            SYNTAX IpAddress
            MAX-ACCESS read-create
            STATUS current
            DESCRIPTION
                "Destination IPv4 address wildcard mask.
                 Only IPv4 Advanced Rule supports this object.
                 Default value is '0.0.0.0'.
                "
            ::= { unisAclIPAclNamedAdvEntry 17 }

        unisAclIPAclNamedAdvDstOp OBJECT-TYPE
            SYNTAX PortOp
            MAX-ACCESS read-create
            STATUS current
            DESCRIPTION
                "Destination port operation symbol of advanced acl group."
            DEFVAL { invalid }
            ::= { unisAclIPAclNamedAdvEntry 18 }

        unisAclIPAclNamedAdvDstPort1 OBJECT-TYPE
            SYNTAX Integer32 (0..65535)
            MAX-ACCESS read-create
            STATUS current
            DESCRIPTION
                "The fourth layer destination port1."
            DEFVAL { 0 }
            ::= { unisAclIPAclNamedAdvEntry 19 }

        unisAclIPAclNamedAdvDstPort2 OBJECT-TYPE
            SYNTAX Integer32 (0..65535)
            MAX-ACCESS read-create
            STATUS current
            DESCRIPTION
                "The fourth layer destination port2."
            DEFVAL { 65535 }
            ::= { unisAclIPAclNamedAdvEntry 20 }

        unisAclIPAclNamedAdvIcmpType OBJECT-TYPE
            SYNTAX Integer32 (0..255|65535)
            MAX-ACCESS read-create
            STATUS current
            DESCRIPTION
                "The type of ICMP packet."
            DEFVAL { 65535 }
            ::= { unisAclIPAclNamedAdvEntry 21 }

        unisAclIPAclNamedAdvIcmpCode OBJECT-TYPE
            SYNTAX Integer32 (0..255|65535)
            MAX-ACCESS read-create
            STATUS current
            DESCRIPTION
                "The code of ICMP packet."
            DEFVAL { 65535 }
            ::= { unisAclIPAclNamedAdvEntry 22 }

        unisAclIPAclNamedAdvPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7)
                "
            DEFVAL { 255 }
            ::= { unisAclIPAclNamedAdvEntry 23 }

        unisAclIPAclNamedAdvTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0)
                "
            DEFVAL { 255 }
            ::= { unisAclIPAclNamedAdvEntry 24 }

        unisAclIPAclNamedAdvDscp OBJECT-TYPE
            SYNTAX DSCPValue
            MAX-ACCESS read-create
            STATUS current
            DESCRIPTION
                "The value of DSCP of IP packet."
            DEFVAL { 255 }
            ::= { unisAclIPAclNamedAdvEntry 25 }

        unisAclIPAclNamedAdvTRangeName OBJECT-TYPE
            SYNTAX OCTET STRING (SIZE(0..32))
            MAX-ACCESS read-create
            STATUS current
            DESCRIPTION
                "The Time-range of advanced ACL rule.
                 Default value is zero-length.
                "
            ::= { unisAclIPAclNamedAdvEntry 26 }

        unisAclIPAclNamedAdvTCPFlag OBJECT-TYPE
            SYNTAX TCPFlag
            MAX-ACCESS read-create
            STATUS current
            DESCRIPTION
                "The packet type of TCP protocol."
            DEFVAL { invalid }
            ::= { unisAclIPAclNamedAdvEntry 27 }

        unisAclIPAclNamedAdvFragmentFlag OBJECT-TYPE
            SYNTAX FragmentFlag
            MAX-ACCESS read-create
            STATUS current
            DESCRIPTION
                "The flag of matching fragmented packet,
                 and now support two value: 0 or 2.
                "
            DEFVAL { invalid }
            ::= { unisAclIPAclNamedAdvEntry 28 }

        unisAclIPAclNamedAdvLog OBJECT-TYPE
            SYNTAX TruthValue
            MAX-ACCESS read-create
            STATUS current
            DESCRIPTION
                "Log matched packets."
            DEFVAL { false }
            ::= { unisAclIPAclNamedAdvEntry 29 }

        unisAclIPAclNamedAdvCount OBJECT-TYPE
            SYNTAX Unsigned32
            MAX-ACCESS read-only
            STATUS current
            DESCRIPTION
                "The count of matches by the rule."
            ::= { unisAclIPAclNamedAdvEntry 30 }

        unisAclIPAclNamedAdvCountClear OBJECT-TYPE
            SYNTAX CounterClear
            MAX-ACCESS read-write
            STATUS current
            DESCRIPTION
                "Reset the statistics counter of this rule."
            DEFVAL { nouse }
            ::= { unisAclIPAclNamedAdvEntry 31 }

        unisAclIPAclNamedAdvEnable OBJECT-TYPE
            SYNTAX TruthValue
            MAX-ACCESS read-only
            STATUS current
            DESCRIPTION
                "The rule is active or not.
                 true : active
                 false : inactive
                "
            DEFVAL { false }
            ::= { unisAclIPAclNamedAdvEntry 32 }

        unisAclIPAclNamedAdvVpnInstName OBJECT-TYPE
            SYNTAX OCTET STRING (SIZE(0..32))
            MAX-ACCESS read-create
            STATUS current
            DESCRIPTION
                "The VPN name to which the rule will be applied.
                 Default value is zero-length.
                "
            ::= { unisAclIPAclNamedAdvEntry 33 }

        unisAclIPAclNamedAdvComment OBJECT-TYPE
            SYNTAX OCTET STRING (SIZE(0..127))
            MAX-ACCESS read-create
            STATUS current
            DESCRIPTION
                "The description of ACL rule.
                 Default value is zero-length String.
                "
            ::= { unisAclIPAclNamedAdvEntry 34 }

        unisAclIPAclNamedAdvReflective OBJECT-TYPE
            SYNTAX TruthValue
            MAX-ACCESS read-create
            STATUS current
            DESCRIPTION
                "The flag of reflective."
            ::= { unisAclIPAclNamedAdvEntry 35 }

        unisAclIPAclNamedAdvCounting OBJECT-TYPE
            SYNTAX TruthValue
            MAX-ACCESS read-create
            STATUS current
            DESCRIPTION
                "The packet will be counted when it matches the rule.
                 It is disabled by default.
                "
            DEFVAL { false }
            ::= { unisAclIPAclNamedAdvEntry 36 }

        unisAclIPAclNamedAdvTCPFlagMask OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Mask.  This is a bit-map of possible conditions.
                The various bit positions are:
                |0        |tcpack                 |
                |1        |tcpfin                 |
                |2        |tcppsh                 |
                |3        |tcprst                 |
                |4        |tcpsyn                 |
                |5        |tcpurg                 |
                "
            ::= { unisAclIPAclNamedAdvEntry 37 }

        unisAclIPAclNamedAdvTCPFlagValue OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Value.  This is a bit-map of possible conditions.
                The various bit positions are:
                |0        |tcpack                 |
                |1        |tcpfin                 |
                |2        |tcppsh                 |
                |3        |tcprst                 |
                |4        |tcpsyn                 |
                |5        |tcpurg                 |
                "
            ::= { unisAclIPAclNamedAdvEntry 38 }

        unisAclIPAclNamedAdvRouteTypeAny OBJECT-TYPE
            SYNTAX TruthValue
            MAX-ACCESS read-create
            STATUS current
            DESCRIPTION
                "The flag of matching any type of routing header of IPv6 packet.
                "
            DEFVAL { false }
            ::= { unisAclIPAclNamedAdvEntry 39 }

        unisAclIPAclNamedAdvRouteTypeValue OBJECT-TYPE
            SYNTAX Integer32 (0..255|65535)
            MAX-ACCESS read-create
            STATUS current
            DESCRIPTION
                "The type of routing header of IPv6 packet."
            DEFVAL { 65535 }
            ::= { unisAclIPAclNamedAdvEntry 40 }

        unisAclIPAclNamedAdvFlowLabel OBJECT-TYPE
            SYNTAX Unsigned32 (0..1048575|4294967295)
            MAX-ACCESS read-create
            STATUS current
            DESCRIPTION
                "The value of flow label of IPv6 packet header."
            DEFVAL { 4294967295 }
            ::= { unisAclIPAclNamedAdvEntry 41 }

        unisAclIPAclNamedAdvSrcSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { unisAclIPAclNamedAdvEntry 42 }

        unisAclIPAclNamedAdvDstSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { unisAclIPAclNamedAdvEntry 43 }

--
-- Node of unisAclMACAclGroup
--
        unisAclMACAclGroup OBJECT IDENTIFIER ::= { unisAclMib2Objects 3 }
--
-- Nodes of unisAclMACTable
--
        unisAclMACTable OBJECT-TYPE
            SYNTAX SEQUENCE OF UnisAclMACEntry
            MAX-ACCESS not-accessible
            STATUS current
            DESCRIPTION
                "A table of MAC acl group.
                 If some objects of this table are not supported by some products,
                 these objects can't be created, changed or applied.
                 Default value of these objects will be returned when they are read.
                "
            ::= { unisAclMACAclGroup 1 }

        unisAclMACEntry OBJECT-TYPE
            SYNTAX UnisAclMACEntry
            MAX-ACCESS not-accessible
            STATUS current
            DESCRIPTION
                "MAC acl group information."
            INDEX
            {
                unisAclNumberGroupType,
                unisAclNumberGroupIndex,
                unisAclMACRuleIndex
            }
            ::= { unisAclMACTable 1 }

        UnisAclMACEntry ::=
            SEQUENCE
            {
                unisAclMACRuleIndex
                    Integer32,
                unisAclMACRowStatus
                    RowStatus,
                unisAclMACAct
                    RuleAction,
                unisAclMACTypeCode
                    OCTET STRING,
                unisAclMACTypeMask
                    OCTET STRING,
                unisAclMACSrcMac
                    MacAddress,
                unisAclMACSrcMacWild
                    MacAddress,
                unisAclMACDestMac
                    MacAddress,
                unisAclMACDestMacWild
                    MacAddress,
                unisAclMACLsapCode
                    OCTET STRING,
                unisAclMACLsapMask
                    OCTET STRING,
                unisAclMACCos
                    Integer32,
                unisAclMACTimeRangeName
                    OCTET STRING,
                unisAclMACCount
                    Unsigned32,
                unisAclMACCountClear
                    CounterClear,
                unisAclMACEnable
                    TruthValue,
                unisAclMACComment
                    OCTET STRING,
                unisAclMACLog
                    TruthValue,
                unisAclMACCounting
                    TruthValue
            }

        unisAclMACRuleIndex OBJECT-TYPE
            SYNTAX Integer32 (0..65534)
            MAX-ACCESS not-accessible
            STATUS current
            DESCRIPTION
                "The rule index of MAC-based acl group."
            ::= { unisAclMACEntry 1 }

        unisAclMACRowStatus OBJECT-TYPE
            SYNTAX RowStatus
            MAX-ACCESS read-create
            STATUS current
            DESCRIPTION
                "RowStatus."
            ::= { unisAclMACEntry 2 }

        unisAclMACAct OBJECT-TYPE
            SYNTAX RuleAction
            MAX-ACCESS read-create
            STATUS current
            DESCRIPTION
                "The action of MAC acl rule."
            ::= { unisAclMACEntry 3 }

        unisAclMACTypeCode OBJECT-TYPE
            SYNTAX OCTET STRING (SIZE(0..32))
            MAX-ACCESS read-create
            STATUS current
            DESCRIPTION
                "The type of protocol."
            REFERENCE
                "rfc894, rfc1010."
            ::= { unisAclMACEntry 4 }

        unisAclMACTypeMask OBJECT-TYPE
            SYNTAX OCTET STRING (SIZE(0..32))
            MAX-ACCESS read-create
            STATUS current
            DESCRIPTION
                "The mask of protocol."
            ::= { unisAclMACEntry 5 }

        unisAclMACSrcMac OBJECT-TYPE
            SYNTAX MacAddress
            MAX-ACCESS read-create
            STATUS current
            DESCRIPTION
                "Source MAC of MAC acl rule.
                 Default value is '00:00:00:00:00:00'.
                "
            ::= { unisAclMACEntry 6 }

        unisAclMACSrcMacWild OBJECT-TYPE
            SYNTAX MacAddress
            MAX-ACCESS read-create
            STATUS current
            DESCRIPTION
                "Source MAC wildzard of MAC acl rule.
                 Default value is '00:00:00:00:00:00'.
                "
            ::= { unisAclMACEntry 7 }

        unisAclMACDestMac OBJECT-TYPE
            SYNTAX MacAddress
            MAX-ACCESS read-create
            STATUS current
            DESCRIPTION
                "Destination MAC of MAC acl rule.
                 Default value is '00:00:00:00:00:00'.
                "
            ::= { unisAclMACEntry 8 }

        unisAclMACDestMacWild OBJECT-TYPE
            SYNTAX MacAddress
            MAX-ACCESS read-create
            STATUS current
            DESCRIPTION
                "Destination MAC wildzard of MAC acl rule.
                 Default value is '00:00:00:00:00:00'
                "
            ::= { unisAclMACEntry 9 }

        unisAclMACLsapCode OBJECT-TYPE
            SYNTAX OCTET STRING (SIZE(0..32))
            MAX-ACCESS read-create
            STATUS current
            DESCRIPTION
                "The type of LSAP."
            REFERENCE
                "ANSI/IEEE Std 802.3"
            ::= { unisAclMACEntry 10 }

        unisAclMACLsapMask OBJECT-TYPE
            SYNTAX OCTET STRING (SIZE(0..32))
            MAX-ACCESS read-create
            STATUS current
            DESCRIPTION
                "The mask of LSAP."
            ::= { unisAclMACEntry 11 }

        unisAclMACCos OBJECT-TYPE
            SYNTAX Integer32 (0..7 | 255)
            MAX-ACCESS read-create
            STATUS current
            DESCRIPTION
                "Vlan priority of MAC acl rule."
            DEFVAL { 255 }
            ::= { unisAclMACEntry 12 }

        unisAclMACTimeRangeName OBJECT-TYPE
            SYNTAX OCTET STRING (SIZE(0..32))
            MAX-ACCESS read-create
            STATUS current
            DESCRIPTION
                "The Time-range of MAC acl rule.
                 Default value is zero-length.
                "
            ::= { unisAclMACEntry 13 }

        unisAclMACCount OBJECT-TYPE
            SYNTAX Unsigned32
            MAX-ACCESS read-only
            STATUS current
            DESCRIPTION
                "The count of matched frames by the rule."
            ::= { unisAclMACEntry 14 }

        unisAclMACCountClear OBJECT-TYPE
            SYNTAX CounterClear
            MAX-ACCESS read-write
            STATUS current
            DESCRIPTION
                "Reset the value of counter."
            DEFVAL { nouse }
            ::= { unisAclMACEntry 15 }

        unisAclMACEnable OBJECT-TYPE
            SYNTAX TruthValue
            MAX-ACCESS read-only
            STATUS current
            DESCRIPTION
                "The rule is active or not.
                 true : active
                 false : inactive
                "
            DEFVAL { false }
            ::= { unisAclMACEntry 16 }

        unisAclMACComment OBJECT-TYPE
            SYNTAX OCTET STRING (SIZE(0..127))
            MAX-ACCESS read-create
            STATUS current
            DESCRIPTION
                "The description of ACL rule.
                 Default value is Zero-length String.
                "
            ::= { unisAclMACEntry 17 }

        unisAclMACLog OBJECT-TYPE
            SYNTAX TruthValue
            MAX-ACCESS read-create
            STATUS current
            DESCRIPTION
                "The packet will be logged when it matches the rule.
                 It is disabled by default.
                "
            DEFVAL { false }
            ::= { unisAclMACEntry 18 }

        unisAclMACCounting OBJECT-TYPE
            SYNTAX TruthValue
            MAX-ACCESS read-create
            STATUS current
            DESCRIPTION
                "The packet will be counted when it matches the rule.
                 It is disabled by default.
                "
            DEFVAL { false }
            ::= { unisAclMACEntry 19 }

--
-- Nodes of named MAC ACL group
--
        unisAclNamedMACTable OBJECT-TYPE
            SYNTAX SEQUENCE OF UnisAclNamedMACEntry
            MAX-ACCESS not-accessible
            STATUS current
            DESCRIPTION
                "A table of named MAC ACL rule.
                 The name of ACL group will be used as an index in this table,
                 which differs from the table unisAclMACTable.
                 If some objects of this table are not supported by some products,
                 these objects can't be created, changed or applied.
                 Default value of these objects will be returned when they are read.
                "
            ::= { unisAclMACAclGroup 2 }

        unisAclNamedMACEntry OBJECT-TYPE
            SYNTAX UnisAclNamedMACEntry
            MAX-ACCESS not-accessible
            STATUS current
            DESCRIPTION
                "MAC acl group information."
            INDEX
            {
                unisAclNumberGroupType,
                unisAclNamedGroupName,
                unisAclMACRuleIndex
            }
            ::= { unisAclNamedMACTable 1 }

        UnisAclNamedMACEntry ::=
            SEQUENCE
            {
                unisAclNamedMACRowStatus
                    RowStatus,
                unisAclNamedMACAct
                    RuleAction,
                unisAclNamedMACTypeCode
                    OCTET STRING,
                unisAclNamedMACTypeMask
                    OCTET STRING,
                unisAclNamedMACSrcMac
                    MacAddress,
                unisAclNamedMACSrcMacWild
                    MacAddress,
                unisAclNamedMACDstMac
                    MacAddress,
                unisAclNamedMACDstMacWild
                    MacAddress,
                unisAclNamedMACLsapCode
                    OCTET STRING,
                unisAclNamedMACLsapMask
                    OCTET STRING,
                unisAclNamedMACCos
                    Integer32,
                unisAclNamedMACTimeRangeName
                    OCTET STRING,
                unisAclNamedMACCount
                    Unsigned32,
                unisAclNamedMACCountClear
                    CounterClear,
                unisAclNamedMACEnable
                    TruthValue,
                unisAclNamedMACComment
                    OCTET STRING,
                unisAclNamedMACLog
                    TruthValue,
                unisAclNamedMACCounting
                    TruthValue
             }

        unisAclNamedMACRowStatus OBJECT-TYPE
            SYNTAX RowStatus
            MAX-ACCESS read-create
            STATUS current
            DESCRIPTION
                "RowStatus."
            ::= { unisAclNamedMACEntry 1 }

        unisAclNamedMACAct OBJECT-TYPE
            SYNTAX RuleAction
            MAX-ACCESS read-create
            STATUS current
            DESCRIPTION
                "The action of MAC ACL rule."
            ::= { unisAclNamedMACEntry 2 }

        unisAclNamedMACTypeCode OBJECT-TYPE
            SYNTAX OCTET STRING (SIZE(0..32))
            MAX-ACCESS read-create
            STATUS current
            DESCRIPTION
                "The type of protocol."
            REFERENCE
                "rfc894, rfc1010."
            ::= { unisAclNamedMACEntry 3 }

        unisAclNamedMACTypeMask OBJECT-TYPE
            SYNTAX OCTET STRING (SIZE(0..32))
            MAX-ACCESS read-create
            STATUS current
            DESCRIPTION
                "The mask of protocol."
            ::= { unisAclNamedMACEntry 4 }

        unisAclNamedMACSrcMac OBJECT-TYPE
            SYNTAX MacAddress
            MAX-ACCESS read-create
            STATUS current
            DESCRIPTION
                "Source MAC of MAC ACL rule.
                 Default value is '00:00:00:00:00:00'.
                "
            ::= { unisAclNamedMACEntry 5 }

        unisAclNamedMACSrcMacWild OBJECT-TYPE
            SYNTAX MacAddress
            MAX-ACCESS read-create
            STATUS current
            DESCRIPTION
                "Source MAC wildcard of MAC ACL rule.
                 Default value is '00:00:00:00:00:00'.
                "
            ::= { unisAclNamedMACEntry 6 }

        unisAclNamedMACDstMac OBJECT-TYPE
            SYNTAX MacAddress
            MAX-ACCESS read-create
            STATUS current
            DESCRIPTION
                "Destination MAC of MAC ACL rule.
                 Default value is '00:00:00:00:00:00'.
                "
            ::= { unisAclNamedMACEntry 7 }

        unisAclNamedMACDstMacWild OBJECT-TYPE
            SYNTAX MacAddress
            MAX-ACCESS read-create
            STATUS current
            DESCRIPTION
                "Destination MAC wildcard of MAC ACL rule.
                 Default value is '00:00:00:00:00:00'
                "
            ::= { unisAclNamedMACEntry 8 }

        unisAclNamedMACLsapCode OBJECT-TYPE
            SYNTAX OCTET STRING (SIZE(0..32))
            MAX-ACCESS read-create
            STATUS current
            DESCRIPTION
                "The type of LSAP."
            REFERENCE
                "ANSI/IEEE Std 802.3"
            ::= { unisAclNamedMACEntry 9 }

        unisAclNamedMACLsapMask OBJECT-TYPE
            SYNTAX OCTET STRING (SIZE(0..32))
            MAX-ACCESS read-create
            STATUS current
            DESCRIPTION
                "The mask of LSAP."
            ::= { unisAclNamedMACEntry 10 }

        unisAclNamedMACCos OBJECT-TYPE
            SYNTAX Integer32 (0..7 | 255)
            MAX-ACCESS read-create
            STATUS current
            DESCRIPTION
                "Vlan priority of MAC ACL rule."
            DEFVAL { 255 }
            ::= { unisAclNamedMACEntry 11 }

        unisAclNamedMACTimeRangeName OBJECT-TYPE
            SYNTAX OCTET STRING (SIZE(0..32))
            MAX-ACCESS read-create
            STATUS current
            DESCRIPTION
                "The time-range of MAC ACL rule.
                 Default value is zero-length.
                "
            ::= { unisAclNamedMACEntry 12 }

        unisAclNamedMACCount OBJECT-TYPE
            SYNTAX Unsigned32
            MAX-ACCESS read-only
            STATUS current
            DESCRIPTION
                "The count of matched frames by the rule."
            ::= { unisAclNamedMACEntry 13 }

        unisAclNamedMACCountClear OBJECT-TYPE
            SYNTAX CounterClear
            MAX-ACCESS read-write
            STATUS current
            DESCRIPTION
                "Reset the value of counter."
            DEFVAL { nouse }
            ::= { unisAclNamedMACEntry 14 }

        unisAclNamedMACEnable OBJECT-TYPE
            SYNTAX TruthValue
            MAX-ACCESS read-only
            STATUS current
            DESCRIPTION
                "The rule is active or not.
                 true : active
                 false : inactive
                "
            DEFVAL { false }
            ::= { unisAclNamedMACEntry 15 }

        unisAclNamedMACComment OBJECT-TYPE
            SYNTAX OCTET STRING (SIZE(0..127))
            MAX-ACCESS read-create
            STATUS current
            DESCRIPTION
                "The description of ACL rule.
                 Default value is Zero-length String.
                "
            ::= { unisAclNamedMACEntry 16 }

        unisAclNamedMACLog OBJECT-TYPE
            SYNTAX TruthValue
            MAX-ACCESS read-create
            STATUS current
            DESCRIPTION
                "The packet will be logged when it matches the rule.
                 It is disabled by default.
                "
            DEFVAL { false }
            ::= { unisAclNamedMACEntry 17 }

        unisAclNamedMACCounting OBJECT-TYPE
            SYNTAX TruthValue
            MAX-ACCESS read-create
            STATUS current
            DESCRIPTION
                "The packet will be counted when it matches the rule.
                 It is disabled by default.
                "
            DEFVAL { false }
            ::= { unisAclNamedMACEntry 18 }

--
-- Node of unisAclEnUserGroup
--
        unisAclEnUserAclGroup OBJECT IDENTIFIER ::= { unisAclMib2Objects 4 }
--
-- Nodes of unisAclEnUserTable
--
        unisAclEnUserTable OBJECT-TYPE
            SYNTAX SEQUENCE OF UnisAclEnUserEntry
            MAX-ACCESS not-accessible
            STATUS current
            DESCRIPTION
                "A table of user acl group information.
                 If some objects of this table are not supported by some products,
                 these objects can't be created, changed and applied.
                 Default value of these objects will be returned when they are read.
                "
            ::= { unisAclEnUserAclGroup 3 }

        unisAclEnUserEntry OBJECT-TYPE
            SYNTAX UnisAclEnUserEntry
            MAX-ACCESS not-accessible
            STATUS current
            DESCRIPTION
                "User defined acl group entry."
            INDEX { unisAclNumberGroupType,
                    unisAclNumberGroupIndex,
                    unisAclEnUserRuleIndex }
            ::= { unisAclEnUserTable 1 }

        UnisAclEnUserEntry ::=
            SEQUENCE
            {
                unisAclEnUserRuleIndex
                    Integer32,
                unisAclEnUserRowStatus
                    RowStatus,
                unisAclEnUserAct
                    RuleAction,
                unisAclEnUserStartString
                    OCTET STRING,
                unisAclEnUserL2String
                    OCTET STRING,
                unisAclEnUserMplsString
                    OCTET STRING,
                unisAclEnUserIPv4String
                    OCTET STRING,
                unisAclEnUserIPv6String
                    OCTET STRING,
                unisAclEnUserL4String
                    OCTET STRING,
                unisAclEnUserL5String
                    OCTET STRING,
                unisAclEnUserTimeRangeName
                    OCTET STRING,
                unisAclEnUserCount
                    Unsigned32,
                unisAclEnUserCountClear
                    CounterClear,
                unisAclEnUserEnable
                    TruthValue,
                unisAclEnUserComment
                    OCTET STRING,
                unisAclEnUserLog
                    TruthValue,
                unisAclEnUserCounting
                    TruthValue
             }

        unisAclEnUserRuleIndex OBJECT-TYPE
            SYNTAX Integer32 (0..65534)
            MAX-ACCESS not-accessible
            STATUS current
            DESCRIPTION
                "The subitem of the user acl."
            ::= { unisAclEnUserEntry 1 }

        unisAclEnUserRowStatus OBJECT-TYPE
            SYNTAX RowStatus
            MAX-ACCESS read-create
            STATUS current
            DESCRIPTION
                "RowStatus."
            ::= { unisAclEnUserEntry 2 }

        unisAclEnUserAct OBJECT-TYPE
            SYNTAX RuleAction
            MAX-ACCESS read-create
            STATUS current
            DESCRIPTION
                "The action of user defined acl rule."
            ::= { unisAclEnUserEntry 3 }

        unisAclEnUserStartString OBJECT-TYPE
            SYNTAX OCTET STRING (SIZE(0..255))
            MAX-ACCESS read-create
            STATUS current
            DESCRIPTION
                "The rule, matching packets, input like this:
                 'RuleOffset','RuleString','RuleMask'.

                 RuleOffset: The value of this object is defined by product and
                 it indicates the offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: 10,10af,ffff.

                 Default value is zero-length.
                "
            ::= { unisAclEnUserEntry 4 }

        unisAclEnUserL2String OBJECT-TYPE
            SYNTAX OCTET STRING (SIZE(0..255))
            MAX-ACCESS read-create
            STATUS current
            DESCRIPTION
                "The rule, matching layer 2 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 5 }

        unisAclEnUserMplsString OBJECT-TYPE
            SYNTAX OCTET STRING (SIZE(0..255))
            MAX-ACCESS read-create
            STATUS current
            DESCRIPTION
                "The rule, matching mpls packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 6 }

        unisAclEnUserIPv4String OBJECT-TYPE
            SYNTAX OCTET STRING (SIZE(0..255))
            MAX-ACCESS read-create
            STATUS current
            DESCRIPTION
                "The rule, matching IPv4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 7 }

        unisAclEnUserIPv6String OBJECT-TYPE
            SYNTAX OCTET STRING (SIZE(0..255))
            MAX-ACCESS read-create
            STATUS current
            DESCRIPTION
                "The rule, matching IPv6 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 8 }

        unisAclEnUserL4String OBJECT-TYPE
            SYNTAX OCTET STRING (SIZE(0..255))
            MAX-ACCESS read-create
            STATUS current
            DESCRIPTION
                "The rule, matching layer 4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 9 }

        unisAclEnUserL5String OBJECT-TYPE
            SYNTAX OCTET STRING (SIZE(0..255))
            MAX-ACCESS read-create
            STATUS current
            DESCRIPTION
                "The rule, matching layer 5 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclEnUserEntry 10 }

        unisAclEnUserTimeRangeName OBJECT-TYPE
            SYNTAX OCTET STRING (SIZE(0..32))
            MAX-ACCESS read-create
            STATUS current
            DESCRIPTION
                "The Time-range of user acl rule.
                 Default value is zero-length."
            ::= { unisAclEnUserEntry 11 }

        unisAclEnUserCount OBJECT-TYPE
            SYNTAX Unsigned32
            MAX-ACCESS read-only
            STATUS current
            DESCRIPTION
                "The count of matched by the rule."
            ::= { unisAclEnUserEntry 12 }

        unisAclEnUserCountClear OBJECT-TYPE
            SYNTAX CounterClear
            MAX-ACCESS read-write
            STATUS current
            DESCRIPTION
                "Reset the value of counter."
            ::= { unisAclEnUserEntry 13 }

        unisAclEnUserEnable OBJECT-TYPE
            SYNTAX TruthValue
            MAX-ACCESS read-only
            STATUS current
            DESCRIPTION
                "The rule is active or not.
                 true : active
                 false : inactive
                "
            DEFVAL { false }
            ::= { unisAclEnUserEntry 14 }

        unisAclEnUserComment OBJECT-TYPE
            SYNTAX OCTET STRING (SIZE(0..127))
            MAX-ACCESS read-create
            STATUS current
            DESCRIPTION
                "The description of ACL rule.
                 Default value is Zero-length String.
                "
            ::= { unisAclEnUserEntry 15 }

        unisAclEnUserLog OBJECT-TYPE
            SYNTAX TruthValue
            MAX-ACCESS read-create
            STATUS current
            DESCRIPTION
                "The packet will be logged when it matches the rule.
                 It is disabled by default.
                "
            DEFVAL { false }
            ::= { unisAclEnUserEntry 16 }

        unisAclEnUserCounting OBJECT-TYPE
            SYNTAX TruthValue
            MAX-ACCESS read-create
            STATUS current
            DESCRIPTION
                "The packet will be counted when it matches the rule.
                 It is disabled by default.
                "
            DEFVAL { false }
            ::= { unisAclEnUserEntry 17 }

--
-- Nodes of unisAclNamedUserTable
--
        unisAclNamedUserTable OBJECT-TYPE
            SYNTAX SEQUENCE OF UnisAclNamedUserEntry
            MAX-ACCESS not-accessible
            STATUS current
            DESCRIPTION
                "A table of named user acl rule.
                 The name of ACL group will be used as an index in this table,
                 which differs from the table unisAclEnUserTable.
                 If some objects of this table are not supported by some products,
                 these objects can't be created, changed and applied.
                 Default value of these objects will be returned when they are read.
                "
            ::= { unisAclEnUserAclGroup 4 }

        unisAclNamedUserEntry OBJECT-TYPE
            SYNTAX UnisAclNamedUserEntry
            MAX-ACCESS not-accessible
            STATUS current
            DESCRIPTION
                "User defined acl group entry."
            INDEX
            {
                unisAclNumberGroupType,
                unisAclNamedGroupName,
                unisAclEnUserRuleIndex
            }
            ::= { unisAclNamedUserTable 1 }

        UnisAclNamedUserEntry ::=
            SEQUENCE
            {
                unisAclNamedUserRowStatus
                    RowStatus,
                unisAclNamedUserAct
                    RuleAction,
                unisAclNamedUserStartString
                    OCTET STRING,
                unisAclNamedUserL2String
                    OCTET STRING,
                unisAclNamedUserMplsString
                    OCTET STRING,
                unisAclNamedUserIPv4String
                    OCTET STRING,
                unisAclNamedUserIPv6String
                    OCTET STRING,
                unisAclNamedUserL4String
                    OCTET STRING,
                unisAclNamedUserL5String
                    OCTET STRING,
                unisAclNamedUserTimeRangeName
                    OCTET STRING,
                unisAclNamedUserCount
                    Unsigned32,
                unisAclNamedUserCountClear
                    CounterClear,
                unisAclNamedUserEnable
                    TruthValue,
                unisAclNamedUserComment
                    OCTET STRING,
                unisAclNamedUserLog
                    TruthValue,
                unisAclNamedUserCounting
                    TruthValue
             }

        unisAclNamedUserRowStatus OBJECT-TYPE
            SYNTAX RowStatus
            MAX-ACCESS read-create
            STATUS current
            DESCRIPTION
                "RowStatus."
            ::= { unisAclNamedUserEntry 1 }

        unisAclNamedUserAct OBJECT-TYPE
            SYNTAX RuleAction
            MAX-ACCESS read-create
            STATUS current
            DESCRIPTION
                "The action of user defined acl rule."
            ::= { unisAclNamedUserEntry 2 }

        unisAclNamedUserStartString OBJECT-TYPE
            SYNTAX OCTET STRING (SIZE(0..255))
            MAX-ACCESS read-create
            STATUS current
            DESCRIPTION
                "The rule, matching packets, input like this:
                 'RuleOffset','RuleString','RuleMask'.

                 RuleOffset: The value of this object is defined by product and
                 it indicates the offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: 10,10af,ffff.

                 Default value is zero-length.
                "
            ::= { unisAclNamedUserEntry 3 }

        unisAclNamedUserL2String OBJECT-TYPE
            SYNTAX OCTET STRING (SIZE(0..255))
            MAX-ACCESS read-create
            STATUS current
            DESCRIPTION
                "The rule, matching layer 2 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 4 }

        unisAclNamedUserMplsString OBJECT-TYPE
            SYNTAX OCTET STRING (SIZE(0..255))
            MAX-ACCESS read-create
            STATUS current
            DESCRIPTION
                "The rule, matching mpls packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 5 }

        unisAclNamedUserIPv4String OBJECT-TYPE
            SYNTAX OCTET STRING (SIZE(0..255))
            MAX-ACCESS read-create
            STATUS current
            DESCRIPTION
                "The rule, matching IPv4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 6 }

        unisAclNamedUserIPv6String OBJECT-TYPE
            SYNTAX OCTET STRING (SIZE(0..255))
            MAX-ACCESS read-create
            STATUS current
            DESCRIPTION
                "The rule, matching IPv6 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 7 }

        unisAclNamedUserL4String OBJECT-TYPE
            SYNTAX OCTET STRING (SIZE(0..255))
            MAX-ACCESS read-create
            STATUS current
            DESCRIPTION
                "The rule, matching layer 4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 8 }

        unisAclNamedUserL5String OBJECT-TYPE
            SYNTAX OCTET STRING (SIZE(0..255))
            MAX-ACCESS read-create
            STATUS current
            DESCRIPTION
                "The rule, matching layer 5 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { unisAclNamedUserEntry 9 }

        unisAclNamedUserTimeRangeName OBJECT-TYPE
            SYNTAX OCTET STRING (SIZE(0..32))
            MAX-ACCESS read-create
            STATUS current
            DESCRIPTION
                "The Time-range of user acl rule.
                 Default value is zero-length."
            ::= { unisAclNamedUserEntry 10 }

        unisAclNamedUserCount OBJECT-TYPE
            SYNTAX Unsigned32
            MAX-ACCESS read-only
            STATUS current
            DESCRIPTION
                "The count of matched by the rule."
            ::= { unisAclNamedUserEntry 11 }

        unisAclNamedUserCountClear OBJECT-TYPE
            SYNTAX CounterClear
            MAX-ACCESS read-write
            STATUS current
            DESCRIPTION
                "Reset the value of counter."
            ::= { unisAclNamedUserEntry 12 }

        unisAclNamedUserEnable OBJECT-TYPE
            SYNTAX TruthValue
            MAX-ACCESS read-only
            STATUS current
            DESCRIPTION
                "The rule is active or not.
                 true : active
                 false : inactive
                "
            DEFVAL { false }
            ::= { unisAclNamedUserEntry 13 }

        unisAclNamedUserComment OBJECT-TYPE
            SYNTAX OCTET STRING (SIZE(0..127))
            MAX-ACCESS read-create
            STATUS current
            DESCRIPTION
                "The description of ACL rule.
                 Default value is Zero-length String.
                "
            ::= { unisAclNamedUserEntry 14 }

        unisAclNamedUserLog OBJECT-TYPE
            SYNTAX TruthValue
            MAX-ACCESS read-create
            STATUS current
            DESCRIPTION
                "The packet will be logged when it matches the rule.
                 It is disabled by default.
                "
            DEFVAL { false }
            ::= { unisAclNamedUserEntry 15 }

        unisAclNamedUserCounting OBJECT-TYPE
            SYNTAX TruthValue
            MAX-ACCESS read-create
            STATUS current
            DESCRIPTION
                "The packet will be counted when it matches the rule.
                 It is disabled by default.
                "
            DEFVAL { false }
            ::= { unisAclNamedUserEntry 16 }

--
-- Node of unisAclResourceGroup
--
        unisAclResourceGroup OBJECT IDENTIFIER ::= { unisAclMib2Objects 5 }
--
-- Nodes of unisAclResourceUsageTable
--
        unisAclResourceUsageTable OBJECT-TYPE
            SYNTAX SEQUENCE OF UnisAclResourceUsageEntry
            MAX-ACCESS not-accessible
            STATUS current
            DESCRIPTION
                "The table shows ACL resource usage information.  Support for
                resource types that are denoted by unisAclResourceType object
                varies with products.  If a type is not supported, the
                corresponding row for the type will not be instantiated
                in this table.
                "
            ::= { unisAclResourceGroup 1 }

        unisAclResourceUsageEntry OBJECT-TYPE
            SYNTAX UnisAclResourceUsageEntry
            MAX-ACCESS not-accessible
            STATUS current
            DESCRIPTION
                "Each row contains a brief description of the resource type,
                a port range associated with the chip, total, reserved, and
                configured amount of resource of this type, the percent of
                resource that has been allocated, and so on.
                "
            INDEX
            {
                unisAclResourceChassis,
                unisAclResourceSlot,
                unisAclResourceChip,
                unisAclResourceType
            }
            ::= { unisAclResourceUsageTable 1 }

        UnisAclResourceUsageEntry ::=
            SEQUENCE
            {
                unisAclResourceChassis
                    Unsigned32,
                unisAclResourceSlot
                    Unsigned32,
                unisAclResourceChip
                    Unsigned32,
                unisAclResourceType
                    Integer32,
                unisAclPortRange
                    OCTET STRING,
                unisAclResourceTotal
                    Unsigned32,
                unisAclResourceReserved
                    Unsigned32,
                unisAclResourceConfigured
                    Unsigned32,
                unisAclResourceUsagePercent
                    Unsigned32,
                unisAclResourceTypeDescription
                    OCTET STRING
            }

        unisAclResourceChassis OBJECT-TYPE
            SYNTAX Unsigned32
            MAX-ACCESS not-accessible
            STATUS current
            DESCRIPTION
                "The chassis number.  On a centralized or distributed device,
                the value for this node is always zero.
                "
            ::= { unisAclResourceUsageEntry 1 }

        unisAclResourceSlot OBJECT-TYPE
            SYNTAX Unsigned32
            MAX-ACCESS not-accessible
            STATUS current
            DESCRIPTION
                "The slot number.  On a centralized device, the value for
                this node is always zero."
            ::= { unisAclResourceUsageEntry 2 }

        unisAclResourceChip OBJECT-TYPE
            SYNTAX Unsigned32
            MAX-ACCESS not-accessible
            STATUS current
            DESCRIPTION
                "The chip number.  On a single chip device, the value for
                this node is always zero."
            ::= { unisAclResourceUsageEntry 3 }

        unisAclResourceType OBJECT-TYPE
            SYNTAX Integer32 (1..255)
            MAX-ACCESS not-accessible
            STATUS current
            DESCRIPTION
                "The resource type."
            ::= { unisAclResourceUsageEntry 4 }

        unisAclPortRange OBJECT-TYPE
            SYNTAX OCTET STRING (SIZE(0..255))
            MAX-ACCESS read-only
            STATUS current
            DESCRIPTION
                "The port range associated with the chip.  Commas are used to
                separate multiple port ranges, for example, Ethernet1/2 to
                Ethernet1/12, Ethernet1/31 to Ethernet1/48.
                "
            ::= { unisAclResourceUsageEntry 5 }

        unisAclResourceTotal OBJECT-TYPE
            SYNTAX Unsigned32
            MAX-ACCESS read-only
            STATUS current
            DESCRIPTION
                "Total TCAM entries of the resource type."
            ::= { unisAclResourceUsageEntry 6 }

        unisAclResourceReserved OBJECT-TYPE
            SYNTAX Unsigned32
            MAX-ACCESS read-only
            STATUS current
            DESCRIPTION
                "The amount of reserved TCAM entries of the resource type."
            ::= { unisAclResourceUsageEntry 7 }

        unisAclResourceConfigured OBJECT-TYPE
            SYNTAX Unsigned32
            MAX-ACCESS read-only
            STATUS current
            DESCRIPTION
                "The amount of configured TCAM entries of the resource type."
            ::= { unisAclResourceUsageEntry 8 }

        unisAclResourceUsagePercent OBJECT-TYPE
            SYNTAX Unsigned32
            MAX-ACCESS read-only
            STATUS current
            DESCRIPTION
                "The percent of TCAM entries that have been used for
                this resource type.
                "
            ::= { unisAclResourceUsageEntry 9 }

        unisAclResourceTypeDescription OBJECT-TYPE
            SYNTAX OCTET STRING (SIZE(0..31))
            MAX-ACCESS read-only
            STATUS current
            DESCRIPTION
                "The description of this resource type."
            ::= { unisAclResourceUsageEntry 10 }

--
-- Node of unisAclIntervalGroup
--
        unisAclIntervalGroup OBJECT IDENTIFIER ::= { unisAclMib2Objects 6 }
--
-- Nodes of unisAclIntervalTable
--
        unisAclIntervalTable OBJECT-TYPE
            SYNTAX SEQUENCE OF UnisAclIntervalEntry
            MAX-ACCESS not-accessible
            STATUS current
            DESCRIPTION
                "Log interval table."
            ::= { unisAclIntervalGroup 1 }

        unisAclIntervalEntry OBJECT-TYPE
            SYNTAX UnisAclIntervalEntry
            MAX-ACCESS not-accessible
            STATUS current
            DESCRIPTION
                "Log interval entry."
            INDEX
            {
                unisAclIntervalType
            }
            ::= { unisAclIntervalTable 1 }

        UnisAclIntervalEntry ::=
            SEQUENCE
            {
                unisAclIntervalType
                    INTEGER,
                unisAclIntervalValue
                    Integer32,
                unisAclIntervalRowStatus
                    RowStatus
            }

        unisAclIntervalType OBJECT-TYPE
            SYNTAX INTEGER
            {
                logging(1),
                trap(2)
            }
            MAX-ACCESS not-accessible
            STATUS current
            DESCRIPTION
                "The types of the interval specified for generating
                packet filtering logs or traps.
                "
            ::= { unisAclIntervalEntry 1 }

        unisAclIntervalValue OBJECT-TYPE
            SYNTAX Integer32 (5..1440)
            MAX-ACCESS read-create
            STATUS current
            DESCRIPTION
                "The value of interval.
                It must be a multiple of 5 and in the range of 5 to 1440.
                "
            ::= { unisAclIntervalEntry 2 }

        unisAclIntervalRowStatus OBJECT-TYPE
            SYNTAX RowStatus
            MAX-ACCESS read-create
            STATUS current
            DESCRIPTION
                "RowStatus."
            ::= { unisAclIntervalEntry 3 }

--
-- Node of unisAclPacketFilterObjects
--
        unisAclPacketFilterObjects OBJECT IDENTIFIER ::= { unisAcl 3 }

        unisPfilterScalarGroup OBJECT IDENTIFIER ::= { unisAclPacketFilterObjects 1 }

        unisPfilterDefaultAction OBJECT-TYPE
            SYNTAX INTEGER
            {
                permit(1),
                deny(2)
            }
            MAX-ACCESS read-write
            STATUS current
            DESCRIPTION
                "The default action of packet filter.
                By default, the packet filter permits packets that do not match
                any ACL rule to pass.
                "
            ::= { unisPfilterScalarGroup 1 }

        unisPfilterProcessingStatus OBJECT-TYPE
            SYNTAX INTEGER
            {
                processing(1),
                done(2)
            }
            MAX-ACCESS read-only
            STATUS current
            DESCRIPTION
                "This object shows the status of the system when applying packet
                filter.  It is forbidden to set or read in unisAclPacketFilterObjects
                MIB module when the value is processing.
                "
            ::= { unisPfilterScalarGroup 2 }

--
-- Nodes of unisPfilterApplyTable
--
        unisPfilterApplyTable OBJECT-TYPE
            SYNTAX SEQUENCE OF UnisPfilterApplyEntry
            MAX-ACCESS not-accessible
            STATUS current
            DESCRIPTION
                "A table of packet filter application.
                It's not supported to set default action on an entity,
                but supported to enable hardware count of default action
                on an entity.
                "
            ::= { unisAclPacketFilterObjects 2 }

        unisPfilterApplyEntry OBJECT-TYPE
            SYNTAX UnisPfilterApplyEntry
            MAX-ACCESS not-accessible
            STATUS current
            DESCRIPTION
                "Packet filter application information entry."
            INDEX
            {
                unisPfilterApplyObjType,
                unisPfilterApplyObjIndex,
                unisPfilterApplyDirection,
                unisPfilterApplyAclType,
                unisPfilterApplyAclIndex
            }
            ::= { unisPfilterApplyTable 1 }

        UnisPfilterApplyEntry ::=
        SEQUENCE
        {
            unisPfilterApplyObjType
                INTEGER,
            unisPfilterApplyObjIndex
                Integer32,
            unisPfilterApplyDirection
                DirectionType,
            unisPfilterApplyAclType
                INTEGER,
            unisPfilterApplyAclIndex
                Integer32,
            unisPfilterApplyHardCount
                TruthValue,
            unisPfilterApplySequence
                Unsigned32,
            unisPfilterApplyCountClear
                CounterClear,
            unisPfilterApplyRowStatus
                RowStatus
        }

        unisPfilterApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { unisPfilterApplyEntry 1 }

        unisPfilterApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { unisPfilterApplyEntry 2 }

        unisPfilterApplyDirection OBJECT-TYPE
            SYNTAX DirectionType
            MAX-ACCESS not-accessible
            STATUS current
            DESCRIPTION
                "The direction of packet filter application."
            ::= { unisPfilterApplyEntry 3 }

        unisPfilterApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { unisPfilterApplyEntry 4 }

        unisPfilterApplyAclIndex OBJECT-TYPE
            SYNTAX Integer32  (0|2000..5999)
            MAX-ACCESS not-accessible
            STATUS current
            DESCRIPTION
                "The ACL group index.
                Basic type: 2000..2999
                Advanced type: 3000..3999
                MAC type: 4000..4999
                User type: 5000..5999
                Default action type: 0
                "
            ::= { unisPfilterApplyEntry 5 }

        unisPfilterApplyHardCount OBJECT-TYPE
            SYNTAX TruthValue
            MAX-ACCESS read-create
            STATUS current
            DESCRIPTION
                "Hardware count flag.
                true: enable hardware count
                false: disable hardware count
                "
            DEFVAL { false }
            ::= { unisPfilterApplyEntry 6 }

        unisPfilterApplySequence OBJECT-TYPE
            SYNTAX Unsigned32
            MAX-ACCESS read-only
            STATUS current
            DESCRIPTION
                "The configure sequence of packet filter application."
            ::= { unisPfilterApplyEntry 7 }

        unisPfilterApplyCountClear OBJECT-TYPE
            SYNTAX CounterClear
            MAX-ACCESS read-write
            STATUS current
            DESCRIPTION
                "Clear the value of counters."
            ::= { unisPfilterApplyEntry 8 }

        unisPfilterApplyRowStatus OBJECT-TYPE
            SYNTAX RowStatus
            MAX-ACCESS read-create
            STATUS current
            DESCRIPTION
                "RowStatus."
            ::= { unisPfilterApplyEntry 9 }

--
-- Nodes of unisPfilterAclGroupRunInfoTable
--
        unisPfilterAclGroupRunInfoTable OBJECT-TYPE
            SYNTAX SEQUENCE OF UnisPfilterAclGroupRunInfoEntry
            MAX-ACCESS not-accessible
            STATUS current
            DESCRIPTION
                "A table of group running information of ACLs
                for packet filtering.  If hardware count function is not
                supported or not enabled to the packet filter application, the
                statistics entry will be zero.
                "
            ::= { unisAclPacketFilterObjects 3 }

        unisPfilterAclGroupRunInfoEntry OBJECT-TYPE
            SYNTAX UnisPfilterAclGroupRunInfoEntry
            MAX-ACCESS not-accessible
            STATUS current
            DESCRIPTION
                "ACL group running information entry for packet filtering."
            INDEX
            {
                unisPfilterRunApplyObjType,
                unisPfilterRunApplyObjIndex,
                unisPfilterRunApplyDirection,
                unisPfilterRunApplyAclType,
                unisPfilterRunApplyAclIndex
            }
            ::= { unisPfilterAclGroupRunInfoTable 1 }

        UnisPfilterAclGroupRunInfoEntry ::=
        SEQUENCE
        {
            unisPfilterRunApplyObjType
                INTEGER,
            unisPfilterRunApplyObjIndex
                Integer32,
            unisPfilterRunApplyDirection
                DirectionType,
            unisPfilterRunApplyAclType
                INTEGER,
            unisPfilterRunApplyAclIndex
                Integer32,
            unisPfilterAclGroupStatus
                INTEGER,
            unisPfilterAclGroupCountStatus
                INTEGER,
            unisPfilterAclGroupPermitPkts
                Counter64,
            unisPfilterAclGroupPermitBytes
                Counter64,
            unisPfilterAclGroupDenyPkts
                Counter64,
            unisPfilterAclGroupDenyBytes
                Counter64
        }

        unisPfilterRunApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { unisPfilterAclGroupRunInfoEntry 1 }

        unisPfilterRunApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { unisPfilterAclGroupRunInfoEntry 2 }

        unisPfilterRunApplyDirection OBJECT-TYPE
            SYNTAX DirectionType
            MAX-ACCESS not-accessible
            STATUS current
            DESCRIPTION
                "The direction of packet filter application."
            ::= { unisPfilterAclGroupRunInfoEntry 3 }

        unisPfilterRunApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { unisPfilterAclGroupRunInfoEntry 4 }

        unisPfilterRunApplyAclIndex OBJECT-TYPE
            SYNTAX Integer32  (1..3|2000..5999)
            MAX-ACCESS not-accessible
            STATUS current
            DESCRIPTION
                "The ACL group index.
                Basic type: 2000..2999
                Advanced type: 3000..3999
                MAC type: 4000..4999
                User type: 5000..5999
                MAC default action: 1
                IPv4 default action: 2
                IPv6 default action: 3
                "
            ::= { unisPfilterAclGroupRunInfoEntry 5 }

        unisPfilterAclGroupStatus OBJECT-TYPE
            SYNTAX INTEGER
            {
                success(1),
                failed(2),
                partialSuccess(3)
            }
            MAX-ACCESS read-only
            STATUS current
            DESCRIPTION
                "The status of ACL group applied.
                success: ACL applied successfully on all slots
                failed: failed to apply ACL on all slots
                partialSuccess: failed to apply ACL on some slots
                "
            ::= { unisPfilterAclGroupRunInfoEntry 6 }

        unisPfilterAclGroupCountStatus OBJECT-TYPE
            SYNTAX INTEGER
            {
                success(1),
                failed(2),
                partialSuccess(3)
            }
            MAX-ACCESS read-only
            STATUS current
            DESCRIPTION
                "The status of enabling hardware count.  If hardware count is
                not enabled, it returns success.
                success: enable hardware count successfully on all slots
                failed: failed to enable hardware count on all slots
                partialSuccess: failed to enable hardware count on some slots
                "
            ::= { unisPfilterAclGroupRunInfoEntry 7 }

        unisPfilterAclGroupPermitPkts OBJECT-TYPE
            SYNTAX Counter64
            MAX-ACCESS read-only
            STATUS current
            DESCRIPTION
                "The number of packets permitted."
            ::= { unisPfilterAclGroupRunInfoEntry 8 }

        unisPfilterAclGroupPermitBytes OBJECT-TYPE
            SYNTAX Counter64
            MAX-ACCESS read-only
            STATUS current
            DESCRIPTION
                "The number of bytes permitted."
            ::= { unisPfilterAclGroupRunInfoEntry 9 }

        unisPfilterAclGroupDenyPkts OBJECT-TYPE
            SYNTAX Counter64
            MAX-ACCESS read-only
            STATUS current
            DESCRIPTION
                "The number of packets denied."
            ::= { unisPfilterAclGroupRunInfoEntry 10 }

        unisPfilterAclGroupDenyBytes OBJECT-TYPE
            SYNTAX Counter64
            MAX-ACCESS read-only
            STATUS current
            DESCRIPTION
                "The number of bytes denied."
            ::= { unisPfilterAclGroupRunInfoEntry 11 }

--
-- Nodes of unisPfilterAclRuleRunInfoTable
--
        unisPfilterAclRuleRunInfoTable OBJECT-TYPE
            SYNTAX SEQUENCE OF UnisPfilterAclRuleRunInfoEntry
            MAX-ACCESS not-accessible
            STATUS current
            DESCRIPTION
                "A table of rule's running information of ACLs
                for packet filtering.  If hardware count function is not
                supported or not enabled to the packet filter application, the
                unisPfilterAclRuleMatchPackets and unisPfilterAclRuleMatchBytes
                will be zero.
                "
            ::= { unisAclPacketFilterObjects 4 }

        unisPfilterAclRuleRunInfoEntry OBJECT-TYPE
            SYNTAX UnisPfilterAclRuleRunInfoEntry
            MAX-ACCESS not-accessible
            STATUS current
            DESCRIPTION
                "ACL rule's running information entry."
            INDEX
            {
                unisPfilterRunApplyObjType,
                unisPfilterRunApplyObjIndex,
                unisPfilterRunApplyDirection,
                unisPfilterRunApplyAclType,
                unisPfilterRunApplyAclIndex,
                unisPfilterAclRuleIndex
            }
            ::= { unisPfilterAclRuleRunInfoTable 1 }

        UnisPfilterAclRuleRunInfoEntry ::=
        SEQUENCE
        {
            unisPfilterAclRuleIndex
                Integer32,
            unisPfilterAclRuleStatus
                INTEGER,
            unisPfilterAclRuleCountStatus
                INTEGER,
            unisPfilterAclRuleMatchPackets
                Counter64,
            unisPfilterAclRuleMatchBytes
                Counter64
        }

        unisPfilterAclRuleIndex OBJECT-TYPE
            SYNTAX Integer32 (0..65534)
            MAX-ACCESS not-accessible
            STATUS current
            DESCRIPTION
                "The ACL rule index."
            ::= { unisPfilterAclRuleRunInfoEntry 1 }

        unisPfilterAclRuleStatus OBJECT-TYPE
            SYNTAX INTEGER
            {
                success(1),
                failed(2),
                partialSuccess(3)
            }
            MAX-ACCESS read-only
            STATUS current
            DESCRIPTION
                "The status of rule application.
                success: rule applied successfully on all slots
                failed: failed to apply rule on all slots
                partialSuccess: failed to apply rule on some slots
                "
            ::= { unisPfilterAclRuleRunInfoEntry 2 }

        unisPfilterAclRuleCountStatus OBJECT-TYPE
            SYNTAX INTEGER
            {
                success(1),
                failed(2),
                partialSuccess(3)
            }
            MAX-ACCESS read-only
            STATUS current
            DESCRIPTION
                "The status of enabling rule's hardware count.
                If hardware count is not enabled, it returns success.
                success: enable hardware count successfully on all slots
                failed: failed to enable hardware count on all slots
                partialSuccess: failed to enable hardware count on some slots
                "
            ::= { unisPfilterAclRuleRunInfoEntry 3 }

        unisPfilterAclRuleMatchPackets OBJECT-TYPE
            SYNTAX Counter64
            MAX-ACCESS read-only
            STATUS current
            DESCRIPTION
                "The number of packets matched."
            ::= { unisPfilterAclRuleRunInfoEntry 4 }

       unisPfilterAclRuleMatchBytes OBJECT-TYPE
            SYNTAX Counter64
            MAX-ACCESS read-only
            STATUS current
            DESCRIPTION
                "The number of bytes matched."
            ::= { unisPfilterAclRuleRunInfoEntry 5 }

--
-- Nodes of unisPfilterStatisticSumTable
--
        unisPfilterStatisticSumTable OBJECT-TYPE
            SYNTAX SEQUENCE OF UnisPfilterStatisticSumEntry
            MAX-ACCESS not-accessible
            STATUS current
            DESCRIPTION
                "A table of ACL rule's sum statistics information,
                accumulated by all entity application on all slots.
                "
            ::= { unisAclPacketFilterObjects 5 }

        unisPfilterStatisticSumEntry OBJECT-TYPE
            SYNTAX UnisPfilterStatisticSumEntry
            MAX-ACCESS not-accessible
            STATUS current
            DESCRIPTION
                "ACL rule's sum statistics information entry."
            INDEX
            {
                unisPfilterSumDirection,
                unisPfilterSumAclType,
                unisPfilterSumAclIndex,
                unisPfilterSumRuleIndex
            }
            ::= { unisPfilterStatisticSumTable 1 }

        UnisPfilterStatisticSumEntry ::=
        SEQUENCE
        {
            unisPfilterSumDirection
                DirectionType,
            unisPfilterSumAclType
                INTEGER,
            unisPfilterSumAclIndex
                Integer32,
            unisPfilterSumRuleIndex
                Integer32,
            unisPfilterSumRuleMatchPackets
                Counter64,
            unisPfilterSumRuleMatchBytes
                Counter64
        }

        unisPfilterSumDirection OBJECT-TYPE
            SYNTAX DirectionType
            MAX-ACCESS not-accessible
            STATUS current
            DESCRIPTION
                "The direction of application."
            ::= { unisPfilterStatisticSumEntry 1 }

        unisPfilterSumAclType OBJECT-TYPE
            SYNTAX INTEGER
            {
                ipv4(1),
                ipv6(2),
                mac(3),
                user(4)
            }
            MAX-ACCESS not-accessible
            STATUS current
            DESCRIPTION
                "ACL type: IPv4, IPv6, MAC, and user."
            ::= { unisPfilterStatisticSumEntry 2 }

        unisPfilterSumAclIndex OBJECT-TYPE
            SYNTAX Integer32 (2000..5999)
            MAX-ACCESS not-accessible
            STATUS current
            DESCRIPTION
                "The ACL group index.
                Basic type: 2000..2999
                Advanced type: 3000..3999
                MAC type: 4000..4999
                User type: 5000..5999
                "
            ::= { unisPfilterStatisticSumEntry 3 }

        unisPfilterSumRuleIndex OBJECT-TYPE
            SYNTAX Integer32 (0..65534)
            MAX-ACCESS not-accessible
            STATUS current
            DESCRIPTION
                "The ACL rule index."
            ::= { unisPfilterStatisticSumEntry 4 }

        unisPfilterSumRuleMatchPackets OBJECT-TYPE
            SYNTAX Counter64
            MAX-ACCESS read-only
            STATUS current
            DESCRIPTION
                "The sum number of packets matched the ACL rule."
            ::= { unisPfilterStatisticSumEntry 5 }

        unisPfilterSumRuleMatchBytes OBJECT-TYPE
            SYNTAX Counter64
            MAX-ACCESS read-only
            STATUS current
            DESCRIPTION
                "The sum number of bytes matched the ACL rule."
            ::= { unisPfilterStatisticSumEntry 6 }

--
-- Nodes of unisPfilter2ApplyTable
--
        unisPfilter2ApplyTable OBJECT-TYPE
            SYNTAX SEQUENCE OF UnisPfilter2ApplyEntry
            MAX-ACCESS not-accessible
            STATUS current
            DESCRIPTION
                "A table of packet filter application.
                It's not supported to set default action on an entity,
                but supported to enable hardware count of default action
                on an entity.
                "
            ::= { unisAclPacketFilterObjects 6 }

        unisPfilter2ApplyEntry OBJECT-TYPE
            SYNTAX UnisPfilter2ApplyEntry
            MAX-ACCESS not-accessible
            STATUS current
            DESCRIPTION
                "Packet filter application information entry."
            INDEX
            {
                unisPfilter2ApplyObjType,
                unisPfilter2ApplyObjIndex,
                unisPfilter2ApplyDirection,
                unisPfilter2ApplyAclType,
                unisPfilter2ApplyAclIndex
            }
            ::= { unisPfilter2ApplyTable 1 }

        UnisPfilter2ApplyEntry ::=
        SEQUENCE
        {
            unisPfilter2ApplyObjType
                INTEGER,
            unisPfilter2ApplyObjIndex
                Integer32,
            unisPfilter2ApplyDirection
                DirectionType,
            unisPfilter2ApplyAclType
                INTEGER,
            unisPfilter2ApplyAclIndex
                OCTET STRING,
            unisPfilter2ApplyHardCount
                TruthValue,
            unisPfilter2ApplySequence
                Unsigned32,
            unisPfilter2ApplyCountClear
                CounterClear,
            unisPfilter2ApplyRowStatus
                RowStatus
        }

        unisPfilter2ApplyObjType OBJECT-TYPE
            SYNTAX INTEGER
            {
                interface(1),
                vlan(2),
                global(3)
            }
            MAX-ACCESS accessible-for-notify
            STATUS current
            DESCRIPTION
                "The object type of packet filter application.
                interface: Apply an ACL to the interface to filter packets.
                vlan: Apply an ACL to the VLAN to filter packets.
                global: Apply an ACL globally to filter packets.
                "
            ::= { unisPfilter2ApplyEntry 1 }

        unisPfilter2ApplyObjIndex OBJECT-TYPE
            SYNTAX Integer32 (0..2147483647)
            MAX-ACCESS accessible-for-notify
            STATUS current
            DESCRIPTION
                "The object ID of packet filter application.
                Interface: interface index, equal to ifIndex
                VLAN: VLAN ID, 1..4094
                Global: 0
                "
            ::= { unisPfilter2ApplyEntry 2 }

        unisPfilter2ApplyDirection OBJECT-TYPE
            SYNTAX DirectionType
            MAX-ACCESS accessible-for-notify
            STATUS current
            DESCRIPTION
                "The direction of packet filter application."
            ::= { unisPfilter2ApplyEntry 3 }

        unisPfilter2ApplyAclType OBJECT-TYPE
            SYNTAX INTEGER
            {
                ipv4(1),
                ipv6(2),
                default(3),
                mac(4),
                user(5)
            }
            MAX-ACCESS accessible-for-notify
            STATUS current
            DESCRIPTION
                "ACL Type: IPv4, IPv6, default action, MAC, and user.
                Take default action as a special ACL group.
                "
            ::= { unisPfilter2ApplyEntry 4 }

        unisPfilter2ApplyAclIndex OBJECT-TYPE
            SYNTAX OCTET STRING (SIZE(1..63))
            MAX-ACCESS accessible-for-notify
            STATUS current
            DESCRIPTION
                "The index of ACL group used by packet-filter.
                If the specified string comprises only digits, it is converted
                into a numerical sequence in decimal notation, and regarded as
                an ACL group index or a default action.  If the string is a
                character string beginning with an English letter, it is
                regarded as an ACL group name.

                Group index range and default action:
                    Basic type: 2000..2999
                    Advanced type: 3000..3999
                    MAC type: 4000..4999
                    User type: 5000..5999
                    Default action type: 0
                "
            ::= { unisPfilter2ApplyEntry 5 }

        unisPfilter2ApplyHardCount OBJECT-TYPE
            SYNTAX TruthValue
            MAX-ACCESS read-create
            STATUS current
            DESCRIPTION
                "Hardware count flag.
                true: enable hardware count
                false: disable hardware count
                "
            DEFVAL { false }
            ::= { unisPfilter2ApplyEntry 6 }

        unisPfilter2ApplySequence OBJECT-TYPE
            SYNTAX Unsigned32
            MAX-ACCESS read-only
            STATUS current
            DESCRIPTION
                "The configure sequence of packet filter application."
            ::= { unisPfilter2ApplyEntry 7 }

        unisPfilter2ApplyCountClear OBJECT-TYPE
            SYNTAX CounterClear
            MAX-ACCESS read-write
            STATUS current
            DESCRIPTION
                "Clear the value of counters."
            DEFVAL { nouse }
            ::= { unisPfilter2ApplyEntry 8 }

        unisPfilter2ApplyRowStatus OBJECT-TYPE
            SYNTAX RowStatus
            MAX-ACCESS read-create
            STATUS current
            DESCRIPTION
                "RowStatus."
            ::= { unisPfilter2ApplyEntry 9 }

--
-- Nodes of unisPfilter2AclGroupRunInfoTable
--
        unisPfilter2AclGroupRunInfoTable OBJECT-TYPE
            SYNTAX SEQUENCE OF UnisPfilter2AclGroupRunInfoEntry
            MAX-ACCESS not-accessible
            STATUS current
            DESCRIPTION
                "A table of group running information of ACLs
                for packet filtering.  If hardware count function is not
                supported or not enabled to the packet filter application, the
                statistics entry will be zero.
                "
            ::= { unisAclPacketFilterObjects 7 }

        unisPfilter2AclGroupRunInfoEntry OBJECT-TYPE
            SYNTAX UnisPfilter2AclGroupRunInfoEntry
            MAX-ACCESS not-accessible
            STATUS current
            DESCRIPTION
                "ACL group running information entry for packet filtering."
            INDEX
            {
                unisPfilter2RunApplyObjType,
                unisPfilter2RunApplyObjIndex,
                unisPfilter2RunApplyDirection,
                unisPfilter2RunApplyAclType,
                unisPfilter2RunApplyAclIndex
            }
            ::= { unisPfilter2AclGroupRunInfoTable 1 }

        UnisPfilter2AclGroupRunInfoEntry ::=
        SEQUENCE
        {
            unisPfilter2RunApplyObjType
                INTEGER,
            unisPfilter2RunApplyObjIndex
                Integer32,
            unisPfilter2RunApplyDirection
                DirectionType,
            unisPfilter2RunApplyAclType
                INTEGER,
            unisPfilter2RunApplyAclIndex
                OCTET STRING,
            unisPfilter2AclGroupStatus
                INTEGER,
            unisPfilter2AclGroupCountStatus
                INTEGER,
            unisPfilter2AclGroupPermitPkts
                Counter64,
            unisPfilter2AclGroupPermitBytes
                Counter64,
            unisPfilter2AclGroupDenyPkts
                Counter64,
            unisPfilter2AclGroupDenyBytes
                Counter64
        }

        unisPfilter2RunApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { unisPfilter2AclGroupRunInfoEntry 1 }

        unisPfilter2RunApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { unisPfilter2AclGroupRunInfoEntry 2 }

        unisPfilter2RunApplyDirection OBJECT-TYPE
            SYNTAX DirectionType
            MAX-ACCESS not-accessible
            STATUS current
            DESCRIPTION
                "The direction of packet filter application."
            ::= { unisPfilter2AclGroupRunInfoEntry 3 }

        unisPfilter2RunApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { unisPfilter2AclGroupRunInfoEntry 4 }

        unisPfilter2RunApplyAclIndex OBJECT-TYPE
            SYNTAX OCTET STRING (SIZE(1..63))
            MAX-ACCESS not-accessible
            STATUS current
            DESCRIPTION
                "The index of ACL group used by packet-filter.
                If the specified string comprises only digits, it is converted
                into a numerical sequence in decimal notation, and regarded as
                an ACL group index or a default action.  If the string is a
                character string beginning with an English letter, it is
                regarded as an ACL group name.

                Group index range and default action:
                    Basic type: 2000..2999
                    Advanced type: 3000..3999
                    MAC type: 4000..4999
                    User type: 5000..5999
                    MAC default action: 1
                    IPv4 default action: 2
                    IPv6 default action: 3
                "
            ::= { unisPfilter2AclGroupRunInfoEntry 5 }

        unisPfilter2AclGroupStatus OBJECT-TYPE
            SYNTAX INTEGER
            {
                success(1),
                failed(2),
                partialSuccess(3)
            }
            MAX-ACCESS read-only
            STATUS current
            DESCRIPTION
                "The status of ACL group applied.
                success: ACL applied successfully on all slots
                failed: failed to apply ACL on all slots
                partialSuccess: failed to apply ACL on some slots
                "
            ::= { unisPfilter2AclGroupRunInfoEntry 6 }

        unisPfilter2AclGroupCountStatus OBJECT-TYPE
            SYNTAX INTEGER
            {
                success(1),
                failed(2),
                partialSuccess(3)
            }
            MAX-ACCESS read-only
            STATUS current
            DESCRIPTION
                "The status of enabling hardware count.  If hardware count is
                not enabled, it returns success.
                success: enable hardware count successfully on all slots
                failed: failed to enable hardware count on all slots
                partialSuccess: failed to enable hardware count on some slots
                "
            ::= { unisPfilter2AclGroupRunInfoEntry 7 }

        unisPfilter2AclGroupPermitPkts OBJECT-TYPE
            SYNTAX Counter64
            MAX-ACCESS read-only
            STATUS current
            DESCRIPTION
                "The number of packets permitted."
            ::= { unisPfilter2AclGroupRunInfoEntry 8 }

        unisPfilter2AclGroupPermitBytes OBJECT-TYPE
            SYNTAX Counter64
            MAX-ACCESS read-only
            STATUS current
            DESCRIPTION
                "The number of bytes permitted."
            ::= { unisPfilter2AclGroupRunInfoEntry 9 }

        unisPfilter2AclGroupDenyPkts OBJECT-TYPE
            SYNTAX Counter64
            MAX-ACCESS read-only
            STATUS current
            DESCRIPTION
                "The number of packets denied."
            ::= { unisPfilter2AclGroupRunInfoEntry 10 }

        unisPfilter2AclGroupDenyBytes OBJECT-TYPE
            SYNTAX Counter64
            MAX-ACCESS read-only
            STATUS current
            DESCRIPTION
                "The number of bytes denied."
            ::= { unisPfilter2AclGroupRunInfoEntry 11 }

--
-- Nodes of unisPfilter2AclRuleRunInfoTable
--
        unisPfilter2AclRuleRunInfoTable OBJECT-TYPE
            SYNTAX SEQUENCE OF UnisPfilter2AclRuleRunInfoEntry
            MAX-ACCESS not-accessible
            STATUS current
            DESCRIPTION
                "A table of rule's running information of ACLs
                for packet filtering.  If hardware count function is not
                supported or not enabled to the packet filter application, the
                unisPfilter2AclRuleMatchPackets and unisPfilter2AclRuleMatchBytes
                will be zero.
                "
            ::= { unisAclPacketFilterObjects 8 }

        unisPfilter2AclRuleRunInfoEntry OBJECT-TYPE
            SYNTAX UnisPfilter2AclRuleRunInfoEntry
            MAX-ACCESS not-accessible
            STATUS current
            DESCRIPTION
                "ACL rule's running information entry."
            INDEX
            {
                unisPfilter2RunApplyObjType,
                unisPfilter2RunApplyObjIndex,
                unisPfilter2RunApplyDirection,
                unisPfilter2RunApplyAclType,
                unisPfilter2RunApplyAclIndex,
                unisPfilter2AclRuleIndex
            }
            ::= { unisPfilter2AclRuleRunInfoTable 1 }

        UnisPfilter2AclRuleRunInfoEntry ::=
        SEQUENCE
        {
            unisPfilter2AclRuleIndex
                Integer32,
            unisPfilter2AclRuleStatus
                INTEGER,
            unisPfilter2AclRuleCountStatus
                INTEGER,
            unisPfilter2AclRuleMatchPackets
                Counter64,
            unisPfilter2AclRuleMatchBytes
                Counter64
        }

        unisPfilter2AclRuleIndex OBJECT-TYPE
            SYNTAX Integer32 (0..65534)
            MAX-ACCESS accessible-for-notify
            STATUS current
            DESCRIPTION
                "The ACL rule index."
            ::= { unisPfilter2AclRuleRunInfoEntry 1 }

        unisPfilter2AclRuleStatus OBJECT-TYPE
            SYNTAX INTEGER
            {
                success(1),
                failed(2),
                partialSuccess(3)
            }
            MAX-ACCESS read-only
            STATUS current
            DESCRIPTION
                "The status of rule application.
                success: rule applied successfully on all slots
                failed: failed to apply rule on all slots
                partialSuccess: failed to apply rule on some slots
                "
            ::= { unisPfilter2AclRuleRunInfoEntry 2 }

        unisPfilter2AclRuleCountStatus OBJECT-TYPE
            SYNTAX INTEGER
            {
                success(1),
                failed(2),
                partialSuccess(3)
            }
            MAX-ACCESS read-only
            STATUS current
            DESCRIPTION
                "The status of enabling rule's hardware count.
                If hardware count is not enabled, it returns success.
                success: enable hardware count successfully on all slots
                failed: failed to enable hardware count on all slots
                partialSuccess: failed to enable hardware count on some slots
                "
            ::= { unisPfilter2AclRuleRunInfoEntry 3 }

        unisPfilter2AclRuleMatchPackets OBJECT-TYPE
            SYNTAX Counter64
            MAX-ACCESS read-only
            STATUS current
            DESCRIPTION
                "The number of packets matched."
            ::= { unisPfilter2AclRuleRunInfoEntry 4 }

       unisPfilter2AclRuleMatchBytes OBJECT-TYPE
            SYNTAX Counter64
            MAX-ACCESS read-only
            STATUS current
            DESCRIPTION
                "The number of bytes matched."
            ::= { unisPfilter2AclRuleRunInfoEntry 5 }

--
-- Nodes of unisPfilter2StatisticSumTable
--
        unisPfilter2StatisticSumTable OBJECT-TYPE
            SYNTAX SEQUENCE OF UnisPfilter2StatisticSumEntry
            MAX-ACCESS not-accessible
            STATUS current
            DESCRIPTION
                "A table of ACL rule's sum statistics information,
                accumulated by all entity application on all slots.
                "
            ::= { unisAclPacketFilterObjects 9 }

        unisPfilter2StatisticSumEntry OBJECT-TYPE
            SYNTAX UnisPfilter2StatisticSumEntry
            MAX-ACCESS not-accessible
            STATUS current
            DESCRIPTION
                "ACL rule's sum statistics information entry."
            INDEX
            {
                unisPfilter2SumDirection,
                unisPfilter2SumAclType,
                unisPfilter2SumAclIndex,
                unisPfilter2SumRuleIndex
            }
            ::= { unisPfilter2StatisticSumTable 1 }

        UnisPfilter2StatisticSumEntry ::=
        SEQUENCE
        {
            unisPfilter2SumDirection
                DirectionType,
            unisPfilter2SumAclType
                INTEGER,
            unisPfilter2SumAclIndex
                OCTET STRING,
            unisPfilter2SumRuleIndex
                Integer32,
            unisPfilter2SumRuleMatchPackets
                Counter64,
            unisPfilter2SumRuleMatchBytes
                Counter64
        }

        unisPfilter2SumDirection OBJECT-TYPE
            SYNTAX DirectionType
            MAX-ACCESS not-accessible
            STATUS current
            DESCRIPTION
                "The direction of application."
            ::= { unisPfilter2StatisticSumEntry 1 }

        unisPfilter2SumAclType OBJECT-TYPE
            SYNTAX INTEGER
            {
                ipv4(1),
                ipv6(2),
                mac(3),
                user(4)
            }
            MAX-ACCESS not-accessible
            STATUS current
            DESCRIPTION
                "ACL type: IPv4, IPv6, MAC, and user."
            ::= { unisPfilter2StatisticSumEntry 2 }

        unisPfilter2SumAclIndex OBJECT-TYPE
            SYNTAX OCTET STRING (SIZE(1..63))
            MAX-ACCESS not-accessible
            STATUS current
            DESCRIPTION
                "The index of ACL group used by packet-filter.
                If the specified string comprises only digits, it is converted
                into a numerical sequence in decimal notation, and regarded as
                an ACL group index.  If the string is a character string
                beginning with an English letter, it is regarded as an ACL
                group name.

                Group index range and default action:
                    Basic type: 2000..2999
                    Advanced type: 3000..3999
                    MAC type: 4000..4999
                    User type: 5000..5999
                "
            ::= { unisPfilter2StatisticSumEntry 3 }

        unisPfilter2SumRuleIndex OBJECT-TYPE
            SYNTAX Integer32 (0..65534)
            MAX-ACCESS not-accessible
            STATUS current
            DESCRIPTION
                "The ACL rule index."
            ::= { unisPfilter2StatisticSumEntry 4 }

        unisPfilter2SumRuleMatchPackets OBJECT-TYPE
            SYNTAX Counter64
            MAX-ACCESS read-only
            STATUS current
            DESCRIPTION
                "The sum number of packets matched the ACL rule."
            ::= { unisPfilter2StatisticSumEntry 5 }

        unisPfilter2SumRuleMatchBytes OBJECT-TYPE
            SYNTAX Counter64
            MAX-ACCESS read-only
            STATUS current
            DESCRIPTION
                "The sum number of bytes matched the ACL rule."
            ::= { unisPfilter2StatisticSumEntry 6 }

--
-- Nodes of unisPacketfilterTrapObjects
--

        unisAclPacketfilterTrapObjects OBJECT IDENTIFIER ::= { unisAcl 4 }

        unisPfilterInterface OBJECT-TYPE
            SYNTAX OCTET STRING
            MAX-ACCESS accessible-for-notify
            STATUS current
            DESCRIPTION
                "The interface which policy apply."
            ::= { unisAclPacketfilterTrapObjects 1 }

        unisPfilterDirection OBJECT-TYPE
            SYNTAX OCTET STRING (SIZE(0..255))
            MAX-ACCESS accessible-for-notify
            STATUS current
            DESCRIPTION
                "Inbound or outbound."
            ::= { unisAclPacketfilterTrapObjects 2 }

        unisPfilterACLNumber OBJECT-TYPE
            SYNTAX Integer32
            MAX-ACCESS accessible-for-notify
            STATUS current
            DESCRIPTION
                "ACL number."
            ::= { unisAclPacketfilterTrapObjects 3 }

        unisPfilterAction OBJECT-TYPE
            SYNTAX OCTET STRING (SIZE(0..255))
            MAX-ACCESS accessible-for-notify
            STATUS current
            DESCRIPTION
                "Permit or deny."
            ::= { unisAclPacketfilterTrapObjects 4 }

        unisMACfilterSourceMac OBJECT-TYPE
            SYNTAX OCTET STRING (SIZE(0..255))
            MAX-ACCESS accessible-for-notify
            STATUS current
            DESCRIPTION
                "Source MAC address."
            ::= { unisAclPacketfilterTrapObjects 5 }

        unisMACfilterDestinationMac OBJECT-TYPE
            SYNTAX OCTET STRING (SIZE(0..255))
            MAX-ACCESS accessible-for-notify
            STATUS current
            DESCRIPTION
                "Destination MAC address."
            ::= { unisAclPacketfilterTrapObjects 6 }

        unisPfilterPacketNumber OBJECT-TYPE
            SYNTAX Integer32
            MAX-ACCESS accessible-for-notify
            STATUS current
            DESCRIPTION
                "The number of packets permitted or denied by ACL."
            ::= { unisAclPacketfilterTrapObjects 7 }

        unisPfilterReceiveInterface OBJECT-TYPE
            SYNTAX OCTET STRING (SIZE(0..255))
            MAX-ACCESS accessible-for-notify
            STATUS current
            DESCRIPTION
                "The interface where packet come from."
            ::= { unisAclPacketfilterTrapObjects 8 }

        unisAclPacketIfName OBJECT-TYPE
            SYNTAX OCTET STRING (SIZE(0..255))
            MAX-ACCESS accessible-for-notify
            STATUS current
            DESCRIPTION
                "The name of the interface on which the packet is matched."
            ::= { unisAclPacketfilterTrapObjects 9 }

        unisAclPacketDirection OBJECT-TYPE
            SYNTAX DirectionType
            MAX-ACCESS accessible-for-notify
            STATUS current
            DESCRIPTION
                "The direction the packet is going."
            ::= { unisAclPacketfilterTrapObjects 10 }

        unisAclPacketBAGG OBJECT-TYPE
            SYNTAX Integer32 (0..2048)
            MAX-ACCESS accessible-for-notify
            STATUS current
            DESCRIPTION
                "The bridge-aggregation-interface ID the interface belongs to.
                "
            DEFVAL { 0 }
            ::= { unisAclPacketfilterTrapObjects 11 }

        unisAclPacketVlanID OBJECT-TYPE
            SYNTAX Integer32 (1..4094)
            MAX-ACCESS accessible-for-notify
            STATUS current
            DESCRIPTION
                "The vlan the interface belongs to."
            ::= { unisAclPacketfilterTrapObjects 12 }

        unisAclPacketSrcIP OBJECT-TYPE
            SYNTAX OCTET STRING (SIZE(0..255))
            MAX-ACCESS accessible-for-notify
            STATUS current
            DESCRIPTION
                "Source IP address of IPv4/IPv6 packet."
            ::= { unisAclPacketfilterTrapObjects 13 }

        unisAclPacketDstIP OBJECT-TYPE
            SYNTAX OCTET STRING (SIZE(0..255))
            MAX-ACCESS accessible-for-notify
            STATUS current
            DESCRIPTION
                "Destination IP address of IPv4/IPv6 packet."
            ::= { unisAclPacketfilterTrapObjects 14 }

        unisAclPacketProtocol  OBJECT-TYPE
            SYNTAX Integer32 (0..255)
            MAX-ACCESS accessible-for-notify
            STATUS current
            DESCRIPTION
                "The protocol of IPv4/IPv6 packet.
                icmp(1),
                tcp(6),
                udp(17),
                igmp(2),
                gre(47),
                ospf(89),
                ipinip(4),
                icmp6(58),
                ipv6_ah(51),
                ipv6_esp(50)
                "
            ::= { unisAclPacketfilterTrapObjects 15 }

        unisAclPacketDscp  OBJECT-TYPE
            SYNTAX DSCPValue
            MAX-ACCESS accessible-for-notify
            STATUS current
            DESCRIPTION
                "DSCP of IPv4/IPv6 packet."
            DEFVAL { 255 }
            ::= { unisAclPacketfilterTrapObjects 16 }

        unisAclPacketFlowLabel  OBJECT-TYPE
            SYNTAX Unsigned32   (0..1048575|4294967295)
            MAX-ACCESS accessible-for-notify
            STATUS current
            DESCRIPTION
                "Flow label value of IPv6 packet."
            DEFVAL { 4294967295 }
            ::= { unisAclPacketfilterTrapObjects 17 }

        unisAclPacketIcmpIgmpType  OBJECT-TYPE
            SYNTAX Integer32   (0..255|65535)
            MAX-ACCESS accessible-for-notify
            STATUS current
            DESCRIPTION
                "The type of ICMP or IGMP packet."
            DEFVAL { 65535 }
            ::= { unisAclPacketfilterTrapObjects 18 }

        unisAclPacketIcmpIgmpCode  OBJECT-TYPE
            SYNTAX Integer32   (0..255|65535)
            MAX-ACCESS accessible-for-notify
            STATUS current
            DESCRIPTION
                "The code of ICMP or IGMP packet."
            DEFVAL { 65535 }
            ::= { unisAclPacketfilterTrapObjects 19 }

        unisAclPacketTcpFlags  OBJECT-TYPE
            SYNTAX INTEGER
            {
                tcpack(1),
                tcpfin(2),
                tcppsh(3),
                tcprst(4),
                tcpsyn(5),
                tcpurg(6),
                invalid(255)
            }

            MAX-ACCESS accessible-for-notify
            STATUS current
            DESCRIPTION
                "The flags of TCP packet.
                tcpack(1),
                tcpfin(2),
                tcppsh(3),
                tcprst(4),
                tcpsyn(5),
                tcpurg(6),
                invalid(255)
                "
            DEFVAL { 255 }
            ::= { unisAclPacketfilterTrapObjects 20 }

        unisAclPacketSrcPort  OBJECT-TYPE
            SYNTAX Integer32 (0..65535)
            MAX-ACCESS accessible-for-notify
            STATUS current
            DESCRIPTION
                "Source port of TCP or UDP packet."
            DEFVAL { 0 }
            ::= { unisAclPacketfilterTrapObjects 21 }

        unisAclPacketDstPort  OBJECT-TYPE
            SYNTAX Integer32 (0..65535)
            MAX-ACCESS accessible-for-notify
            STATUS current
            DESCRIPTION
                "Destination port of TCP or UDP packet."
            DEFVAL { 65535 }
            ::= { unisAclPacketfilterTrapObjects 22 }

        unisAclPacketSrcMacAddr  OBJECT-TYPE
            SYNTAX MacAddress
            MAX-ACCESS accessible-for-notify
            STATUS current
            DESCRIPTION
                "Source MAC address of Ethernet packet."
            ::= { unisAclPacketfilterTrapObjects 23 }

        unisAclPacketDstMacAddr  OBJECT-TYPE
            SYNTAX MacAddress
            MAX-ACCESS accessible-for-notify
            STATUS current
            DESCRIPTION
                "Destination MAC address of Ethernet packet."
            ::= { unisAclPacketfilterTrapObjects 24 }

        unisAclPacketMacTypeLen  OBJECT-TYPE
            SYNTAX Integer32 (0..65535)
            MAX-ACCESS accessible-for-notify
            STATUS current
            DESCRIPTION
                "The Ethertype or 802.3 length of Ethernet packet."
            DEFVAL { 0 }
            ::= { unisAclPacketfilterTrapObjects 25 }

        unisAclPacketVlanPCP  OBJECT-TYPE
            SYNTAX  Integer32    (0..7|255)
            MAX-ACCESS accessible-for-notify
            STATUS current
            DESCRIPTION
                "802.1p priority code point of Ethernet packet."
            DEFVAL { 255 }
            ::= { unisAclPacketfilterTrapObjects 26 }

--
-- Nodes of unisPacketfilterTrap
--

        unisAclPacketfilterTrap OBJECT IDENTIFIER ::= { unisAcl 5 }

        unisPfilterTrapPrefix OBJECT IDENTIFIER ::= { unisAclPacketfilterTrap 0 }

        unisMACfilterTrap NOTIFICATION-TYPE
            OBJECTS
            {
                unisPfilterInterface,
                unisPfilterDirection,
                unisPfilterACLNumber,
                unisPfilterAction,
                unisMACfilterSourceMac,
                unisMACfilterDestinationMac,
                unisPfilterPacketNumber,
                unisPfilterReceiveInterface
            }
            STATUS current
            DESCRIPTION
                "This notification is generated when a packet was processed
                by MAC address filter, but not every packet will generate one
                notification, the same notification only generate once in 30
                seconds.
                "
            ::= { unisPfilterTrapPrefix 1 }

        unisAclRuleMatchCount NOTIFICATION-TYPE
            OBJECTS
            {
                unisPfilter2ApplyObjType,
                unisPfilter2ApplyObjIndex,
                unisPfilter2ApplyDirection,
                unisPfilter2ApplyAclType,
                unisPfilter2ApplyAclIndex,
                unisPfilter2AclRuleIndex,
                unisPfilter2AclRuleMatchPackets
            }
            STATUS current
            DESCRIPTION
                "This notification is generated periodically due to a timer.
                The interval of the timer is configured in unisAclIntervalTable.
                The notification details the entries about the packet-filter
                object, the matched ACL rule and the number of matching packets.
                "
            ::= { unisPfilterTrapPrefix 2 }

        unisAclFirstIPv4PktCaptured NOTIFICATION-TYPE
            OBJECTS
            {
                unisPfilter2ApplyAclIndex,
                unisPfilter2AclRuleIndex,
                unisAclPacketIfName,
                unisAclPacketDirection,
                unisAclPacketBAGG,
                unisAclPacketVlanID,
                unisAclPacketSrcIP,
                unisAclPacketDstIP,
                unisAclPacketProtocol,
                unisAclPacketDscp,
                unisAclPacketIcmpIgmpType,
                unisAclPacketIcmpIgmpCode,
                unisAclPacketTcpFlags,
                unisAclPacketSrcPort,
                unisAclPacketDstPort
            }
            STATUS current
            DESCRIPTION
                "This notification is generated immediately when the first
                packet of the matched IPv4 flow is captured.  Other packets
                of the matched flow won't be captured.
                "
            ::= { unisPfilterTrapPrefix 3 }

        unisAclFirstIPv6PktCaptured NOTIFICATION-TYPE
            OBJECTS
            {
                unisPfilter2ApplyAclIndex,
                unisPfilter2AclRuleIndex,
                unisAclPacketIfName,
                unisAclPacketDirection,
                unisAclPacketBAGG,
                unisAclPacketVlanID,
                unisAclPacketSrcIP,
                unisAclPacketDstIP,
                unisAclPacketProtocol,
                unisAclPacketDscp,
                unisAclPacketFlowLabel,
                unisAclPacketIcmpIgmpType,
                unisAclPacketIcmpIgmpCode,
                unisAclPacketTcpFlags,
                unisAclPacketSrcPort,
                unisAclPacketDstPort
            }
            STATUS current
            DESCRIPTION
                "This notification is generated immediately when the first
                packet of the matched IPv6 flow is captured.  Other packets
                of the matched flow won't be captured.
                "
            ::= { unisPfilterTrapPrefix 4 }

        unisAclFirstEthernetPktCaptured NOTIFICATION-TYPE
            OBJECTS
            {
                unisPfilter2ApplyAclIndex,
                unisPfilter2AclRuleIndex,
                unisAclPacketIfName,
                unisAclPacketDirection,
                unisAclPacketBAGG,
                unisAclPacketVlanID,
                unisAclPacketSrcMacAddr,
                unisAclPacketDstMacAddr,
                unisAclPacketMacTypeLen,
                unisAclPacketVlanPCP
            }
            STATUS current
            DESCRIPTION
                "This notification is generated immediately when the first
                packet of the matched Ethernet flow is captured.  Other packets
                of the matched flow won't be captured.
                "
            ::= { unisPfilterTrapPrefix 5 }

--
-- Nodes of unisAclTrapObjects
--

        unisAclTrapObjects OBJECT IDENTIFIER ::= { unisAcl 6 }

        unisAclResourceTypeName OBJECT-TYPE
            SYNTAX OCTET STRING (SIZE(1..255))
            MAX-ACCESS accessible-for-notify
            STATUS current
            DESCRIPTION
                "The name of TCAM resources."
            ::= { unisAclTrapObjects 1 }

        unisAclResourceUsage OBJECT-TYPE
            SYNTAX Integer32 (1..100)
            MAX-ACCESS accessible-for-notify
            STATUS current
            DESCRIPTION
                "The current usage of TCAM resources."
            ::= { unisAclTrapObjects 2 }

        unisAclResourceUsedEntries OBJECT-TYPE
            SYNTAX Integer32
            MAX-ACCESS accessible-for-notify
            STATUS current
            DESCRIPTION
                "The used number of entries on TCAM."
            ::= { unisAclTrapObjects 3 }

        unisAclResourceTotalEntries OBJECT-TYPE
            SYNTAX Integer32
            MAX-ACCESS accessible-for-notify
            STATUS current
            DESCRIPTION
                "The total number of entries on TCAM."
            ::= { unisAclTrapObjects 4 }

        unisAclResourceChassisID OBJECT-TYPE
            SYNTAX Integer32
            MAX-ACCESS accessible-for-notify
            STATUS current
            DESCRIPTION
                "The chassis number.  On a centralized or distributed device,
                 the value for this node is always zero."
            ::= { unisAclTrapObjects 5 }

       unisAclResourceSlotID OBJECT-TYPE
            SYNTAX Integer32
            MAX-ACCESS accessible-for-notify
            STATUS current
            DESCRIPTION
                "The slot number.  On a centralized device, the value for
                 this node is always zero."
            ::= { unisAclTrapObjects 6 }

--
-- Nodes of unisAclResourceTrap
--

        unisAclTrap OBJECT IDENTIFIER ::= { unisAcl 7 }

        unisAclTrapPrefix OBJECT IDENTIFIER ::= { unisAclTrap 0 }

        unisAclResourceTrap NOTIFICATION-TYPE
            OBJECTS
            {
                unisAclResourceTypeName,
                unisAclResourceUsage,
                unisAclResourceUsedEntries,
                unisAclResourceTotalEntries,
                unisAclMib2ResourceThreshold,
                unisAclResourceChassisID,
                unisAclResourceSlotID
            }
            STATUS current
            DESCRIPTION
                "This notification is generated when the number of entries on TCAM
                 becomes equal to or greater than a preset threshold level"
            ::= { unisAclTrapPrefix 1 }

END
