-- ==================================================================================
-- Copyright (c) 2020 Unisyue Technologies Co., Ltd.  All rights reserved.
--
-- Description: This file describes the MIB implementation of ndec
-- Reference:
-- Version: V1.6
-- History:
--  for V1.0
--      Add MODULE-IDENTITY to mib
--  V1.1 2004-9-9 lizhiyong
--      add unishipsNDECSAListTable,unishikeSATable,unishipsIKEPolicyTable,
--      unishipsStaticCryptomapTable,unishipsTransformNameSetTable,unishipsNDECLeaf,
--      modify unishipsNDECInfoTable,
--  V1.2 2004-9-14 lizhiyong
--      delete useless comments
--      modify the SYNTAX type of unishipsInPac,unishipsOutPac,unishipsInByte,unishipsOutByte
--      and unishipsDropPac from Gauge to Counter32.
--      delete the underscore character "_" which is note compliant with ASN.1
--      modify the whole file with SMIv2.
--  V1.3 2004-10-12 updated by gaolong
--      Remove variable value range from table SEQUENCE definition.
--  V1.4 2004-10-21 lizhiyong
--      modify unishipsStaticCryptomapMatchAddr range from 1..199 to 1..100000.
--      update the description of unishipsNDECBackup node
--  V1.5 2004-11-26 updated by gaolong
--      File description updated
--  V1.6 2007-1-29 updated by liukan
--      Add a new value ealgXNsa in unishipsEncAlgorithm type.
-- ===================================================================================
UNIS-NDEC-MIB DEFINITIONS ::= BEGIN

IMPORTS
    IpAddress, Counter32, Gauge32, Integer32 ,Unsigned32 ,NOTIFICATION-TYPE,MODULE-IDENTITY,OBJECT-TYPE
        FROM SNMPv2-SMI
    DisplayString, TruthValue
        FROM SNMPv2-TC
    unismlsr
        FROM UNIS-OID-MIB;

--  UNIS-NDEC-MIB definition


        unisNDEC MODULE-IDENTITY
            LAST-UPDATED "200409150000Z"        -- August 15, 2004  GMT
            ORGANIZATION
                "Unisyue Technologies Co., Ltd."
            CONTACT-INFO
                ""
            DESCRIPTION
                "This MIB contains objects to manage the NDEC device.
                "
            REVISION "200409151052Z"        -- August 15, 2004 at 10:52 GMT
            DESCRIPTION
                "The initial version of this MIB module"
            ::= { unismlsr 2 }

--transform         Set authentication/encryption method


unishipsNDECSAListTable OBJECT-TYPE
    SYNTAX SEQUENCE OF UnisHipsNDECSAListEntry
    MAX-ACCESS not-accessible
    STATUS current
    DESCRIPTION
        "The table containing the list of all
        SA entries configured on NDEC by the operator."
    ::= { unisNDEC 1 }

unishipsNDECSAListEntry OBJECT-TYPE
    SYNTAX UnisHipsNDECSAListEntry
    MAX-ACCESS not-accessible
    STATUS current
    DESCRIPTION
        "Each entry contains the attributes
        associated with a single NDEC'S SA entry."
    INDEX { unishipsPeerIpAddr, unishipsProtocol, unishipsSPI  }
    ::= { unishipsNDECSAListTable 1 }

UnisHipsNDECSAListEntry ::= SEQUENCE {
    unishipsPeerIpAddr      IpAddress,
    unishipsProtocol        INTEGER,
    unishipsSPI             Gauge32,
    unishipsEncAlgorithm        INTEGER,
    unishipsAuthAlgorithm       INTEGER,
    unishipsLocalIpAddr         IpAddress,
    unishipsSaLifeKBytes        Gauge32,
    unishipsSaLifeSecond        Gauge32,
    unishipsByCard          TruthValue,
    unishipsNegotiateSaMode     INTEGER,
    unishipsExpBytes        Gauge32,
    unishipsSoftBytes       Gauge32,
    unishipsExpTimeout      Gauge32,
    unishipsSoftTimeout         Gauge32
    }


unishipsPeerIpAddr OBJECT-TYPE
    SYNTAX IpAddress
    MAX-ACCESS read-only
    STATUS current
    DESCRIPTION
        "The peer IP address of this SA entry.
        "
    ::= { unishipsNDECSAListEntry 1 }

unishipsProtocol OBJECT-TYPE
      SYNTAX INTEGER {
          ipsecEsp(50),
          ipsecAh(51)
      }
    MAX-ACCESS read-only
    STATUS current
    DESCRIPTION
        "The Protocol of this SA entry.
        "
    ::= { unishipsNDECSAListEntry 2 }

unishipsSPI OBJECT-TYPE
    SYNTAX Gauge32(256..4294967295)
    MAX-ACCESS read-only
    STATUS current
    DESCRIPTION
        "The SPI of this SA entry.
        "
    ::= { unishipsNDECSAListEntry 3 }

unishipsEncAlgorithm OBJECT-TYPE
    SYNTAX INTEGER {
        ealgNone(1),
        ealgDescbc(2),
        ealg3desCbc(3),
        ealgXBlf(4),
        ealgXCast(5),
        ealgXSkipjack(6),
        ealgXAes(7),
        ealgXQc5(8),
        ealgXNsa(9)
    }

    MAX-ACCESS read-only
    STATUS current
    DESCRIPTION
        "The encrypt algorithm of this SA entry.
        "
    ::= { unishipsNDECSAListEntry 4 }

unishipsAuthAlgorithm OBJECT-TYPE
    SYNTAX INTEGER {
        aalgNone(1),
        aalgMd5Hmac(2),
        aalgSha1Hmac(3),
        aalgMd5Hmac96(4),
        aalgSha1Hmac96(5),
        aalgXRipeMd160Hmac96(6),
        aalgXMd5(7),
        aalgXSha1(8)
       }
    MAX-ACCESS read-only
    STATUS current
    DESCRIPTION
        "The authentication algorithm of this SA entry.
        "
    ::= { unishipsNDECSAListEntry 5 }

unishipsLocalIpAddr OBJECT-TYPE
    SYNTAX IpAddress
    MAX-ACCESS read-only
    STATUS current
    DESCRIPTION
        "The local IP address of this SA entry.
        "
    ::= { unishipsNDECSAListEntry 6 }

unishipsSaLifeKBytes OBJECT-TYPE
    SYNTAX Gauge32
    MAX-ACCESS read-only
    STATUS current
    DESCRIPTION
        "The lifetime of this SA entry in bytes.
        "
    ::= { unishipsNDECSAListEntry 7 }

unishipsSaLifeSecond OBJECT-TYPE
    SYNTAX Gauge32
    MAX-ACCESS read-only
    STATUS current
    DESCRIPTION
        "The lifetime of this SA entry in seconds.
        "
    ::= { unishipsNDECSAListEntry 8 }

unishipsByCard OBJECT-TYPE
    SYNTAX TruthValue
    MAX-ACCESS read-only
    STATUS current
    DESCRIPTION
        "The flag of this SA on NDEC or not.
        "
    ::= { unishipsNDECSAListEntry 9 }


unishipsNegotiateSaMode OBJECT-TYPE
    SYNTAX INTEGER {
        none(1),
        isakmp(2),
        manual(3)
    }
    MAX-ACCESS read-only
    STATUS current
    DESCRIPTION
        "The type of key used by the IPSec Phase-2 Tunnel.
        "
    ::= { unishipsNDECSAListEntry 10 }

unishipsExpBytes OBJECT-TYPE
    SYNTAX Gauge32
    MAX-ACCESS read-only
    STATUS current
    DESCRIPTION
        "This object specifies the lifetime in bytes
        of the tunnels generated using this
        policy specification."
    ::= { unishipsNDECSAListEntry 11 }

unishipsSoftBytes OBJECT-TYPE
    SYNTAX Gauge32
    MAX-ACCESS read-only
    STATUS current
    DESCRIPTION
        "This object specifies the lifetime in bytes
        of the tunnels generated using this
        policy specification."
    ::= { unishipsNDECSAListEntry 12 }

unishipsExpTimeout OBJECT-TYPE
    SYNTAX Gauge32
    MAX-ACCESS read-only
    STATUS current
    DESCRIPTION
        "This object specifies the lifetime in seconds
        of the tunnels generated using this
        policy specification."
    ::= { unishipsNDECSAListEntry 13 }

unishipsSoftTimeout OBJECT-TYPE
    SYNTAX Gauge32
    MAX-ACCESS read-only
    STATUS current
    DESCRIPTION
        "This object specifies the lifetime in seconds
        of the tunnels generated using this
        policy specification."
    ::= { unishipsNDECSAListEntry 14 }


 unishikeSATable OBJECT-TYPE
    SYNTAX SEQUENCE OF UnisHikeSAEntry
    MAX-ACCESS not-accessible
    STATUS current
    DESCRIPTION
        "The table containing IKE SA entities
        configured on NDEC by the operator.
        "

    ::= { unisNDEC 2 }

unishikeSAEntry OBJECT-TYPE
    SYNTAX UnisHikeSAEntry
    MAX-ACCESS not-accessible
    STATUS current
    DESCRIPTION
        "Each entry contains the attributes
        associated with a single IKE SA entity."
    INDEX { unishikeConnId }
    ::= { unishikeSATable 1 }

UnisHikeSAEntry ::= SEQUENCE {
    unishikeConnId  Integer32,
    unishikePeerIpAddr  IpAddress,
    unishikeFlag        DisplayString,
    unishikePhase       INTEGER,
    unishikeDoi         INTEGER,
    unishikeClearSA     TruthValue
     }

unishikeConnId OBJECT-TYPE
    SYNTAX Integer32(0..65535)
    MAX-ACCESS read-only
    STATUS current
    DESCRIPTION
        "The identifier of IKE SA connection."
    ::= { unishikeSAEntry 1 }

unishikePeerIpAddr OBJECT-TYPE
    SYNTAX IpAddress
    MAX-ACCESS read-only
    STATUS current
    DESCRIPTION
        "The peer IP address of this IKE SA.
        "
    ::= { unishikeSAEntry 2 }

unishikeFlag OBJECT-TYPE
    SYNTAX DisplayString
    MAX-ACCESS read-only
    STATUS current
    DESCRIPTION
        "The status of this IKE SA.
        "
    ::= { unishikeSAEntry 3 }

unishikePhase OBJECT-TYPE
    SYNTAX INTEGER{
        unkown(1),
        phase1(2),
        phase2(3)
    }
    MAX-ACCESS read-only
    STATUS current
    DESCRIPTION
        "The phase of this IKE SA.
        "
    ::= { unishikeSAEntry 4 }

unishikeDoi OBJECT-TYPE
   SYNTAX INTEGER{
        unkown(1),
        ipsec(2)
       }
    MAX-ACCESS read-only
    STATUS current
    DESCRIPTION
        "The domain of this IKE SA
        "
    ::= { unishikeSAEntry 5 }

unishikeClearSA OBJECT-TYPE
    SYNTAX TruthValue
    MAX-ACCESS read-write
    STATUS current
    DESCRIPTION
        "Clear this IKE SA or not.
        "
    ::= { unishikeSAEntry 6 }


unishipsIKEPolicyTable OBJECT-TYPE
    SYNTAX SEQUENCE OF UnisHipsIKEPolicyEntry
    MAX-ACCESS not-accessible
    STATUS current
    DESCRIPTION
        "List of all ISAKMP policy entries."
    ::= { unisNDEC 3 }

unishipsIKEPolicyEntry OBJECT-TYPE
    SYNTAX UnisHipsIKEPolicyEntry
    MAX-ACCESS not-accessible
    STATUS current
    DESCRIPTION
        "Each entry includes the properties of a ISAKMP Policy entry."
    INDEX { unishipsIsakmpPolPriority }
    ::= { unishipsIKEPolicyTable 1 }

UnisHipsIKEPolicyEntry ::= SEQUENCE {
    unishipsIsakmpPolPriority   Integer32,
    unishipsIsakmpPolEncr       INTEGER,
    unishipsIsakmpPolHash       INTEGER,
    unishipsIsakmpPolAuth       INTEGER,
    unishipsIsakmpPolGroup      INTEGER,
    unishipsIsakmpPolLifetime   Gauge32
    }

unishipsIsakmpPolPriority OBJECT-TYPE
    SYNTAX Integer32(0..65535)
    MAX-ACCESS read-only
    STATUS current
    DESCRIPTION
        "ISAKMP Policy entry's priority."
    ::= { unishipsIKEPolicyEntry 1 }

unishipsIsakmpPolEncr OBJECT-TYPE
    SYNTAX INTEGER {
        ikeEncryptNone(1),
        ikeEncryptDesCbc(2),
        ikeEncryptIdeaCbc(3),
        ikeEncryptBlowfishcbc(4),
        ikeEncryptRc5R16B64cbc(5),
        ikeEncrypt3DesCbc(6),
        ikeEncryptCastCbc(7)
    }
    MAX-ACCESS read-only
    STATUS current
    DESCRIPTION
        "The specified encryption transform. It is used by
        Internet Key Exchange(IKE) tunnels to protect the ISAKMP
        PDUs."
    ::= { unishipsIKEPolicyEntry 2 }

unishipsIsakmpPolHash OBJECT-TYPE
    SYNTAX INTEGER {
        ikeHashNone(1),
        ikeHashMd5(2),
        ikeHashSha(3),
        ikeHashTiger(4)
        }
    MAX-ACCESS read-only
    STATUS current
    DESCRIPTION
        "The specified hash transform. It is used by
        Internet Key Exchange(IKE) tunnels to protect the ISAKMP
        PDUs."
    ::= { unishipsIKEPolicyEntry 3 }

unishipsIsakmpPolAuth OBJECT-TYPE
    SYNTAX INTEGER {
        ikeAuthPreNone(1),
        ikeAuthPreShared(2) ,
        ikeAuthDss(3),
        ikeAuthRsaSig(4),
        ikeAuthRsaEnc(5),
        ikeAuthRsaEncRev(6)
        }
    MAX-ACCESS read-only
    STATUS current
    DESCRIPTION
        "The specified peer authentication method.
        The local entity would authenticate the peer using
        the method specified by this object when this policy
        entity is selected to negotiate with a peer."
    ::= { unishipsIKEPolicyEntry 4 }

unishipsIsakmpPolGroup OBJECT-TYPE
    SYNTAX INTEGER {
        none(1),
        dhGroup1(2),
        dhGroup2(3)
    }
    MAX-ACCESS read-only
    STATUS current
    DESCRIPTION
        "This object is used to specify the Oakley group
        which is used for Diffie Hellman exchange in the
        Main Mode.
        The local entity selects the group specified by
        this object to perform Diffie Hellman exchange with
        the peer when this policy item is chosen to negotiate
        the Main Mode with an IKE peer."
    ::= { unishipsIKEPolicyEntry 5 }

unishipsIsakmpPolLifetime OBJECT-TYPE
    SYNTAX Gauge32
    MAX-ACCESS read-only
    STATUS current
    DESCRIPTION
        "This object indicates the lifetime of the IKE tunnels in seconds."
    ::= { unishipsIKEPolicyEntry 6 }


unishipsStaticCryptomapTable OBJECT-TYPE
    SYNTAX SEQUENCE OF UnisHipsStaticCryptomapEntry
    MAX-ACCESS not-accessible
    STATUS current
    DESCRIPTION
        "The table includes the list of the member cryptomaps
        of the cryptomap sets which are set on the specific entity."
    ::= { unisNDEC 4 }

unishipsStaticCryptomapEntry OBJECT-TYPE
    SYNTAX UnisHipsStaticCryptomapEntry
    MAX-ACCESS not-accessible
    STATUS current
    DESCRIPTION
        "Each entry contains  properites of a single static cryptomap entry.
        The members of dynamic cryptomap sets, which may be linked with the
        parent static cryptomap set, are not included in this table."
    INDEX { unishipsStaticCryptomapName,unishipsStaticCryptomapSN }
    ::= { unishipsStaticCryptomapTable 1 }

UnisHipsStaticCryptomapEntry ::= SEQUENCE {
    unishipsStaticCryptomapName         DisplayString,
    unishipsStaticCryptomapSN       Integer32,
    unishipsStaticCryptomapNegMode      INTEGER,
    unishipsStaticCryptomapMatchAddr    INTEGER,
    unishipsStaticCryptomapPeerIpAddr   IpAddress,
    unishipsStaticCryptomapTransforName     DisplayString,
    unishipsStaticCryptomapLifetime     Gauge32,
    unishipsStaticCryptomapLifesize     Gauge32,
    unishipsStaticCryptomapLocalIpAddr  IpAddress,
    unishipsIfNameUsed              DisplayString,
    unishipsInAHSPI             Gauge32,
    unishipsInESPSPI            Gauge32,
    unishipsOutAHSPI            Gauge32,
    unishipsOutESPSPI           Gauge32,
    unishipsInAhHexKeyString        DisplayString,
    unishipsInEspCipherHexKeyString     DisplayString,
    unishipsInEspAuthenHexKeyString     DisplayString,
    unishipsInAhStringKeyString         DisplayString,
    unishipsInEspStringKeyString        DisplayString,
    unishipsOutAhHexKeyString       DisplayString,
    unishipsOutEspCipherHexKeyString    DisplayString,
    unishipsOutEspAuthenHexKeyString    DisplayString,
    unishipsOutAhStringKeyString        DisplayString,
    unishipsOutEspStringKeyString       DisplayString
    }



unishipsStaticCryptomapName OBJECT-TYPE
    SYNTAX DisplayString
    MAX-ACCESS read-only
    STATUS current
    DESCRIPTION
        "The name of the cryptomap entry in the
        cryptomap set. This is the first index
        component of this table."
    ::= { unishipsStaticCryptomapEntry 1 }

unishipsStaticCryptomapSN OBJECT-TYPE
    SYNTAX Integer32(0..65535)
    MAX-ACCESS read-only
    STATUS current
    DESCRIPTION
        "The sequence number of the cryptomap entry in the
        cryptomap set. This is the second index component
        of this table."
    ::= { unishipsStaticCryptomapEntry 2 }

unishipsStaticCryptomapNegMode OBJECT-TYPE
    SYNTAX INTEGER {
            none(1),
            isakmp(2),
            manual(3)
           }
    MAX-ACCESS read-only
    STATUS current
    DESCRIPTION
        "Type of the cryptomap entry. This object may be an ISAKMP
        cryptomap or manual."
    ::= { unishipsStaticCryptomapEntry 3 }

unishipsStaticCryptomapMatchAddr OBJECT-TYPE
    SYNTAX INTEGER(1..100000)
    MAX-ACCESS read-only
    STATUS current
    DESCRIPTION
        "The access list number entered by the operatoir
        while creating this cryptomap. "
    ::= { unishipsStaticCryptomapEntry 4 }

unishipsStaticCryptomapPeerIpAddr OBJECT-TYPE
    SYNTAX IpAddress
    MAX-ACCESS read-only
    STATUS current
    DESCRIPTION
        "The IP address of the current peer. Traffic protected by
        this cryptomap is protected by a tunnel terminating
        at the device whose IP address is the value of this object."
    ::= { unishipsStaticCryptomapEntry 5 }

unishipsStaticCryptomapTransforName OBJECT-TYPE
    SYNTAX DisplayString
    MAX-ACCESS read-only
    STATUS current
    DESCRIPTION
        "The transform associated with this cryptomap entry."
    ::= { unishipsStaticCryptomapEntry 6 }

unishipsStaticCryptomapLifetime OBJECT-TYPE
    SYNTAX Gauge32
    MAX-ACCESS read-only
    STATUS current
    DESCRIPTION
        "This object indicates the lifetime of the IPSec SA which is
        created using this IPSec policy entry."
    ::= { unishipsStaticCryptomapEntry 7 }

unishipsStaticCryptomapLifesize OBJECT-TYPE
    SYNTAX Gauge32
    MAX-ACCESS read-only
    STATUS current
    DESCRIPTION
        "This object identifies the lifesize of the IPSec SAs
        generated using this IPSec policy entry.
        Lifesize means maximum traffic in bytes that may be carried.
        "
    ::= { unishipsStaticCryptomapEntry 8 }

unishipsStaticCryptomapLocalIpAddr OBJECT-TYPE
    SYNTAX IpAddress
    MAX-ACCESS read-only
    STATUS current
    DESCRIPTION
        "The value of this object is the local IP address of the
        IPSec SAs generated using this IPSec policy entry.
        "
    ::= { unishipsStaticCryptomapEntry 9 }


   unishipsIfNameUsed OBJECT-TYPE
    SYNTAX DisplayString
    MAX-ACCESS read-only
    STATUS current
    DESCRIPTION
        "This object indicates the name of the
        interface which uses this IPSec policy entry.
        "
    ::= { unishipsStaticCryptomapEntry 10 }


unishipsInAHSPI OBJECT-TYPE
    SYNTAX Gauge32
    MAX-ACCESS read-only
    STATUS current
    DESCRIPTION
        "This object indicates the inbound AH SPI
        IPSec SAs generated using this IPSec policy entry."
    ::= { unishipsStaticCryptomapEntry 11 }

unishipsInESPSPI OBJECT-TYPE
    SYNTAX Gauge32
    MAX-ACCESS read-only
    STATUS current
    DESCRIPTION
        "This object indicates the inbound ESP SPI
        IPSec SAs generated using this IPSec policy entry.
       "
    ::= { unishipsStaticCryptomapEntry 12 }

unishipsOutAHSPI OBJECT-TYPE
    SYNTAX Gauge32
    MAX-ACCESS read-only
    STATUS current
    DESCRIPTION
        "This object indicates the outbound AH SPI
        IPSec SAs generated using this IPSec policy entry.
       "
    ::= { unishipsStaticCryptomapEntry 13 }

unishipsOutESPSPI OBJECT-TYPE
    SYNTAX Gauge32
    MAX-ACCESS read-only
    STATUS current
    DESCRIPTION
        "This object indicates the outbound ESP SPI
        IPSec SAs generated using this IPSec policy entry.
       "
    ::= { unishipsStaticCryptomapEntry 14 }

unishipsInAhHexKeyString OBJECT-TYPE
    SYNTAX DisplayString
    MAX-ACCESS read-only
    STATUS current
    DESCRIPTION
        "This object indicates the inbound AH authentication key
        IPSec SAs generated using this IPSec policy entry.
        The AH authentication key is in hex.
       "
    ::= { unishipsStaticCryptomapEntry 15 }

 unishipsInEspCipherHexKeyString OBJECT-TYPE
    SYNTAX DisplayString
    MAX-ACCESS read-only
    STATUS current
    DESCRIPTION
        "This object indicates the inbound ESP authentication key
       IPSec SAs generated using this IPSec policy entry.
       The ESP authentication key is hex.
       "
    ::= { unishipsStaticCryptomapEntry 16 }

 unishipsInEspAuthenHexKeyString OBJECT-TYPE
    SYNTAX DisplayString
    MAX-ACCESS read-only
    STATUS current
    DESCRIPTION
        "This object indicates the inbound ESP authentication key
        IPSec SAs generated using this IPSec policy entry.
        The ESP authentication key is hex.
       "
    ::= { unishipsStaticCryptomapEntry 17 }


 unishipsInAhStringKeyString OBJECT-TYPE
    SYNTAX DisplayString
    MAX-ACCESS read-only
    STATUS current
    DESCRIPTION
        "This object indicates the inbound ESP authentication key
        IPSec SAs generated using this IPSec policy entry.
        The key is in string.
       "
    ::= { unishipsStaticCryptomapEntry 18 }
 unishipsInEspStringKeyString OBJECT-TYPE
    SYNTAX DisplayString
    MAX-ACCESS read-only
    STATUS current
    DESCRIPTION
        "This object indicates the inbound ESP authentication key
        IPSec SAs generated using this IPSec policy entry.
        The key is in string.
       "
    ::= { unishipsStaticCryptomapEntry 19 }
 unishipsOutAhHexKeyString OBJECT-TYPE
    SYNTAX DisplayString
    MAX-ACCESS read-only
    STATUS current
    DESCRIPTION
        "This object indicates the outbound AH authentication key
        IPSec SAs generated using this IPSec policy entry.
        The key is in hex.
       "
    ::= { unishipsStaticCryptomapEntry 20 }
 unishipsOutEspCipherHexKeyString OBJECT-TYPE
    SYNTAX DisplayString
    MAX-ACCESS read-only
    STATUS current
    DESCRIPTION
        "This object indicates the outbound ESP authentication key
        IPSec SAs generated using this IPSec policy entry.
        The key is in hex.
       "
    ::= { unishipsStaticCryptomapEntry 21 }
 unishipsOutEspAuthenHexKeyString OBJECT-TYPE
    SYNTAX DisplayString
    MAX-ACCESS read-only
    STATUS current
    DESCRIPTION
        "This object indicates the outbound ESP authentication key
        IPSec SAs generated using this IPSec policy entry.
        The key is in hex.
       "
    ::= { unishipsStaticCryptomapEntry 22 }
 unishipsOutAhStringKeyString OBJECT-TYPE
    SYNTAX DisplayString
    MAX-ACCESS read-only
    STATUS current
    DESCRIPTION
        "This object indicates the outbound AH authentication key
        IPSec SAs generated using this IPSec policy entry.
        The key is in string.
       "
    ::= { unishipsStaticCryptomapEntry 23 }

  unishipsOutEspStringKeyString OBJECT-TYPE
    SYNTAX DisplayString
    MAX-ACCESS read-only
    STATUS current
    DESCRIPTION
        "This object indicates the outbound ESP authentication key
        IPSec SAs generated using this IPSec policy entry.
        The key is in string.
       "
    ::= { unishipsStaticCryptomapEntry 24 }


unishipsTransformNameSetTable OBJECT-TYPE
    SYNTAX SEQUENCE OF UnisHipsTransformNameSetEntry
    MAX-ACCESS not-accessible
    STATUS current
    DESCRIPTION
        "Transform set table."
    ::= { unisNDEC 5 }

unishipsTransformNameSetEntry OBJECT-TYPE
    SYNTAX UnisHipsTransformNameSetEntry
    MAX-ACCESS not-accessible
    STATUS current
    DESCRIPTION
        "Each entry refers to properties of a transform."
    INDEX { unishipsTransformName }
    ::= { unishipsTransformNameSetTable 1 }

UnisHipsTransformNameSetEntry ::= SEQUENCE {
    unishipsTransformName       DisplayString,
    unishipsTransformMode       INTEGER,
    unishipsTransformProtocol   INTEGER,
    unishipsAH          INTEGER,
    unishipsEespEn          INTEGER,
    unishipsEspAu           INTEGER,
    unishipsIsCardTransform     TruthValue
    }


unishipsTransformName OBJECT-TYPE
    SYNTAX DisplayString
    MAX-ACCESS read-only
    STATUS current
    DESCRIPTION
        "Name of the transform entry."
    ::= { unishipsTransformNameSetEntry 1 }

unishipsTransformMode OBJECT-TYPE
    SYNTAX INTEGER {
        tunnel(1),
        transport(2)
    }
    MAX-ACCESS read-only
    STATUS current
    DESCRIPTION
        "Mode of the transform entry."
    ::= { unishipsTransformNameSetEntry 2 }

unishipsTransformProtocol OBJECT-TYPE
    SYNTAX INTEGER {
                    ipsecNone(1),
                    ipsecAhNew(2),
                    ipsecAhEspNew(3),
                    ipsecAhEspOld(4),
                    ipsecAhOld(5),
                    ipsecEspNew(6),
                    ipsecEspAhNew(7),
                    ipsecEspAhOld(8),
                    ipsecEspOld(9)
                    }
    MAX-ACCESS read-only
    STATUS current
    DESCRIPTION
        "Transform protocol."
    ::= { unishipsTransformNameSetEntry 3 }

unishipsAH OBJECT-TYPE
    SYNTAX INTEGER {
        aalgNone(1),
        aalgMd5Hmac(2),
        aalgSha1Hmac(3),
        aalgMd5Hmac96(4),
        aalgSha1Hmac96(5),
        aalgXRipeMd160Hmac96(6),
        aalgXMd5(7),
        aalgXSha1(8)
       }
    MAX-ACCESS read-only
    STATUS current
    DESCRIPTION
        "Algorithm of AH protocol."
    ::= { unishipsTransformNameSetEntry 4 }


unishipsEespEn OBJECT-TYPE
    SYNTAX INTEGER {
        ealgNone(1),
        ealgDescbc(2),
        ealg3desCbc(3),
        ealgXBlf(4),
        ealgXCast(5),
        ealgXSkipjack(6),
        ealgXAes(7),
        ealgXQc5(8)
    }

    MAX-ACCESS read-only
    STATUS current
    DESCRIPTION
        "Encryption algorithm of ESP protocol."
    ::= { unishipsTransformNameSetEntry 5 }

unishipsEspAu OBJECT-TYPE
    SYNTAX INTEGER {
        aalgNone(1),
        aalgMd5Hmac(2),
        aalgSha1Hmac(3),
        aalgMd5Hmac96(4),
        aalgSha1Hmac96(5),
        aalgXRipeMd160Hmac96(6),
        aalgXMd5(7),
        aalgXSha1(8)
       }
    MAX-ACCESS read-only
    STATUS current
    DESCRIPTION
        "Authentication algorithm of ESP protocol."
    ::= { unishipsTransformNameSetEntry 6 }


unishipsIsCardTransform OBJECT-TYPE
    SYNTAX TruthValue
    MAX-ACCESS read-only
    STATUS current
    DESCRIPTION
        "This object indicates the flag of the NDEC is used for
        IPSec SAs generated using this IPSec policy entry.
       "
    ::= { unishipsTransformNameSetEntry 7 }


unishipsNDECInfoTable OBJECT-TYPE
    SYNTAX SEQUENCE OF UnisHipsNDECInfoEntry
    MAX-ACCESS not-accessible
    STATUS current
    DESCRIPTION
        "Table of NDEC set."
    ::= { unisNDEC 6 }

unishipsNDECInfoEntry OBJECT-TYPE
    SYNTAX UnisHipsNDECInfoEntry
    MAX-ACCESS not-accessible
    STATUS current
    DESCRIPTION
        "Properties of each NDEC.
        "
    INDEX { unishipsCardSlot }
    ::= { unishipsNDECInfoTable 1 }

UnisHipsNDECInfoEntry ::= SEQUENCE {
    unishipsCardSlot        INTEGER,
    unishipsInPac           Counter32,
    unishipsOutPac          Counter32,
    unishipsInByte          Counter32,
    unishipsOutByte         Counter32,
    unishipsDropPac         Counter32,
    unishipsCardStatus          INTEGER,
    unishipsCardHardVer         DisplayString,
    unishipsCardSoftVer         DisplayString,
    unishipsCardCPLDVer         DisplayString,
    unishipsCardOperate         INTEGER,
    unishipsDropPacInUnitTime   Gauge32
    }


unishipsCardSlot OBJECT-TYPE
    SYNTAX INTEGER(0..7)
    MAX-ACCESS read-only
    STATUS current
    DESCRIPTION
        "Slot number of NDEC ."
    ::= { unishipsNDECInfoEntry 1 }

unishipsInPac OBJECT-TYPE
    SYNTAX Counter32
    MAX-ACCESS read-only
    STATUS current
    DESCRIPTION
        "Total packets of the NDEC recieved."
    ::= { unishipsNDECInfoEntry 2 }

unishipsOutPac OBJECT-TYPE
    SYNTAX Counter32
    MAX-ACCESS read-only
    STATUS current
    DESCRIPTION
        "Total packets of the NDEC sent."
    ::= { unishipsNDECInfoEntry 3 }

unishipsInByte OBJECT-TYPE
    SYNTAX Counter32
    MAX-ACCESS read-only
    STATUS current
    DESCRIPTION
        "Total bytes of the NDEC sent."
    ::= { unishipsNDECInfoEntry 4 }

unishipsOutByte OBJECT-TYPE
    SYNTAX Counter32
    MAX-ACCESS read-only
    STATUS current
    DESCRIPTION
        "Total bytes of the NDEC sent."
    ::= { unishipsNDECInfoEntry 5 }

unishipsDropPac OBJECT-TYPE
    SYNTAX Counter32
    MAX-ACCESS read-only
    STATUS current
    DESCRIPTION
        "Total packets of the NDEC dropped ."
    ::= { unishipsNDECInfoEntry 6 }

unishipsCardStatus OBJECT-TYPE
    SYNTAX INTEGER{
        ecStateInvalid(1),  -- status exeception
        ecStateReady(2),    -- status normal
        ecStateResetting(3) ,   -- card is reseting
        ecStateProgramUpdating(4),   --card is loading
        ecStateDisable(5)         -- card is forbidden
    }
    MAX-ACCESS read-only
    STATUS current
    DESCRIPTION
        "State of the NDEC."
    ::= { unishipsNDECInfoEntry 7 }

unishipsCardHardVer OBJECT-TYPE
    SYNTAX DisplayString
    MAX-ACCESS read-only
    STATUS current
    DESCRIPTION
        "Hardware version of the NDEC."
    ::= { unishipsNDECInfoEntry 8 }

unishipsCardSoftVer OBJECT-TYPE
    SYNTAX DisplayString
    MAX-ACCESS read-only
    STATUS current
    DESCRIPTION
        "Software version of the NDEC."
    ::= { unishipsNDECInfoEntry 9 }

unishipsCardCPLDVer OBJECT-TYPE
    SYNTAX DisplayString
    MAX-ACCESS read-only
    STATUS current
    DESCRIPTION
        "CPLD version of the NDEC."
    ::= { unishipsNDECInfoEntry 10 }

unishipsCardOperate OBJECT-TYPE
    SYNTAX INTEGER {
        cardClearStatic(1),
        cardReset(2),
        cardSynTime(3),
        cardSysLogOn(4),
        cardSysLogOff(5),
        cardSysLogClear(6)
    }
    MAX-ACCESS read-write
    STATUS current
    DESCRIPTION
         "The version of the NDEC's CPLD.
         cardClearStatic(1): clear the statistics of the card
         cardReset(2): rest the card
         cardSynTime(3): synchoronize the clock of the card
         cardSysLogOn(4):turn on the log of the card
         cardSysLogOff(5):turn off the log of the card
         cardSysLogClear(6):clear the log of the card"
    ::= { unishipsNDECInfoEntry 11 }

unishipsDropPacInUnitTime OBJECT-TYPE
    SYNTAX Gauge32
    MAX-ACCESS read-only
    STATUS current
    DESCRIPTION
         "Dropped packets in unit interval."
    ::= { unishipsNDECInfoEntry 12 }


unishipsNDECLeaf OBJECT IDENTIFIER ::= { unisNDEC 7 }

unishipsNDECConnections OBJECT-TYPE
    SYNTAX INTEGER
    MAX-ACCESS read-only
    STATUS current
    DESCRIPTION
        "Total connections of the system at this time."
    ::= { unishipsNDECLeaf 1 }

unishipsNDECBackup OBJECT-TYPE
    SYNTAX INTEGER
    MAX-ACCESS read-write
    STATUS current
    DESCRIPTION
        "The flag that NDEC using backup. The value 1 represents using backup
        The value 0 represents not using backup"
    ::= { unishipsNDECLeaf 2 }


unishipsTraps OBJECT IDENTIFIER ::= { unisNDEC 8 }

unishipsNDECNormalResetTrap NOTIFICATION-TYPE
     OBJECTS { unishipsCardSlot,unishipsCardHardVer,
     unishipsCardSoftVer,unishipsCardCPLDVer }
     STATUS  current
     DESCRIPTION
          "This trap is generated when the NDEC card is reset."
    ::= { unishipsTraps 1 }

unishipsNDECStateChangeTrap NOTIFICATION-TYPE
     OBJECTS { unishipsCardSlot,unishipsCardStatus       }
     STATUS  current
     DESCRIPTION
         "This trap is generated when the NDEC card's state changes."
    ::= { unishipsTraps 2 }

unishipsNDECFlowTrap NOTIFICATION-TYPE
     OBJECTS { unishipsCardSlot,unishipsDropPacInUnitTime }
     STATUS  current
     DESCRIPTION
         "This trap is generated when a NDEC card is overloaded."
    ::= { unishipsTraps 3 }

END
