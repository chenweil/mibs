-- ==================================================================
-- Copyright (c) 2020 Unisyue Technologies Co., Ltd.  All rights reserved.
--
-- Description: Interface Management MIB
-- Reference:
-- Version: V4.1
-- History:
--      V1.0 (1) Created by Zhangshilin, 2001.06.29
--           (2) Revised by Qizhenglin, 2002.01.08
--      V1.1 2004/7/20 Add PortList and VlanIndex define
--      V1.2 2004/8/05 Add unisifEthernetIsolate and unisIsolateGroupMax
--                     by Chenshixing
--      V1.3 2004/9/08 add fabric value to unisifVLANType object and
--                     change the DESCRIPTION by chenshixing
--           2004/9/08 1.change the DESCRIPTION and the range of
--                       SYNTAX  INTEGER  from (5..100) to (1..100)
--                       in unisifMcastControl object by wangyingxia
--                     2.add the unisifPpsMcastControl object
--                       by wangyingxia
--                     3.change the status  in unisLswVlanMngObject
--                       to current by gaolong
--      V1.4 2004-10-12 updated by gaolong
--           Import TEXTUAL-CONVENTION, OBJECT-IDENTITY, Unsigned32.
--           Relocate unisLswL2InfMib MODULE-IDENTITY clause.
--           Change SYNTAX clause type of VlanIndex from INTEGER to Unsigned32.
--           Change MAX-ACCESS clause vlaue of unisifClearStat and unisifEthernetTest
--           from write-only to read-write.
--           Change value of unisifAggregateModel, unisdot1qVlanType, unisVlanInterfaceFrameType
--           and unisifEthernetMdi from underscores to hyphens.
--           Change value of unisifMacAddrLearnMode, beginning with lowercase.
--      V1.5 2004-11-15
--           Add the object unisdot1qVlanBcastSuppressionPPS by lihaijun
--           Adjust the format of the description of unisdot1qVlanBroadcastSuppression
--      V1.6 2004-12-2
--           Add the object unisGlobalBroadcastMaxPps by zhanggang
--           Add the object unisGlobalBroadcastMaxRatio by zhanggang
--           Add unisifVlanVPNStatus and unisBpduTunnelStatus by caiqiang
--           Add unisVlanInterfaceIpMethod by wangchao
--      V1.7 2005-01-22
--           Remove the content of unisLswVlan from this MIB to UNIS-LswVLAN-MIB
--           Remove SnmpAdminString
--      V1.8 2005-2-2
--           Add the object unisifPpsBcastDisValControl by zhangjianwei
--      V1.9 2005-03-08
--           Add unisifUniSuppressionStep, unisifPpsUniSuppressionMax, unisifMulSuppressionStep,
--           unisifPpsMulSuppressionMax, unisifUniSuppression, unisifPpsUniSuppression,
--           unisifMulSuppression, unisifPpsMulSuppression by wanghaisheng
--      V2.0 2005-06-14
--           Add the object unisifComboActivePort by majun and adjust format
--      V2.1 2005-06-30
--           Add the object unisifVlanVPNUplinkStatus, unisifVlanVPNTPID,
--           unisVlanVPNTPIDMode and unisVlanVPNTPID by hejunwei
--           Add unisifUnknownPacketDropMul, unisifUnknownPacketDropUni by wangyupeng
--           Add unisifBMbpsMulSuppressionMax, unisifBMbpsMulSuppression,
--           unisifBKbpsMulSuppressionMax, unisifBKbpsMulSuppressionStep
--           and unisifBKbpsMulSuppression by lichunyan
--           Update decription of MIB objects by gaolong
--      V2.2 2005-09-05
--           Add the object unisifIsolateGroupID, unisifisUplinkPort,
--           unisPortIsolateGroupTable, unisPortIsolateGroupEntry,
--           unisPortIsolateGroupIndex, unisPortIsolateUplinkIfIndex,
--           unisPortIsolateGroupRowStatus by huzinan
--      V2.3 2005-10-13
--           Add the object unisPortIsolateGroupDescription by hejunwei
--      V2.4 2005-11-15
--           Add the value 24000M to unisifEthernetSpeed by wanglirong
--      V2.5 2006-01-16
--           Add unisMaxMacLearnRange by zhangyinfei
--           Change the DESCRIPTION and the range of unisMaxMacLearn by zhangyinfei
--      V2.6 2006-01-03
--           Remove the value range from the definition of unisifXXBasePortIndex
--           by wangzhaoyan
--      V2.7 2006-02-11
--           Modify description of unisifXXBasePortIndex and unisifXXDevPortIndex
--           Modify description of unisifHybridTaggedVlanListLow, unisifHybridTaggedVlanListHigh,
--           unisifHybridUnTaggedVlanListLow and unisifHybridUnTaggedVlanListHigh
--           Modify some wrong format of the description
--      V2.8 2006-03-14
--           Add unisifEthernetAutoSpeedMask, unisifEthernetAutoSpeed in
--           unisethernetTable and SpeedModeFlag definition by Jin Yongfeng.
--      V2.9 2006-04-24
--           Remove value range of unisifEthernetMTU by Chenxi.
--      V3.0 2006-04-30
--           Add unisifBMbpsUniSuppressionMax, unisifBMbpsUniSuppression,
--           unisifBKbpsUniSuppressionMax, unisifBKbpsUniSuppressionStep
--           and unisifBKbpsUniSuppression by lichunyan.
--      V3.1 2006-09-27
--           unisifComboActivePort is obsoleted in unisifXXTable.
--           unisifComboPortTable is added for combo interface.
--           unisifComboActivePort is replaced with unisifComboPortCurActive.
--      V3.2 2009-04-11
--           Add unisifOutPayloadOctets, unisifInPayloadOctets, unisifInErrorPktsRate,
--           unisifInPkts, unisifInNormalPkts, unisifOutPkts by lisong.
--      V3.3 2011-11-08
--           Add the value s40000M and s100000M to SpeedModeFlag and
--           unisifEthernetSpeed by xiedong.
--      V3.4 2012-09-29
--           Modify description of unisifClearStat by xiedong.
--           2012-11-03
--           Add unisifPktBufTable, unisifPktBufEntry, unisifPktBufFree,
--           unisifPktBufInit, unisifPktBufMin, unisifPktBufMiss by chenkaiping
--      V3.5 2013-08-17
--           Add unisifPortProtocolStatTable by yangxiaoren.
--      V3.6 2014-02-08
--           Modify description of unisifUniSuppression, unisifMulSuppression and
--           unisifMcastControl, modify value list of unisifMcastControl by huhonghui,
--           for supporting value 0.
--      V3.7 2015-10-14
--           Add unisifMulSuppressionFlag by chenzhouhui.
--           Modify description of unisifMulSuppression and unisifPpsMulSuppression by chenzhouhui.
--           Add unisifPktBufInDrop and unisifPktBufEgDrop to unisifPktBufTable,
--           add unisifQueuePktBufTable by zhangji.
--      V3.8 2016-07-02
--           Add the values s2500M, s5000M, s20000M, s25000M and s50000M to SpeedModeFlag
--           and unisifEthernetSpeed by yuhaiyan.
--      V3.9 2018-10-09
--           Modify description of unisifComboPortCurActive,
--           modify value list of unisifComboPortCurActive by jinyiting,
--           for supporting value 4.
--      V4.0 2019-06-13
--           Add unisifQueueBufUsageIn5Seconds, unisifQueueBufUsageIn1Minute, unisifQueueBufUsageIn5Minutes
--           to unisifQueuePktBufTable by mazhixing.
--      V4.1 2019-08-03
--           Add the values s200000M, s400000M to SpeedModeFlag
--           and unisifEthernetSpeed by mazhixing.

-- ==================================================================
--
-- Variables and types be imported
--
-- ==================================================================
UNIS-LswINF-MIB DEFINITIONS ::= BEGIN

IMPORTS
    RowStatus, DisplayString, TruthValue, TEXTUAL-CONVENTION
        FROM SNMPv2-TC
    MODULE-IDENTITY, OBJECT-TYPE, Integer32, Counter64, Unsigned32, Counter32
        FROM SNMPv2-SMI
    ifIndex, InterfaceIndex
        FROM IF-MIB
    unislswCommon
        FROM UNIS-OID-MIB;

    unisLswL2InfMib MODULE-IDENTITY
            LAST-UPDATED "201908030000Z"
            ORGANIZATION
                "Unisyue Technologies Co., Ltd."
            CONTACT-INFO
                ""
            DESCRIPTION
            ""
            REVISION "201908030000Z"
            DESCRIPTION
                "Add the values s200000M and s400000M to SpeedModeFlag and unisifEthernetSpeed"
            REVISION "201906130000Z"
            DESCRIPTION
                "Add unisifQueueBufUsageIn5Seconds, unisifQueueBufUsageIn1Minute, unisifQueueBufUsageIn5Minutes to unisifQueuePktBufTable"
            REVISION "201607020000Z"
            DESCRIPTION
                "Add the values s2500M, s5000M, s20000M, s25000M and s50000M to SpeedModeFlag and unisifEthernetSpeed"
            REVISION "201510140000Z"
            DESCRIPTION
                "Add unisifPktBufInDrop and unisifPktBufEgDrop to unisifPktBufTable,
                 unisifMulSuppressionFlag, and unisifQueuePktBufTable, modify description of unisifMulSuppression and unisifPpsMulSuppression"
            REVISION "200106290000Z"
            DESCRIPTION
            "Initial version."
            ::= { unislswCommon 5 }


-- =============================================================
-- Textual Conventions
-- =============================================================

    PortList ::= TEXTUAL-CONVENTION
        STATUS      current
        DESCRIPTION
            "Each octet within this value specifies a set of eight
            ports, with the first octet specifying ports 1 through
            8, the second octet specifying ports 9 through 16, etc.
            Within each octet, the most significant bit represents
            the lowest numbered port, and the least significant bit
            represents the highest numbered port.  Thus, each port
            of the bridge is represented by a single bit within the
            value of this object.  If that bit has a value of '1'
            then that port is included in the set of ports; the port
            is not included if its bit has a value of '0'."
        SYNTAX      OCTET STRING


    VlanIndex ::= TEXTUAL-CONVENTION
        STATUS      current
        DESCRIPTION
            "A value used to index per-VLAN tables: values of 0 and
            4095 are not permitted; if the value is between 1 and
            4094 inclusive, it represents an IEEE 802.1Q VLAN-ID with
            global scope within a given bridged domain (see VlanId
            textual convention).  If the value is greater than 4095
            then it represents a VLAN with scope local to the
            particular agent, i.e. one without a global VLAN-ID
            assigned to it. Such VLANs are outside the scope of
            IEEE 802.1Q but it is convenient to be able to manage them
            in the same way using this MIB."
        SYNTAX      Unsigned32 (0..4294967295)

    DropDirection ::= TEXTUAL-CONVENTION
       STATUS  current
       DESCRIPTION
          "Representing the direction of dropping packets, if applicable."
       SYNTAX  INTEGER  {
                   disable        (1),
                   enableInbound  (2),
                   enableOutbound (3),
                   enableBoth     (4)
               }

    SpeedModeFlag ::= TEXTUAL-CONVENTION
        STATUS current
        DESCRIPTION
            "Type of Negotiable Speed mode."
        SYNTAX BITS
            {
                s10M(0),       -- 10M speed
                s100M(1),      -- 100M speed
                s1000M(2),     -- 1000M speed
                s10000M(3),    -- 10000M speed
                s24000M(4),    -- 24000M speed
                s40000M(5),    -- 40000M speed
                s100000M(6),   -- 100000M speed
                s2500M(7),     -- 2500M speed
                s5000M(8),     -- 5000M speed
                s20000M(9),    -- 20000M speed
                s25000M(10),   -- 25000M speed
                s50000M(11),   -- 50000M speed
                s200000M(12),  -- 200000M speed
                s400000M(13)   -- 400000M speed
            }


-- ==================================================================
--
-- ======================= definition begin =========================
--
-- ==================================================================
    unisLswExtInterface OBJECT IDENTIFIER ::= { unislswCommon 1 }

    unisifXXTable  OBJECT-TYPE
        SYNTAX SEQUENCE OF UnisIfXXEntry
        MAX-ACCESS not-accessible
        STATUS   current
        DESCRIPTION "Extended interface information table."
        ::= { unisLswExtInterface  1 }


    unisifXXEntry  OBJECT-TYPE
        SYNTAX UnisIfXXEntry
        MAX-ACCESS not-accessible
        STATUS   current
        DESCRIPTION "Entries of extended interface information table."
        INDEX { ifIndex }
        ::= { unisifXXTable 1}

    UnisIfXXEntry ::=
    SEQUENCE {
        unisifUnBoundPort     TruthValue  ,
        unisifISPhyPort       TruthValue  ,
        unisifAggregatePort   TruthValue  ,
        unisifMirrorPort      TruthValue  ,
        unisifVLANType        INTEGER     ,
        unisifMcastControl    INTEGER     ,
        unisifFlowControl     TruthValue  ,
        unisifSrcMacControl   TruthValue  ,
        unisifClearStat       INTEGER,
        unisifXXBasePortIndex INTEGER,
        unisifXXDevPortIndex  INTEGER,
        unisifPpsMcastControl  Integer32,
        unisifPpsBcastDisValControl INTEGER,
        unisifUniSuppressionStep Integer32,
        unisifPpsUniSuppressionMax Integer32,
        unisifMulSuppressionStep Integer32,
        unisifPpsMulSuppressionMax Integer32,
        unisifUniSuppression   Integer32,
        unisifPpsUniSuppression Integer32,
        unisifMulSuppression    Integer32,
        unisifPpsMulSuppression Integer32,
        unisifComboActivePort   INTEGER,
        unisifBMbpsMulSuppressionMax Integer32,
        unisifBMbpsMulSuppression Integer32,
        unisifBKbpsMulSuppressionMax Integer32,
        unisifBKbpsMulSuppressionStep Integer32,
        unisifBKbpsMulSuppression Integer32,
        unisifUnknownPacketDropMul DropDirection,
        unisifUnknownPacketDropUni DropDirection,
        unisifBMbpsUniSuppressionMax Integer32,
        unisifBMbpsUniSuppression Integer32,
        unisifBKbpsUniSuppressionMax Integer32,
        unisifBKbpsUniSuppressionStep Integer32,
        unisifBKbpsUniSuppression Integer32,
        unisifOutPayloadOctets Counter64,
        unisifInPayloadOctets Counter64,
        unisifInErrorPktsRate Integer32,
        unisifInPkts Counter64,
        unisifInNormalPkts  Counter64,
        unisifOutPkts Counter64,
        unisifMulSuppressionFlag  INTEGER
        }


   unisifUnBoundPort  OBJECT-TYPE
        SYNTAX  TruthValue
        MAX-ACCESS read-only
        STATUS current
        DESCRIPTION
            "Whether it is the unbound port. (true indicates that the port is
            the main port of the aggregation or the port does not participate
            in the aggregation.)"
        ::= { unisifXXEntry 1 }


    unisifISPhyPort  OBJECT-TYPE
        SYNTAX  TruthValue
        MAX-ACCESS read-only
        STATUS current
        DESCRIPTION "Whether it is a physical interface."
        ::= { unisifXXEntry 2 }


    unisifAggregatePort OBJECT-TYPE
        SYNTAX  TruthValue
        MAX-ACCESS read-only
        STATUS current
        DESCRIPTION "Whether it is the aggregated port. (if the port participates
                    in the aggregation, this value is true.)"
        ::= { unisifXXEntry 3 }


    unisifMirrorPort  OBJECT-TYPE
        SYNTAX  TruthValue
        MAX-ACCESS read-write
        STATUS current
        DESCRIPTION "Whether it is a mirror port."
        ::= { unisifXXEntry 4 }


    unisifVLANType  OBJECT-TYPE
        SYNTAX  INTEGER
        {
        vLANTrunk  (1),
        access   (2),
        hybrid    (3),
        fabric   (4)
        }
        MAX-ACCESS read-write
        STATUS current
        DESCRIPTION
            "port vlan types.
            hybrid (3) port can carry multiple VLANs.
            If fabric function is supported, fabric(4) means the port is
            a fabric port."
        ::= { unisifXXEntry 5 }


    unisifMcastControl OBJECT-TYPE
        SYNTAX  INTEGER (0..100)
        MAX-ACCESS read-write
        STATUS current
        DESCRIPTION
            "Broadcast storm suppression with the step length of 1,
            ranging from 0 to 100 percent.
            In some products the step is 5, ranging from 0 to 100."
        ::= { unisifXXEntry 6 }

    unisifFlowControl  OBJECT-TYPE
        SYNTAX  TruthValue
        MAX-ACCESS read-write
        STATUS current
        DESCRIPTION "Flow control status."
        ::= { unisifXXEntry 7 }


    unisifSrcMacControl OBJECT-TYPE
        SYNTAX  TruthValue
        MAX-ACCESS read-only
        STATUS current
        DESCRIPTION "Whether to filter by source MAC address."
        ::= { unisifXXEntry 8 }


    unisifClearStat  OBJECT-TYPE
        SYNTAX  INTEGER
        {
            clear(1)
        }
        MAX-ACCESS read-write
        STATUS current
        DESCRIPTION "Clear specify port statistics.  Operation read is not supported."
        ::= { unisifXXEntry 9 }

    unisifXXBasePortIndex OBJECT-TYPE
        SYNTAX  INTEGER
        MAX-ACCESS read-only
        STATUS current
        DESCRIPTION "Index number of the port and the first port index of the
                    device is 1."
        ::= { unisifXXEntry 10 }

    unisifXXDevPortIndex OBJECT-TYPE
        SYNTAX  INTEGER
        MAX-ACCESS read-only
        STATUS current
        DESCRIPTION "Device index of the port."
        ::= { unisifXXEntry 11 }

   unisifPpsMcastControl OBJECT-TYPE
        SYNTAX  Integer32
        MAX-ACCESS read-write
        STATUS current
        DESCRIPTION
            "The broadcast suppression with pps(packet per second) type.
            The max value is determined by the port type and product."
        ::= { unisifXXEntry 12 }

   unisifPpsBcastDisValControl OBJECT-TYPE
        SYNTAX  INTEGER
        {
          enable(1),
          disable(2)
        }
        MAX-ACCESS read-write
        STATUS current
        DESCRIPTION
            "Control the port's pps(packet per second) broadcast suppression.
            When the port is enabled, its pps broadcast suppression value is the
            global disperse value, and when disabled, it doesn't suppress broadcast."
        ::= { unisifXXEntry 13 }

   unisifUniSuppressionStep OBJECT-TYPE
        SYNTAX  Integer32
        MAX-ACCESS read-only
        STATUS current
        DESCRIPTION "The step of unicast suppression in ratio mode."
        ::= { unisifXXEntry 14 }

   unisifPpsUniSuppressionMax OBJECT-TYPE
        SYNTAX  Integer32
        MAX-ACCESS read-only
        STATUS current
        DESCRIPTION "The max pps(packet per second) value of unicast suppression
                    in pps mode."
        ::= { unisifXXEntry 15 }

   unisifMulSuppressionStep OBJECT-TYPE
        SYNTAX  Integer32
        MAX-ACCESS read-only
        STATUS current
        DESCRIPTION "The step of multicast suppression in ratio mode."
        ::= { unisifXXEntry 16 }

   unisifPpsMulSuppressionMax OBJECT-TYPE
        SYNTAX  Integer32
        MAX-ACCESS read-only
        STATUS current
        DESCRIPTION "The max pps(packet per second) value of multicast suppression
                    in pps mode."
        ::= { unisifXXEntry 17 }

   unisifUniSuppression OBJECT-TYPE
        SYNTAX  Integer32
        MAX-ACCESS read-write
        STATUS current
        DESCRIPTION
            "The unicast suppression with the ranging from 0 to 100 percent
            in ratio mode.
            The step is determined by unisifUniSuppressionStep."
        ::= { unisifXXEntry 18 }

   unisifPpsUniSuppression OBJECT-TYPE
        SYNTAX  Integer32
        MAX-ACCESS read-write
        STATUS current
        DESCRIPTION
            "The unicast suppression in pps(packet per second) mode.
            The max value is determined by unisifPpsUniSuppressionMax."
        ::= { unisifXXEntry 19 }

   unisifMulSuppression OBJECT-TYPE
        SYNTAX  Integer32
        MAX-ACCESS read-write
        STATUS current
        DESCRIPTION
            "The multicast suppression with ranging from 0 to 100 percent
            in ratio mode.
            The step is determined by unisifMulSuppressionStep.
            If unisifMulSuppressionFlag is 2 it means only unknown
            traffic suppression."
        ::= { unisifXXEntry 20 }

   unisifPpsMulSuppression OBJECT-TYPE
        SYNTAX  Integer32
        MAX-ACCESS read-write
        STATUS current
        DESCRIPTION
            "The multicast suppression in pps(packet per second) mode.
            The max pps value is determined by unisifPpsMulSuppressionMax.
            If unisifMulSuppressionFlag is 2 it means only unknown
            traffic suppression."
        ::= { unisifXXEntry 21 }

   unisifComboActivePort OBJECT-TYPE
        SYNTAX  INTEGER
        {
            fiber   (1),    -- Optical port
            copper  (2),    -- Electrical port
            na      (3)     -- Not applicable
        }
        MAX-ACCESS read-write
        STATUS obsolete
        DESCRIPTION "Active port on combo interface."
        ::= { unisifXXEntry 22 }

    unisifBMbpsMulSuppressionMax OBJECT-TYPE
        SYNTAX  Integer32
        MAX-ACCESS read-only
        STATUS current
        DESCRIPTION
                "The maximum value of the multicast suppression with bandwidth-based(Mbps)
                that a port can be configured."
        ::= { unisifXXEntry 23 }

    unisifBMbpsMulSuppression OBJECT-TYPE
        SYNTAX  Integer32
        MAX-ACCESS read-write
        STATUS current
        DESCRIPTION
                "With bandwidth-based multicast suppression, the bandwidth is measured
                in Mbps.
                The upper limit of the multicast suppession with bandwidth-based(Mbps)
                is the value of unisifBMbpsMulSuppressionMax in the entry.
                The default value of unisifBMbpsMulSuppression is the value of
                unisifBMbpsMulSuppressionMax."
        ::= { unisifXXEntry 24 }

    unisifBKbpsMulSuppressionMax OBJECT-TYPE
        SYNTAX  Integer32
        MAX-ACCESS read-only
        STATUS current
        DESCRIPTION
                "The maximum value of the multicast suppression with bandwidth-based(Kbps)
                that a port can be configured."
        ::= { unisifXXEntry 25 }

    unisifBKbpsMulSuppressionStep OBJECT-TYPE
        SYNTAX  Integer32
        MAX-ACCESS read-only
        STATUS current
        DESCRIPTION
                "The step of multicast suppression with bandwidth-based(Kbps)."
        ::= { unisifXXEntry 26 }

    unisifBKbpsMulSuppression OBJECT-TYPE
        SYNTAX  Integer32
        MAX-ACCESS read-write
        STATUS current
        DESCRIPTION
                "With bandwidth-based multicast suppression, the bandwidth
                is measured in Kbps.
                The upper limit of the multicast suppession with bandwidth-based(Kbps)
                is the value of unisifBKbpsMulSuppressionMax in the entry.
                The value of unisifBKbpsMulSuppression must be multiple of the
                value of unisifBKbpsMulSuppressionStep.
                The default value of unisifBKbpsMulSuppression is the value of
                unisifBKbpsMulSuppressionMax."
        ::= { unisifXXEntry 27 }

   unisifUnknownPacketDropMul OBJECT-TYPE
        SYNTAX  DropDirection
        MAX-ACCESS read-write
        STATUS current
        DESCRIPTION "Control the port's unknown-multicast packets drop. When
                     inbound direction is enabled on this port, the port will
                     drop unknown-multicast packets in inbound direction. When
                     outbound direction is enabled on this port, the port will
                     drop unknown-multicast packets in outbound direction. When
                     both directions are enabled on this port, the port will
                     drop unknown-multicast packets in both inbound and outbound
                     directions."
        DEFVAL { disable }
        ::= { unisifXXEntry 28 }

   unisifUnknownPacketDropUni OBJECT-TYPE
        SYNTAX  DropDirection
        MAX-ACCESS read-write
        STATUS current
        DESCRIPTION "Control the port's unknown-unicast packets drop. When
                     inbound direction is enabled on this port, the port will
                     drop unknown-unicast packets in inbound direction. When
                     outbound direction is enabled on this port, the port will
                     drop unknown-unicast packets in outbound direction. When
                     both directions are enabled on this port, the port will
                     drop unknown-unicast packets in both inbound and outbound
                     directions."
        DEFVAL { disable }
        ::= { unisifXXEntry 29 }

    unisifBMbpsUniSuppressionMax OBJECT-TYPE
        SYNTAX  Integer32
        MAX-ACCESS read-only
        STATUS current
        DESCRIPTION "
            The maximum value of the unicast suppression with bandwidth-based
            (Mbps) that a port can be configured."
        ::= { unisifXXEntry 30 }

    unisifBMbpsUniSuppression OBJECT-TYPE
        SYNTAX  Integer32
        MAX-ACCESS read-write
        STATUS current
        DESCRIPTION "
            With bandwidth-based Unicast suppression, the bandwidth is measured
            in Mbps.
            The upper limit of the unicast suppession with bandwidth-based(Mbps)
            is the value of unisifBMbpsUniSuppressionMax in the entry.
            The default value of unisifBMbpsUniSuppression is the value of
            unisifBMbpsUniSuppressionMax."
        ::= { unisifXXEntry 31 }

    unisifBKbpsUniSuppressionMax OBJECT-TYPE
        SYNTAX  Integer32
        MAX-ACCESS read-only
        STATUS current
        DESCRIPTION "
            The maximum value of the unicast suppression with bandwidth-based
            (Kbps) that a port can be configured."
        ::= { unisifXXEntry 32 }

    unisifBKbpsUniSuppressionStep OBJECT-TYPE
        SYNTAX  Integer32
        MAX-ACCESS read-only
        STATUS current
        DESCRIPTION "
            The step of unicast suppression with bandwidth-based(Kbps)."
        ::= { unisifXXEntry 33 }

    unisifBKbpsUniSuppression OBJECT-TYPE
        SYNTAX  Integer32
        MAX-ACCESS read-write
        STATUS current
        DESCRIPTION "
            With bandwidth-based unicast suppression, the bandwidth
            is measured in Kbps.
            The upper limit of the unicast suppession with bandwidth-based(Kbps)
            is the value of unisifBKbpsUniSuppressionMax in the entry.
            The value of unisifBKbpsUniSuppression must be multiple of the
            value of unisifBKbpsUniSuppressionStep.
            The default value of unisifBKbpsUniSuppression is the value of
            unisifBKbpsUniSuppressionMax."
        ::= { unisifXXEntry 34 }

    unisifOutPayloadOctets OBJECT-TYPE
        SYNTAX  Counter64
        MAX-ACCESS read-only
        STATUS current
        DESCRIPTION "
            The actual output octets of the interface."
        ::= { unisifXXEntry 35 }

    unisifInPayloadOctets OBJECT-TYPE
        SYNTAX  Counter64
        MAX-ACCESS read-only
        STATUS current
        DESCRIPTION "
            The actual input octets of the interface."
        ::= { unisifXXEntry 36 }

    unisifInErrorPktsRate OBJECT-TYPE
        SYNTAX  Integer32
        MAX-ACCESS read-only
        STATUS current
        DESCRIPTION "
            The rate of inbound error packets on the interface."
        ::= { unisifXXEntry 37 }

    unisifInPkts OBJECT-TYPE
        SYNTAX  Counter64
        MAX-ACCESS read-only
        STATUS current
        DESCRIPTION "
            The number of packets received on the interface."
        ::= { unisifXXEntry 38 }

    unisifInNormalPkts OBJECT-TYPE
        SYNTAX  Counter64
        MAX-ACCESS read-only
        STATUS current
        DESCRIPTION "
            The number of normal packets received on the interface."
        ::= { unisifXXEntry 39 }

    unisifOutPkts OBJECT-TYPE
        SYNTAX  Counter64
        MAX-ACCESS read-only
        STATUS current
        DESCRIPTION "
            The number of packets sent on the interface."
        ::= { unisifXXEntry 40 }

   unisifMulSuppressionFlag OBJECT-TYPE
        SYNTAX  INTEGER
        {
            all      (1),    -- known and unknown traffic
            unknown  (2)    -- only unknown traffic
        }
        MAX-ACCESS read-write
        STATUS current
        DESCRIPTION "
            The multicast suppression flag.  If only unknown multicast
            traffic is suppressed, the value is unknown(2), and all(1) for suppression of all traffic (unknown and known)."
        ::= { unisifXXEntry 41 }

    unisifAggregateTable  OBJECT-TYPE
        SYNTAX SEQUENCE OF UnisIfAggregateEntry
        MAX-ACCESS not-accessible
        STATUS current
        DESCRIPTION "Port aggregation information table."
        ::= { unisLswExtInterface  2 }


    unisifAggregateEntry  OBJECT-TYPE
        SYNTAX UnisIfAggregateEntry
        MAX-ACCESS not-accessible
        STATUS current
        DESCRIPTION "Port aggregation information table."
        INDEX   { unisifAggregatePortIndex }
        ::= { unisifAggregateTable 1}

    UnisIfAggregateEntry  ::=
    SEQUENCE {
        unisifAggregatePortIndex      InterfaceIndex,
        unisifAggregatePortName       OCTET STRING,
        unisifAggregatePortListPorts  PortList,
        unisifAggregateModel          INTEGER,
        unisifAggregateOperStatus     RowStatus
        }



    unisifAggregatePortIndex  OBJECT-TYPE
        SYNTAX  InterfaceIndex
        MAX-ACCESS read-only
        STATUS current
        DESCRIPTION "Index number of the main aggregated port."
        ::= { unisifAggregateEntry 1 }


    unisifAggregatePortName  OBJECT-TYPE
        SYNTAX  OCTET STRING (SIZE(0..40))
        MAX-ACCESS read-write
        STATUS current
        DESCRIPTION "Aggregation group name."
        ::= { unisifAggregateEntry 2 }


    unisifAggregatePortListPorts OBJECT-TYPE
        SYNTAX  PortList
        MAX-ACCESS read-write
        STATUS current
        DESCRIPTION   "Portlist of a aggregating."
        ::= { unisifAggregateEntry 3 }


    unisifAggregateModel  OBJECT-TYPE
        SYNTAX  INTEGER
        {
        ingress     (1),
        both        (2),
        round-robin (3)
        }
        MAX-ACCESS read-write
        STATUS current
        DESCRIPTION "Load sharing mode for the port aggregation."
        ::= { unisifAggregateEntry 4 }


    unisifAggregateOperStatus  OBJECT-TYPE
        SYNTAX  RowStatus
        MAX-ACCESS read-create
        STATUS current
        DESCRIPTION "Current operation status of the row."
        ::= { unisifAggregateEntry 5 }

-- ==================================================================
    unisifHybridPortTable  OBJECT-TYPE
        SYNTAX SEQUENCE OF UnisifHybridPortEntry
        MAX-ACCESS not-accessible
        STATUS current
        DESCRIPTION "Hybrid-port configuration table."
        ::= { unisLswExtInterface  3 }


    unisifHybridPortEntry  OBJECT-TYPE
        SYNTAX UnisifHybridPortEntry
        MAX-ACCESS not-accessible
        STATUS current
        DESCRIPTION "Hybrid-port configuration table."
        INDEX   { unisifHybridPortIndex }
        ::= { unisifHybridPortTable 1}

    UnisifHybridPortEntry  ::=
    SEQUENCE {
        unisifHybridPortIndex            INTEGER,
        unisifHybridTaggedVlanListLow    OCTET STRING,
        unisifHybridTaggedVlanListHigh   OCTET STRING,
        unisifHybridUnTaggedVlanListLow  OCTET STRING,
        unisifHybridUnTaggedVlanListHigh OCTET STRING
        }



    unisifHybridPortIndex  OBJECT-TYPE
        SYNTAX  INTEGER
        MAX-ACCESS read-only
        STATUS current
        DESCRIPTION "Index number of Hybrid-port."
        ::= { unisifHybridPortEntry 1 }


    unisifHybridTaggedVlanListLow  OBJECT-TYPE
        SYNTAX  OCTET STRING (SIZE(0..256))
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each tagged VLAN
                    of the hybrid port is represented by a single bit within
                    the value of this object. If that bit has a value of '1'
                    then that VLAN is tagged in the set of VLANs; the VLAN
                    is not tagged if its bit has a value of '0'."
        ::= { unisifHybridPortEntry 2 }


    unisifHybridTaggedVlanListHigh OBJECT-TYPE
        SYNTAX  OCTET STRING (SIZE(0..256))
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each tagged VLAN
                    of the hybrid port is represented by a single bit within
                    the value of this object. If that bit has a value of '1'
                    then that VLAN is tagged in the set of VLANs; the VLAN
                    is not tagged if its bit has a value of '0'."
        ::= { unisifHybridPortEntry 3 }


    unisifHybridUnTaggedVlanListLow  OBJECT-TYPE
        SYNTAX  OCTET STRING (SIZE(0..256))
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each untagged
                    VLAN of the hybrid port is represented by a single bit
                    within the value of this object. If that bit has a value
                    of '1' then that VLAN is untagged in the set of VLANs; the
                    VLAN is not untagged if its bit has a value of '0'."
        ::= { unisifHybridPortEntry 4 }


    unisifHybridUnTaggedVlanListHigh OBJECT-TYPE
        SYNTAX  OCTET STRING (SIZE(0..256))
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each untagged
                    VLAN of the hybrid port is represented by a single bit
                    within the value of this object. If that bit has a value of
                    '1' then that VLAN is untagged in the set of VLANs; the VLAN
                    is not untagged if its bit has a value of '0'."
        ::= { unisifHybridPortEntry 5 }

-- ==================== Combo port table ============================
    unisifComboPortTable  OBJECT-TYPE
        SYNTAX SEQUENCE OF UnisifComboPortEntry
        MAX-ACCESS not-accessible
        STATUS current
        DESCRIPTION "Combo-port table."
        ::= { unisLswExtInterface  4 }

    unisifComboPortEntry  OBJECT-TYPE
        SYNTAX UnisifComboPortEntry
        MAX-ACCESS not-accessible
        STATUS current
        DESCRIPTION "The entry of unisifComboPortTable."
        INDEX    { unisifComboPortIndex }
        ::= { unisifComboPortTable 1}

    UnisifComboPortEntry  ::=
    SEQUENCE {
        unisifComboPortIndex       InterfaceIndex,
        unisifComboPortCurActive   INTEGER
        }

    unisifComboPortIndex OBJECT-TYPE
        SYNTAX  InterfaceIndex
        MAX-ACCESS read-only
        STATUS current
        DESCRIPTION
            "The combo-port interface index. Its value is the same as the value
            of ifIndex in ifTable, but only includes indexes of the combo-port
            interfaces."
        ::= { unisifComboPortEntry 1 }

    unisifComboPortCurActive OBJECT-TYPE
        SYNTAX  INTEGER
        {
            fiber   (1),    -- Optical port
            copper  (2),    -- Electrical port
            na      (3),    -- Not applicable
            auto    (4)     -- Identifing the optical/electrical port automatic
        }
        MAX-ACCESS read-write
        STATUS current
        DESCRIPTION
            "Current active interface of combo interfaces. The value 'fiber'
            means the interface with fiber connector of the pair of combo-port
            interfaces is active. The value 'copper' means the interface with
            copper connector of the pair is active. The value 'na' means not
            supported. The value 'auto' means the interface identified
            the copper or fiber port automatic."
        ::= { unisifComboPortEntry 2 }

-- ======================pkt buf table===============================
    unisifPktBufTable  OBJECT-TYPE
        SYNTAX SEQUENCE OF UnisifPktBufEntry
        MAX-ACCESS not-accessible
        STATUS current
        DESCRIPTION "Packet buffer table."
        ::= { unisLswExtInterface  5 }

    unisifPktBufEntry  OBJECT-TYPE
        SYNTAX UnisifPktBufEntry
        MAX-ACCESS not-accessible
        STATUS current
        DESCRIPTION "The entry of unisifPktBufTable."
        INDEX { ifIndex }
        ::= { unisifPktBufTable 1}

    UnisifPktBufEntry  ::=
        SEQUENCE {
            unisifPktBufFree      Integer32,
            unisifPktBufInit      Integer32,
            unisifPktBufMin       Integer32,
            unisifPktBufMiss      Counter64,
            unisifPktBufInDrop    Counter64,
            unisifPktBufEgDrop    Counter64
            }

    unisifPktBufFree OBJECT-TYPE
        SYNTAX  Integer32
        MAX-ACCESS read-only
        STATUS current
        DESCRIPTION
            "The number of packet buffers available for the interface."
        ::= { unisifPktBufEntry 1 }

    unisifPktBufInit OBJECT-TYPE
        SYNTAX  Integer32
        MAX-ACCESS read-only
        STATUS current
        DESCRIPTION
            "The number of packet buffers allocated when the interface was created."
        ::= { unisifPktBufEntry 2 }

    unisifPktBufMin OBJECT-TYPE
        SYNTAX  Integer32
        MAX-ACCESS read-only
        STATUS current
        DESCRIPTION
            "The smallest number of packet buffers available for the interface."
        ::= { unisifPktBufEntry 3 }

    unisifPktBufMiss OBJECT-TYPE
        SYNTAX  Counter64
        MAX-ACCESS read-only
        STATUS current
        DESCRIPTION
            "The number of times that the interface failed to obtain a packet
             buffer.  Failure to obtain a buffer indicates that buffers were busy."
        ::= { unisifPktBufEntry 4 }

    unisifPktBufInDrop OBJECT-TYPE
        SYNTAX  Counter64
        MAX-ACCESS read-only
        STATUS current
        DESCRIPTION
            "The number of ingress packets dropped by the interface
             because of insufficient data buffer."
        ::= { unisifPktBufEntry 5 }

    unisifPktBufEgDrop OBJECT-TYPE
        SYNTAX  Counter64
        MAX-ACCESS read-only
        STATUS current
        DESCRIPTION
            "The number of egress packets dropped by the interface
             because of insufficient data buffer."
        ::= { unisifPktBufEntry 6 }

-- ======================if queue pkt buf table===============================
    unisifQueuePktBufTable  OBJECT-TYPE
        SYNTAX SEQUENCE OF UnisifQueuePktBufEntry
        MAX-ACCESS not-accessible
        STATUS current
        DESCRIPTION "802.1p queue of the interface packet buffer table."
        ::= { unisLswExtInterface  6 }

    unisifQueuePktBufEntry  OBJECT-TYPE
        SYNTAX UnisifQueuePktBufEntry
        MAX-ACCESS not-accessible
        STATUS current
        DESCRIPTION "The entry of unisifQueuePktBufTable."
        INDEX
            {
                ifIndex,
                unisifQueueId
            }
        ::= { unisifQueuePktBufTable 1}

    UnisifQueuePktBufEntry  ::=
        SEQUENCE {
            unisifQueueId                  Integer32,
            unisifQueuePktBufTotal         Unsigned32,
            unisifQueueBufUsed             Unsigned32,
            unisifQueueBufThreCount        Counter32,
            unisifQueueBufUsageIn5Seconds  Integer32,
            unisifQueueBufUsageIn1Minute   Integer32,
            unisifQueueBufUsageIn5Minutes  Integer32
            }

    unisifQueueId OBJECT-TYPE
        SYNTAX  Integer32(1..8)
        MAX-ACCESS read-only
        STATUS current
        DESCRIPTION
            "The 802.1p queue ID of the interface. This value is
             used to specify the queue ID of the interface
             when the user wants to read one queue of the interface.
             The index number 1-8 correspond with 802.1p queue ID 0-7."
        ::= { unisifQueuePktBufEntry 1 }

    unisifQueuePktBufTotal OBJECT-TYPE
        SYNTAX  Unsigned32
        MAX-ACCESS read-only
        STATUS current
        DESCRIPTION
            "The number of packet buffers available for the interface,
             including fixed buffer and shared buffer."
        ::= { unisifQueuePktBufEntry 2 }

    unisifQueueBufUsed OBJECT-TYPE
        SYNTAX  Unsigned32
        MAX-ACCESS read-only
        STATUS current
        DESCRIPTION
            "The number of packet buffers that have been used for each
             802.1p queue of the interface."
        ::= { unisifQueuePktBufEntry 3 }

    unisifQueueBufThreCount OBJECT-TYPE
        SYNTAX  Counter32
        MAX-ACCESS read-only
        STATUS current
        DESCRIPTION
            "The number of times that each 802.1p queue of the interface has
             exceeded the buffer threshold. The threshold is configurated by user."
        ::= { unisifQueuePktBufEntry 4 }

    unisifQueueBufUsageIn5Seconds OBJECT-TYPE
        SYNTAX  Integer32 (0..100)
        MAX-ACCESS read-only
        STATUS current
        DESCRIPTION
            "The buffer usage in the last 5 seconds for each 802.1p queue of the interface."
        ::= { unisifQueuePktBufEntry 5 }

    unisifQueueBufUsageIn1Minute OBJECT-TYPE
        SYNTAX  Integer32 (0..100)
        MAX-ACCESS read-only
        STATUS current
        DESCRIPTION
            "The buffer usage in the last 1 minute for each 802.1p queue of the interface."
        ::= { unisifQueuePktBufEntry 6 }

    unisifQueueBufUsageIn5Minutes OBJECT-TYPE
        SYNTAX  Integer32 (0..100)
        MAX-ACCESS read-only
        STATUS current
        DESCRIPTION
            "The buffer usage in the last 5 minutes for each 802.1p queue of the interface."
        ::= { unisifQueuePktBufEntry 7 }

-- ========================l2========================================
    unisLswL2InfMibObject OBJECT IDENTIFIER ::= {  unisLswL2InfMib 1  }

    unisSlotPortMax  OBJECT-TYPE
        SYNTAX  INTEGER
        MAX-ACCESS read-only
        STATUS current
        DESCRIPTION "Max ports of the slots."
        ::= { unisLswL2InfMibObject  1 }

    unisSwitchPortMax  OBJECT-TYPE
        SYNTAX  INTEGER
        MAX-ACCESS read-only
        STATUS current
        DESCRIPTION "Max ports that this switch includes."
        ::= { unisLswL2InfMibObject  2 }

    unisifVLANTrunkStatusTable  OBJECT-TYPE
        SYNTAX SEQUENCE OF UnisIfVLANTrunkStatusEntry
        MAX-ACCESS not-accessible STATUS   current
        DESCRIPTION "Gvrp attributes on the VlanTrunk port."
        ::= { unisLswL2InfMibObject  3 }

    unisifVLANTrunkStatusEntry  OBJECT-TYPE
        SYNTAX UnisIfVLANTrunkStatusEntry
        MAX-ACCESS not-accessible STATUS   current
        DESCRIPTION "Gvrp attributes on the VlanTrunk port."
        INDEX   { unisifVLANTrunkIndex }
        ::= { unisifVLANTrunkStatusTable 1}

    UnisIfVLANTrunkStatusEntry    ::=
    SEQUENCE {
        unisifVLANTrunkIndex              InterfaceIndex,
        unisifVLANTrunkGvrpRegistration   INTEGER,
        unisifVLANTrunkPassListLow        OCTET STRING,
        unisifVLANTrunkPassListHigh       OCTET STRING,
        unisifVLANTrunkAllowListLow       OCTET STRING,
        unisifVLANTrunkAllowListHigh      OCTET STRING
        }



    unisifVLANTrunkIndex  OBJECT-TYPE
        SYNTAX  InterfaceIndex
        MAX-ACCESS read-only
        STATUS current
        DESCRIPTION "Index number of the VLANTrunk interface."
        ::= { unisifVLANTrunkStatusEntry 1 }


    unisifVLANTrunkGvrpRegistration OBJECT-TYPE
        SYNTAX  INTEGER
        {
        normal  (1),
        fixed   (2),
        forbidden   (3)
        }
        MAX-ACCESS read-write
        STATUS current
        DESCRIPTION
            "GVRP registration information
            normal:     This is the default configuration. Allow create, register
                        and unregister vlans dynamiclly at this port.
            fixed:      Aallow create and register vlan manually at this port.
                        Prevent from unregistering vlans or registering known
                        vlans of this port at another trunk port.
            forbidden:  Unregister all vlans but vlan 1, forbid to create or
                        register any other vlans at this port."
        ::= { unisifVLANTrunkStatusEntry 2 }


    unisifVLANTrunkPassListLow OBJECT-TYPE
        SYNTAX  OCTET STRING
        MAX-ACCESS read-only
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each actually
                    passed VLAN of the trunk port is represented by a single
                    bit within the value of this object. If that bit has a
                    value of '1' then that VLAN is actually passed in the set
                    of VLANs; the VLAN is not actually passed if its bit has
                    a value of '0'."
        ::= { unisifVLANTrunkStatusEntry 4 }

    unisifVLANTrunkPassListHigh OBJECT-TYPE
        SYNTAX  OCTET STRING
        MAX-ACCESS read-only
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each actually
                    passed VLAN of the trunk port is represented by a single
                    bit within the value of this object. If that bit has a
                    value of '1' then that VLAN is actually passed in the set
                    of VLANs; the VLAN is not actually passed if its bit has
                    a value of '0'."
        ::= { unisifVLANTrunkStatusEntry 5 }

    unisifVLANTrunkAllowListLow OBJECT-TYPE
        SYNTAX  OCTET STRING
        MAX-ACCESS read-write
        STATUS current
        DESCRIPTION "Each octet within this value specifies a set of eight
                    VLANs, with the first octet specifying VLANs 1 through
                    8, the second octet specifying VLANs 9 through 16, etc.
                    Within each octet, the most significant bit represents
                    the highest numbered VLAN, and the least significant bit
                    represents the lowest numbered VLAN. Thus, each allowed
                    VLAN of the trunk port is represented by a single bit
                    within the value of this object. If that bit has a value
                    of '1' then that VLAN is allowed in the set of VLANs;
                    the VLAN is not allowed if its bit has a value of '0'."
        ::= { unisifVLANTrunkStatusEntry 6 }

    unisifVLANTrunkAllowListHigh OBJECT-TYPE
        SYNTAX  OCTET STRING
        MAX-ACCESS read-write
        STATUS current
        DESCRIPTION "Each octet within this value specifies a set of eight
                    VLANs, with the first octet specifying VLANs 2049 through
                    2056, the second octet specifying VLANs 2057 through 2064,
                    etc. Within each octet, the most significant bit represents
                    the highest numbered VLAN, and the least significant bit
                    represents the lowest numbered VLAN. Thus, each allowed
                    VLAN of the trunk port is represented by a single bit within
                    the value of this object. If that bit has a value of '1'
                    then that VLAN is allowed in the set of VLANs; the VLAN is
                    not allowed if its bit has a value of '0'."
        ::= { unisifVLANTrunkStatusEntry 7 }




    unisethernetTable  OBJECT-TYPE
        SYNTAX SEQUENCE OF UnisEthernetEntry
        MAX-ACCESS not-accessible
        STATUS current
        DESCRIPTION "Ethernet port attribute table."
        ::= { unisLswL2InfMibObject  4 }


    unisethernetEntry  OBJECT-TYPE
        SYNTAX UnisEthernetEntry
        MAX-ACCESS not-accessible
        STATUS current
        DESCRIPTION "Entries of Ethernet port attribute table"
        INDEX { ifIndex }
        ::= { unisethernetTable 1}

    UnisEthernetEntry ::=
    SEQUENCE {
        unisifEthernetDuplex          INTEGER,
        unisifEthernetMTU             INTEGER,
        unisifEthernetSpeed           INTEGER,
        unisifEthernetMdi             INTEGER,
        unisMaxMacLearn               INTEGER,
        unisifMacAddressLearn         INTEGER,
        unisifEthernetTest            INTEGER,
        unisifMacAddrLearnMode        INTEGER,
        unisifEthernetFlowInterval    INTEGER,
        unisifEthernetIsolate         OCTET STRING,
        unisifVlanVPNStatus           INTEGER,
        unisifVlanVPNUplinkStatus     INTEGER,
        unisifVlanVPNTPID             Integer32,
        unisifIsolateGroupID          Integer32,
        unisifisUplinkPort            INTEGER,
        unisifEthernetAutoSpeedMask   SpeedModeFlag,
        unisifEthernetAutoSpeed       SpeedModeFlag
        }

    unisifEthernetDuplex OBJECT-TYPE
        SYNTAX  INTEGER
        {
        full    (1),
        half    (2),
        auto    (3)
        }
        MAX-ACCESS read-write
        STATUS current
        DESCRIPTION "Ethernet interface mode."
        ::= { unisethernetEntry 3 }


    unisifEthernetMTU  OBJECT-TYPE
        SYNTAX  INTEGER
        MAX-ACCESS read-write
        STATUS current
        DESCRIPTION "MTU on the Ethernet interface."
        ::= { unisethernetEntry 4 }


    unisifEthernetSpeed OBJECT-TYPE
        SYNTAX  INTEGER
        {
        auto    (0),
        s10M    (10),
        s100M   (100),
        s1000M  (1000),
        s2500M  (2500),
        s5000M  (5000),
        s10000M (10000),
        s24000M (24000),
        s40000M (40000),
        s20000M (20000),
        s25000M (25000),
        s50000M (50000),
        s100000M (100000),
        s200000M (200000),
        s400000M (400000)
        }
        MAX-ACCESS read-write
        STATUS current
        DESCRIPTION "Ethernet interface speed."
        ::= { unisethernetEntry 5 }

    unisifEthernetMdi OBJECT-TYPE
        SYNTAX  INTEGER
        {
        mdi-ii   (1),
        mdi-x   (2),
        mdi-auto   (3)
        }
        MAX-ACCESS read-write
        STATUS current
        DESCRIPTION
            "Type of the line connected to the port.
            MDI-II (straight-through cable): 1
            MDI-X (crossover cable): 2
            MDI-AUTO (auto-sensing): 3"
        ::= { unisethernetEntry 7 }

    unisMaxMacLearn OBJECT-TYPE
        SYNTAX  INTEGER(-1..2147483647)
        MAX-ACCESS read-write
        STATUS current
        DESCRIPTION
            "The maximum number of MAC addresses that the port can learn.
            The value -1 means that the number of Mac addresses that the port
            can learn is unlimited."
        ::= { unisethernetEntry 8 }

    unisifMacAddressLearn OBJECT-TYPE
        SYNTAX  INTEGER
        {
            enabled(1),
            disabled(2)
        }
        MAX-ACCESS read-only
        STATUS current
        DESCRIPTION
            "This object indicates if the interface is allowed to learn mac address.
            eanbled(1) means the interface can learn mac address, otherwise disabled(2)
            can be set."
        ::= { unisethernetEntry 9 }

    unisifEthernetTest OBJECT-TYPE
        SYNTAX  INTEGER
        {
            test(1)
        }
        MAX-ACCESS read-write
        STATUS current
        DESCRIPTION
            "Test this interface.
            The actual testing will be different according to products.
            Read operation not supported."
        ::= { unisethernetEntry 10 }

    unisifMacAddrLearnMode OBJECT-TYPE
        SYNTAX  INTEGER
        {
            iVL(1),
            sVL(2)
        }
        MAX-ACCESS read-only
        STATUS current
        DESCRIPTION
            "Status indicates mac address learn mode of the interface.
            IVL(1) means independent VLAN learning.
            SVL means shared VLAN learning."
        ::= { unisethernetEntry 11 }

    unisifEthernetFlowInterval OBJECT-TYPE
        SYNTAX  INTEGER (5..300)
        MAX-ACCESS read-write
        STATUS current
        DESCRIPTION
            "Set flow interval of the ethernet.
            The NMS should set value to integer which is a multiple of 5."
        ::= { unisethernetEntry 12 }

    unisifEthernetIsolate  OBJECT-TYPE
        SYNTAX  OCTET STRING
        MAX-ACCESS read-write
        STATUS current
        DESCRIPTION
            "Isolate group means that all ports in the same isolate group can not
            send and receive packets each other.
            Each octet within this value specifies a set of eight isolate groups,
            with the first octet specifying isolate groups 1 through 8,  the second
            octet specifying isolate groups 9 through 16, etc. Within each octet,
            the leftmost bit is the first bit.
            the first bit represents the lowest numbered isolate group, and the
            last bit represents the highest numbered isolate group. one port can
            belong to more than one isolate group.
            Thus, each isolate group is represented by a single bit within the
            value of this object.
            If that bit has a value of '1', then that isolate group includes this port;
            the port is not included if its bit has a value of '0'.
            for example, the first octet is '10000100' means that the port is
            included in the isolate group 1 and isolate group 6."
        ::= { unisethernetEntry 13 }

    unisifVlanVPNStatus OBJECT-TYPE
        SYNTAX  INTEGER
        {
             enabled(1),
             disabled(2)
        }
        MAX-ACCESS read-write
        STATUS current
        DESCRIPTION "Vlan VPN enable status."
        ::= { unisethernetEntry 14 }

    unisifVlanVPNUplinkStatus OBJECT-TYPE
        SYNTAX  INTEGER
        {
             enabled(1),
             disabled(2)
        }
        MAX-ACCESS read-write
        STATUS current
        DESCRIPTION "Vlan VPN uplink status."
        ::= { unisethernetEntry 15 }

    unisifVlanVPNTPID OBJECT-TYPE
        SYNTAX  Integer32 (1..65535)
        MAX-ACCESS read-write
        STATUS current
        DESCRIPTION
            "Port based Vlan VPN TPID(Tag Protocol Indentifier), default value
            is 0x8100.
            Please refer to unisVlanVPNTPIDMode to get more information."
        ::= { unisethernetEntry 16 }

    unisifIsolateGroupID OBJECT-TYPE
        SYNTAX  Integer32
        MAX-ACCESS read-write
        STATUS current
        DESCRIPTION
            "Isolate group identifier. Value zero means this interface does not
            belong to any isolate group."
        ::= { unisethernetEntry 17 }

    unisifisUplinkPort OBJECT-TYPE
        SYNTAX  INTEGER
        {
             yes(1),
             no(2)
        }
        MAX-ACCESS read-only
        STATUS current
        DESCRIPTION
            "Ethernet uplink status, default value is 2."
        ::= { unisethernetEntry 18 }

    unisifEthernetAutoSpeedMask OBJECT-TYPE
        SYNTAX  SpeedModeFlag
        MAX-ACCESS read-only
        STATUS current
        DESCRIPTION
            "This object specifies which kinds of speed mode can be negotiated.
            Each bit corresponds to a kind of speed mode.

            If the value of a bit is '1', it means the corresponding speed mode
            is negotiable on the port. Otherwise the negotiation for that
            kind of speed mode is not supported on this port. If there are
            several negotiable speed modes, all bits for them  are '1'.
            For example, if the speed mode 's10M' and 's1000M' can be negotiable,
            the value of this object is 0xA0."
        ::= { unisethernetEntry 19 }

    unisifEthernetAutoSpeed OBJECT-TYPE
        SYNTAX  SpeedModeFlag
        MAX-ACCESS read-write
        STATUS  current
        DESCRIPTION
            "This object indicates which kinds of speed mode are negotiable
            on this port.

            Only when a bit of unisifEthernetAutoSpeedMask is '1', the corresponding
            bit of this object can be set to '1', indicating the corresponding
            speed mode is negotiable.

            For example, if the value of unisifEthernetAutoSpeedMask is 0xA0,
            which indicates speed mode 's10M' and 's1000M' are negotiable,
            the possible value of this object should be one of the four values
            (0x00, 0x20, 0x80 and 0xA0).

            If the value of unisifEthernetSpeed is not 'auto', the value of this
            object is insignificant and should be ignored. The value length of
            this object should be as long as that of unisifEthernetAutoSpeedMask."
        ::= { unisethernetEntry 20 }

    unisIsolateGroupMax  OBJECT-TYPE
        SYNTAX  Integer32
        MAX-ACCESS read-only
        STATUS current
        DESCRIPTION
            "Max isolate group that this device support, the value is zero
            means that the device does not support isolate group."
        ::= { unisLswL2InfMibObject  5 }

   unisGlobalBroadcastMaxPps   OBJECT-TYPE
        SYNTAX INTEGER   (0..14881000)
        MAX-ACCESS read-write
        STATUS  current
        DESCRIPTION
            "The global max packets per second. When it is set, the value of
            BroadcastMaxPps in all ports will be changed to that setting."
        ::= { unisLswL2InfMibObject 6 }

  unisGlobalBroadcastMaxRatio OBJECT-TYPE
        SYNTAX INTEGER (0..100)
        MAX-ACCESS read-write
        STATUS  current
        DESCRIPTION
            "The global max-ratio of broadcast from 0 to 100 percent.
            When it is set, the value of BroadcastMaxRatio in all ports
            will be changed to that setting."
        ::= { unisLswL2InfMibObject 7  }

    unisBpduTunnelStatus  OBJECT-TYPE
        SYNTAX  INTEGER
        {
             enabled(1),
             disabled(2)
        }
        MAX-ACCESS read-write
        STATUS current
        DESCRIPTION "Bpdu tunnel enable status."
        ::= { unisLswL2InfMibObject  8 }

   unisVlanVPNTPIDMode OBJECT-TYPE
        SYNTAX  INTEGER
        {
             port-based(1),
             global(2)
        }
        MAX-ACCESS read-only
        STATUS current
        DESCRIPTION
            "Vlan VPN TPID mode.

            The value 'port-based' means VLAN VPN TPID value would be set based
            on port via unisifVlanVPNTPID. In this situation, unisVlanVPNTPID is
            meaningless and always return 0x8100.

            The value 'global' means VLAN VPN TPID value should be set globally
            via unisVlanVPNTPID. In this situation, unisifVlanVPNTPID in unisethernetTable
            has the same value with unisVlanVPNTPID."
      ::= { unisLswL2InfMibObject  9 }

   unisVlanVPNTPID OBJECT-TYPE
        SYNTAX  Integer32 (1..65535)
        MAX-ACCESS read-write
        STATUS current
        DESCRIPTION
            "Global Vlan VPN TPID(Tag Protocol Indentifier), default value
            is 0x8100."
        ::= { unisLswL2InfMibObject  10 }

   unisPortIsolateGroupTable  OBJECT-TYPE
        SYNTAX SEQUENCE OF UnisPortIsolateGroupEntry
        MAX-ACCESS not-accessible
        STATUS current
        DESCRIPTION "Isolate Group attribute table."
        ::= { unisLswL2InfMibObject  11 }


   unisPortIsolateGroupEntry  OBJECT-TYPE
        SYNTAX UnisPortIsolateGroupEntry
        MAX-ACCESS not-accessible
        STATUS current
        DESCRIPTION "The entry of unisPortIsolateGroupTable."
        INDEX    { unisPortIsolateGroupIndex }
        ::= { unisPortIsolateGroupTable 1 }

    UnisPortIsolateGroupEntry ::=
    SEQUENCE {
        unisPortIsolateGroupIndex              Integer32,
        unisPortIsolateUplinkIfIndex           InterfaceIndex,
        unisPortIsolateGroupRowStatus          RowStatus,
        unisPortIsolateGroupDescription        DisplayString
        }

   unisPortIsolateGroupIndex OBJECT-TYPE
        SYNTAX  Integer32
        MAX-ACCESS not-accessible
        STATUS current
        DESCRIPTION
            "Port isolate group identifier.
            The index of the unisPortIsolateGroupTable.
            The value ranges from 1 to the limit of isolate group quantity."
        ::= { unisPortIsolateGroupEntry 1 }

   unisPortIsolateUplinkIfIndex  OBJECT-TYPE
        SYNTAX  InterfaceIndex
        MAX-ACCESS read-create
        STATUS current
        DESCRIPTION "Index number of the uplink interface."
        ::= { unisPortIsolateGroupEntry 2 }

    unisPortIsolateGroupRowStatus OBJECT-TYPE
        SYNTAX  RowStatus
        MAX-ACCESS read-create
        STATUS current
        DESCRIPTION
            "Current operation status of the row."
        ::= { unisPortIsolateGroupEntry  3 }

    unisPortIsolateGroupDescription OBJECT-TYPE
        SYNTAX  DisplayString (SIZE(0..80))
        MAX-ACCESS read-create
        STATUS current
        DESCRIPTION
            "Port isolate group description, default value is zero-length string."
        ::= { unisPortIsolateGroupEntry 4 }

    unisMaxMacLearnRange OBJECT-TYPE
        SYNTAX  Integer32
        MAX-ACCESS read-only
        STATUS current
        DESCRIPTION "The maximum number of MAC address that the port supports."
        ::= { unisLswL2InfMibObject  12 }


    unisifPortProtocolStatTable  OBJECT-TYPE
        SYNTAX SEQUENCE OF UnisifPortProtocolStatEntry
        MAX-ACCESS not-accessible
        STATUS current
        DESCRIPTION
            "This table contains objects of port statistics information based on
            IPv4 and IPv6 protocols."
        ::= { unisLswL2InfMibObject  13 }

    unisifPortProtocolStatEntry  OBJECT-TYPE
        SYNTAX UnisifPortProtocolStatEntry
        MAX-ACCESS not-accessible
        STATUS current
        DESCRIPTION "The entry of unisifPortProtocolStatTable."
        INDEX    { ifIndex }
        ::= { unisifPortProtocolStatTable 1 }

    UnisifPortProtocolStatEntry ::=
        SEQUENCE {
            unisifIPv4InOctets                        Counter64,
            unisifIPv4InUcastPkts                     Counter64,
            unisifIPv4InMultiPkts                     Counter64,
            unisifIPv4InBroadcastPkts                 Counter64,
            unisifIPv4InDiscards                      Counter64,
            unisifIPv4InErrors                        Counter64,
            unisifIPv4OutOctets                       Counter64,
            unisifIPv4OutUcastPkts                    Counter64,
            unisifIPv4OutMultiPkts                    Counter64,
            unisifIPv4OutBroadcastPkts                Counter64,
            unisifIPv4OutDiscards                     Counter64,
            unisifIPv4OutErrors                       Counter64,
            unisifIPv6InOctets                        Counter64,
            unisifIPv6InUcastPkts                     Counter64,
            unisifIPv6InMultiPkts                     Counter64,
            unisifIPv6InAnycastPkts                   Counter64,
            unisifIPv6InDiscards                      Counter64,
            unisifIPv6InErrors                        Counter64,
            unisifIPv6OutOctets                       Counter64,
            unisifIPv6OutUcastPkts                    Counter64,
            unisifIPv6OutMultiPkts                    Counter64,
            unisifIPv6OutAnycastPkts                  Counter64,
            unisifIPv6OutDiscards                     Counter64,
            unisifIPv6OutErrors                       Counter64
        }
    unisifIPv4InOctets OBJECT-TYPE
        SYNTAX  Counter64
        MAX-ACCESS read-only
        STATUS current
        DESCRIPTION
            "Number of octets based on IPv4 received on the interface."
        ::= { unisifPortProtocolStatEntry 1 }

    unisifIPv4InUcastPkts OBJECT-TYPE
        SYNTAX  Counter64
        MAX-ACCESS read-only
        STATUS current
        DESCRIPTION
            "Number of unicast packets based on IPv4 received on the interface."
        ::= { unisifPortProtocolStatEntry 2 }

    unisifIPv4InMultiPkts OBJECT-TYPE
        SYNTAX  Counter64
        MAX-ACCESS read-only
        STATUS current
        DESCRIPTION
            "Number of multicast packets based on IPv4 received on the interface."
        ::= { unisifPortProtocolStatEntry 3 }

    unisifIPv4InBroadcastPkts OBJECT-TYPE
        SYNTAX  Counter64
        MAX-ACCESS read-only
        STATUS current
        DESCRIPTION
            "Number of broadcast packets based on IPv4 received on the interface."
        ::= { unisifPortProtocolStatEntry 4 }

    unisifIPv4InDiscards OBJECT-TYPE
        SYNTAX  Counter64
        MAX-ACCESS read-only
        STATUS current
        DESCRIPTION
            "Number of discard packets based on IPv4 received on the interface."
        ::= { unisifPortProtocolStatEntry 5 }

    unisifIPv4InErrors OBJECT-TYPE
        SYNTAX  Counter64
        MAX-ACCESS read-only
        STATUS current
        DESCRIPTION
            "Number of error packets based on IPv4 received on the interface."
        ::= { unisifPortProtocolStatEntry 6 }

    unisifIPv4OutOctets OBJECT-TYPE
        SYNTAX  Counter64
        MAX-ACCESS read-only
        STATUS current
        DESCRIPTION
            "Number of octets based on IPv4 transmitted out of the interface."
        ::= { unisifPortProtocolStatEntry  7 }

    unisifIPv4OutUcastPkts OBJECT-TYPE
        SYNTAX  Counter64
        MAX-ACCESS read-only
        STATUS current
        DESCRIPTION
            "Number of unicast packets based on IPv4 transmitted out of the
            interface."
        ::= { unisifPortProtocolStatEntry  8 }

    unisifIPv4OutMultiPkts OBJECT-TYPE
        SYNTAX  Counter64
        MAX-ACCESS read-only
        STATUS current
        DESCRIPTION
            "Number of multicast packets based on IPv4 transmitted out of the
            interface."
        ::= { unisifPortProtocolStatEntry 9 }

    unisifIPv4OutBroadcastPkts OBJECT-TYPE
        SYNTAX  Counter64
        MAX-ACCESS read-only
        STATUS current
        DESCRIPTION
            "Number of broadcast packets based on IPv4 transmitted out of the
            interface."
        ::= { unisifPortProtocolStatEntry 10 }

    unisifIPv4OutDiscards OBJECT-TYPE
        SYNTAX  Counter64
        MAX-ACCESS read-only
        STATUS current
        DESCRIPTION
            "Number of discard packets based on IPv4 transmitted out of the
            interface."
        ::= { unisifPortProtocolStatEntry 11 }

    unisifIPv4OutErrors OBJECT-TYPE
        SYNTAX  Counter64
        MAX-ACCESS read-only
        STATUS current
        DESCRIPTION
            "Number of error packets based on IPv4 transmitted out of the
            interface."
        ::= { unisifPortProtocolStatEntry 12 }

    unisifIPv6InOctets OBJECT-TYPE
        SYNTAX  Counter64
        MAX-ACCESS read-only
        STATUS current
        DESCRIPTION
            "Number of octets based on IPv6 received on the interface."
        ::= { unisifPortProtocolStatEntry 13 }

    unisifIPv6InUcastPkts OBJECT-TYPE
        SYNTAX  Counter64
        MAX-ACCESS read-only
        STATUS current
        DESCRIPTION
            "Number of unicast packets based on IPv6 received on the interface."
        ::= { unisifPortProtocolStatEntry 14 }

    unisifIPv6InMultiPkts OBJECT-TYPE
        SYNTAX  Counter64
        MAX-ACCESS read-only
        STATUS current
        DESCRIPTION
            "Number of multicast packets based on IPv6 received on the interface."
        ::= { unisifPortProtocolStatEntry 15 }

    unisifIPv6InAnycastPkts OBJECT-TYPE
        SYNTAX  Counter64
        MAX-ACCESS read-only
        STATUS current
        DESCRIPTION
            "Number of anycast packets based on IPv6 received on the interface."
        ::= { unisifPortProtocolStatEntry 16 }

    unisifIPv6InDiscards OBJECT-TYPE
        SYNTAX  Counter64
        MAX-ACCESS read-only
        STATUS current
        DESCRIPTION
            "Number of discard packets based on IPv6 received on the interface."
        ::= { unisifPortProtocolStatEntry 17 }

    unisifIPv6InErrors OBJECT-TYPE
        SYNTAX  Counter64
        MAX-ACCESS read-only
        STATUS current
        DESCRIPTION
            "Number of error packets based on IPv6 received on the interface."
        ::= { unisifPortProtocolStatEntry 18 }

    unisifIPv6OutOctets OBJECT-TYPE
        SYNTAX  Counter64
        MAX-ACCESS read-only
        STATUS current
        DESCRIPTION
            "Number of octets based on IPv6 transmitted of the interface."
        ::= { unisifPortProtocolStatEntry  19 }

    unisifIPv6OutUcastPkts OBJECT-TYPE
        SYNTAX  Counter64
        MAX-ACCESS read-only
        STATUS current
        DESCRIPTION
            "Number of unicast packets based on IPv6 transmitted out of the
            interface."
        ::= { unisifPortProtocolStatEntry  20 }

    unisifIPv6OutMultiPkts OBJECT-TYPE
        SYNTAX  Counter64
        MAX-ACCESS read-only
        STATUS current
        DESCRIPTION
            "Number of multicast packets based on IPv6 transmitted out of the
            interface."
        ::= { unisifPortProtocolStatEntry 21 }

    unisifIPv6OutAnycastPkts OBJECT-TYPE
        SYNTAX  Counter64
        MAX-ACCESS read-only
        STATUS current
        DESCRIPTION
            "Number of anycast packets based on IPv6 transmitted out of the
            interface."
        ::= { unisifPortProtocolStatEntry 22 }

    unisifIPv6OutDiscards OBJECT-TYPE
        SYNTAX  Counter64
        MAX-ACCESS read-only
        STATUS current
        DESCRIPTION
            "Number of discard packets based on IPv6 transmitted out of the
            interface."
        ::= { unisifPortProtocolStatEntry 23 }

    unisifIPv6OutErrors OBJECT-TYPE
        SYNTAX  Counter64
        MAX-ACCESS read-only
        STATUS current
        DESCRIPTION
            "Number of error packets based on IPv6 transmitted out of the
            interface."
        ::= { unisifPortProtocolStatEntry 24 }
END
