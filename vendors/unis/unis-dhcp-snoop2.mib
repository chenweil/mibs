-- =========================================================================
-- Copyright (c) 2020 Unisyue Technologies Co., Ltd.  All rights reserved.
--
-- Description: DHCP Snooping MIB 2
-- Reference:
-- Version:     V1.3
-- History:
-- V1.0 The initial version, created by lilin, 2012.05.15
-- V1.1 Modified the mib description by lilin, 2013.04.15
-- V1.2 Modified unisDhcpSnoop2IfMaxLearnNum by yuguoqing, 2014.03.20
-- V1.3 Modified unisDhcpSnoop2IfOpt82CIDMode by heminhong, 2017.01.13
-- =========================================================================
UNIS-DHCP-SNOOP2-MIB DEFINITIONS ::= BEGIN

-- =========================================================================
-- Imported variables and types
-- =========================================================================
IMPORTS
    TruthValue, RowStatus, MacAddress
        FROM SNMPv2-TC
    MODULE-IDENTITY, OBJECT-TYPE, Counter64, Unsigned32
        FROM SNMPv2-SMI
    ifIndex, InterfaceIndexOrZero
        FROM IF-MIB
    InetAddressIPv4
        FROM INET-ADDRESS-MIB
    unisCommon
        FROM UNIS-OID-MIB;

-- =========================================================================
-- Module identity
-- =========================================================================
unisDhcpSnoop2 MODULE-IDENTITY
    LAST-UPDATED "201701130000Z"
    ORGANIZATION
        "Unisyue Technologies Co., Ltd."
    CONTACT-INFO
        ""
    DESCRIPTION "DHCP SNOOPING MIB 2"
    REVISION
        "201701130000Z"
    DESCRIPTION
        "Modified to add 'unisDhcpSnoop2IfOpt82CIDMode' mode."
    REVISION
         "201304150000Z"
    DESCRIPTION
        "The private MIB file includes the DHCP Snooping profile."
    ::= { unisCommon  124 }

-- ==========================================================================
-- Scalar objects definition
-- ==========================================================================
    unisDhcpSnoop2ScalarObjects OBJECT IDENTIFIER ::= {  unisDhcpSnoop2 1  }

-- ==================================================================
-- unisDhcpSnoop2ScalarObjects: unisDhcpSnoop2ConfigGroup
-- ==================================================================
unisDhcpSnoop2ConfigGroup   OBJECT IDENTIFIER ::= { unisDhcpSnoop2ScalarObjects 1 }

unisDhcpSnoop2Enabled OBJECT-TYPE
    SYNTAX     TruthValue
    MAX-ACCESS read-write
    STATUS     current
    DESCRIPTION
        "If the value of this object is set to 'true',
         DHCP snooping is enabled."
    DEFVAL { false }
    ::= { unisDhcpSnoop2ConfigGroup 1 }

unisDhcpSnoop2BindDbName OBJECT-TYPE
    SYNTAX     OCTET STRING(SIZE(0..512))
    MAX-ACCESS read-write
    STATUS     current
    DESCRIPTION
        "Name of the file that used to store binding information.

         If the value of the object is set to a zero-length string,
         the configuration will be removed."
    ::= { unisDhcpSnoop2ConfigGroup 2 }

unisDhcpSnoop2BindRefreshIntvl OBJECT-TYPE
    SYNTAX     Unsigned32(60..864000)
    MAX-ACCESS read-write
    STATUS     current
    DESCRIPTION
        "The refresh interval of the binding information in seconds."
    DEFVAL { 300 }
    ::= { unisDhcpSnoop2ConfigGroup 3 }

unisDhcpSnoop2BindRefresh OBJECT-TYPE
    SYNTAX     INTEGER
    {
        on(1)
    }
    MAX-ACCESS read-write
    STATUS     current
    DESCRIPTION
        "If the value of this object is set to 'on', the binding
         information will be refreshed immediately."
    ::= { unisDhcpSnoop2ConfigGroup 4 }

-- ==================================================================
-- unisDhcpSnoop2ScalarObjects: unisDhcpSnoop2StatisticsGroup
-- ==================================================================
unisDhcpSnoop2StatisticsGroup   OBJECT IDENTIFIER ::= { unisDhcpSnoop2ScalarObjects 2 }

unisDhcpSnoop2PktSentNum OBJECT-TYPE
    SYNTAX      Counter64
    MAX-ACCESS  read-only
    STATUS      current
    DESCRIPTION
        "The total number of the packets send by DHCP snooping."
    ::= { unisDhcpSnoop2StatisticsGroup 1 }

unisDhcpSnoop2PktRcvNum OBJECT-TYPE
    SYNTAX      Counter64
    MAX-ACCESS  read-only
    STATUS      current
    DESCRIPTION
        "The total number of the packets received by
         DHCP snooping."
    ::= { unisDhcpSnoop2StatisticsGroup 2 }

unisDhcpSnoop2PktDropNum OBJECT-TYPE
    SYNTAX      Counter64
    MAX-ACCESS  read-only
    STATUS      current
    DESCRIPTION
        "The total number of the packets dropped by
         DHCP snooping."
    ::= { unisDhcpSnoop2StatisticsGroup 3 }

-- ==========================================================================
-- Table definition
-- ==========================================================================
    unisDhcpSnoop2Tables OBJECT IDENTIFIER ::= {  unisDhcpSnoop2 2  }

-- ==========================================================================
-- 1st Table of unisDhcpSnoop2Tables: unisDhcpSnoop2BindTable
-- ==========================================================================
unisDhcpSnoop2BindTable OBJECT-TYPE
    SYNTAX     SEQUENCE OF UnisDhcpSnoop2BindEntry
    MAX-ACCESS not-accessible
    STATUS     current
    DESCRIPTION
        "The table containing information of DHCP clients listened by
         DHCP snooping."
    ::= { unisDhcpSnoop2Tables 1 }

unisDhcpSnoop2BindEntry OBJECT-TYPE
    SYNTAX     UnisDhcpSnoop2BindEntry
    MAX-ACCESS not-accessible
    STATUS     current
    DESCRIPTION
        "An entry containing information of DHCP clients."
    INDEX
        {
            unisDhcpSnoop2BindIpAddr,
            unisDhcpSnoop2BindVlanId,
            unisDhcpSnoop2BindSecVlanId
        }
    ::= { unisDhcpSnoop2BindTable 1 }

UnisDhcpSnoop2BindEntry ::=
    SEQUENCE
        {
            unisDhcpSnoop2BindIpAddr           InetAddressIPv4,
            unisDhcpSnoop2BindVlanId           Unsigned32,
            unisDhcpSnoop2BindSecVlanId        Unsigned32,
            unisDhcpSnoop2BindMacAddr          MacAddress,
            unisDhcpSnoop2BindLease            Unsigned32,
            unisDhcpSnoop2BindPortIndex        InterfaceIndexOrZero,
            unisDhcpSnoop2BindRowStatus        RowStatus
        }

unisDhcpSnoop2BindIpAddr OBJECT-TYPE
    SYNTAX     InetAddressIPv4
    MAX-ACCESS not-accessible
    STATUS     current
    DESCRIPTION
        "DHCP client's IP addresses collected by DHCP snooping."
    ::= { unisDhcpSnoop2BindEntry 1 }

unisDhcpSnoop2BindVlanId OBJECT-TYPE
    SYNTAX     Unsigned32(1..4094)
    MAX-ACCESS not-accessible
    STATUS     current
    DESCRIPTION
        "DHCP client's VLAN ID collected by DHCP snooping."
    ::= { unisDhcpSnoop2BindEntry 2 }

unisDhcpSnoop2BindSecVlanId OBJECT-TYPE
    SYNTAX     Unsigned32(1..4094 | 65535)
    MAX-ACCESS not-accessible
    STATUS     current
    DESCRIPTION
        "DHCP client's second VLAN ID collected by DHCP snooping.
         65535 means no second VLAN."
    ::= { unisDhcpSnoop2BindEntry 3 }

unisDhcpSnoop2BindMacAddr OBJECT-TYPE
    SYNTAX     MacAddress
    MAX-ACCESS read-only
    STATUS     current
    DESCRIPTION
        "DHCP client's MAC address collected by DHCP snooping."
    ::= { unisDhcpSnoop2BindEntry 4 }

unisDhcpSnoop2BindLease OBJECT-TYPE
    SYNTAX     Unsigned32
    MAX-ACCESS read-only
    STATUS     current
    DESCRIPTION
        "Left lease time in seconds collected by DHCP snooping.
         The value of this object cannot be 0."
    ::= { unisDhcpSnoop2BindEntry 5 }

unisDhcpSnoop2BindPortIndex OBJECT-TYPE
    SYNTAX     InterfaceIndexOrZero
    MAX-ACCESS read-only
    STATUS     current
    DESCRIPTION
        "DHCP client's port index collected by DHCP snooping.
         The value of zero means unknown port."
    ::= { unisDhcpSnoop2BindEntry 6 }

unisDhcpSnoop2BindRowStatus    OBJECT-TYPE
     SYNTAX      RowStatus
     MAX-ACCESS  read-create
     STATUS      current
     DESCRIPTION
         "RowStatus.  Only destroy action is allow to use."
     ::= { unisDhcpSnoop2BindEntry 7 }

-- ==========================================================================
-- 2nd Table of unisDhcpSnoop2Tables: unisDhcpSnoop2IfConfigTable
-- ==========================================================================
unisDhcpSnoop2IfConfigTable OBJECT-TYPE
    SYNTAX     SEQUENCE OF UnisDhcpSnoop2IfConfigEntry
    MAX-ACCESS not-accessible
    STATUS     current
    DESCRIPTION
        "A table is used to configure DHCP snooping functions on ports."
    ::= {unisDhcpSnoop2Tables 2 }

unisDhcpSnoop2IfConfigEntry OBJECT-TYPE
    SYNTAX     UnisDhcpSnoop2IfConfigEntry
    MAX-ACCESS not-accessible
    STATUS     current
    DESCRIPTION
        "An entry containing DHCP snooping configurations of ports."
    INDEX   { ifIndex }
    ::= {unisDhcpSnoop2IfConfigTable 1}

UnisDhcpSnoop2IfConfigEntry  ::=
    SEQUENCE
        {
            unisDhcpSnoop2IfTrustStatus                INTEGER,
            unisDhcpSnoop2IfCheckMac                   TruthValue,
            unisDhcpSnoop2IfCheckRequest               TruthValue,
            unisDhcpSnoop2IfRateLimit                  Unsigned32,
            unisDhcpSnoop2IfRecordBind                 TruthValue,
            unisDhcpSnoop2IfMaxLearnNum                Unsigned32,
            unisDhcpSnoop2IfOpt82Enable                TruthValue,
            unisDhcpSnoop2IfOpt82Strategy              INTEGER,
            unisDhcpSnoop2IfOpt82CIDMode               INTEGER,
            unisDhcpSnoop2IfOpt82CIDNodeType           INTEGER,
            unisDhcpSnoop2IfOpt82CIDNodeStr            OCTET STRING,
            unisDhcpSnoop2IfOpt82CIDStr                OCTET STRING,
            unisDhcpSnoop2IfOpt82CIDFormat             INTEGER,
            unisDhcpSnoop2IfOpt82RIDMode               INTEGER,
            unisDhcpSnoop2IfOpt82RIDStr                OCTET STRING,
            unisDhcpSnoop2IfOpt82RIDFormat             INTEGER
        }

unisDhcpSnoop2IfTrustStatus OBJECT-TYPE
    SYNTAX     INTEGER
    {
        untrusted(0),
        trusted(1)
    }
    MAX-ACCESS read-write
    STATUS     current
    DESCRIPTION
        "Trusted status of the port."
    DEFVAL { untrusted }
    ::= { unisDhcpSnoop2IfConfigEntry 1 }

unisDhcpSnoop2IfCheckMac OBJECT-TYPE
    SYNTAX      TruthValue
    MAX-ACCESS  read-write
    STATUS      current
    DESCRIPTION
        "If the value is 'true', MAC address of DHCP packets received
         on the port will be checked."
    DEFVAL { false }
    ::= { unisDhcpSnoop2IfConfigEntry 2 }

unisDhcpSnoop2IfCheckRequest OBJECT-TYPE
    SYNTAX     TruthValue
    MAX-ACCESS read-write
    STATUS     current
    DESCRIPTION
        "If the value is 'true', DHCP request packets will be checked."
    DEFVAL { false }
    ::= { unisDhcpSnoop2IfConfigEntry 3 }

unisDhcpSnoop2IfRateLimit OBJECT-TYPE
    SYNTAX     Unsigned32
    MAX-ACCESS read-write
    STATUS     current
    DESCRIPTION
        "The rate limit in Kbps.
         If the value is 0, there is no rate limit on the port."
    DEFVAL { 0 }
    ::= { unisDhcpSnoop2IfConfigEntry 4 }

unisDhcpSnoop2IfRecordBind OBJECT-TYPE
    SYNTAX     TruthValue
    MAX-ACCESS read-write
    STATUS     current
    DESCRIPTION
        "If the value is 'true', information of DHCP packets received
         on the port will be recorded."
    DEFVAL { false }
    ::= { unisDhcpSnoop2IfConfigEntry 5 }

unisDhcpSnoop2IfMaxLearnNum OBJECT-TYPE
    SYNTAX     Unsigned32(0..4294967295)
    MAX-ACCESS read-write
    STATUS     current
    DESCRIPTION
        "The maximum number of binding entries that could be learned on
         the port.
         If the value is 0, it means that there is no threshold on the
         port."
    DEFVAL { 0 }
    ::= { unisDhcpSnoop2IfConfigEntry 6 }

unisDhcpSnoop2IfOpt82Enable OBJECT-TYPE
    SYNTAX     TruthValue
    MAX-ACCESS read-write
    STATUS     current
    DESCRIPTION
        "If DHCP snooping supports option 82 functions, the
         value is 'true'.
         If DHCP snooping does NOT support option 82 functions,
         the value is 'false'."
    DEFVAL     { false }
    ::= { unisDhcpSnoop2IfConfigEntry 7 }

unisDhcpSnoop2IfOpt82Strategy     OBJECT-TYPE
    SYNTAX      INTEGER
    {
        drop(1),
        keep(2),
        replace(3)
    }
    MAX-ACCESS  read-write
    STATUS      current
    DESCRIPTION
        "The strategy of DHCP snooping handling option 82.

         'drop' indicates DHCP snooping discarding the request
         packet including option 82.

         'keep' indicates DHCP snooping accepting the request
         packet without any change of the option 82.

         'replace' indicates DHCP snooping accepting the
         request packet on condition that it generates a new
         option 82 to replace the original one."
    DEFVAL      { replace }
    ::= { unisDhcpSnoop2IfConfigEntry 8 }

unisDhcpSnoop2IfOpt82CIDMode OBJECT-TYPE
    SYNTAX      INTEGER
    {
        normal(1),
        verbose(2),
        userDefine(3),
        bas(4)
    }
    MAX-ACCESS  read-write
    STATUS      current
    DESCRIPTION
        "The mode of filling in the circuit ID suboption
         of DHCP option 82.

         'normal' is the standard mode.

         'verbose' is the detailed mode.

         'userDefine' is the user-defined mode.

         'bas' is the bas mode.

         If the value of this object is set to 'userDefine',
         unisDhcpSnoop2IfOpt82CIDStr must also be set."
    DEFVAL      { normal }
    ::= { unisDhcpSnoop2IfConfigEntry 9 }

unisDhcpSnoop2IfOpt82CIDNodeType OBJECT-TYPE
    SYNTAX     INTEGER
    {
        invalid(1),
        mac(2),
        sysname(3),
        userDefine(4)
    }
    MAX-ACCESS read-write
    STATUS     current
    DESCRIPTION
        "Type of access node identifier that is used to fill
         in the circuit ID suboption of option 82 when the value
         of unisDhcpSnoop2IfOption82CIDMode is set to 'verbose'.

         The SET operation of this object must be with the SET
         operation of unisDhcpSnoop2IfOpt82CIDMode.

         'invalid' indicates that the node identifier is NOT used
         to fill in the circuit ID suboption of option 82.
         If the value of unisDhcpSnoop2IfOpt82CIDMode is NOT
         'verbose', the value of this object is set to 'invalid'
         automatically.
         Otherwise the value of this object cannot be set to 'invalid'.

         'mac' indicates that the node identifier is
         filled in with the bridge MAC of DHCP snooping device.
         If the value of unisDhcpSnoop2IfOpt82CIDMode is set to
         'verbose', the default value of this object is 'mac'.

         'sysname' indicates that the node identifier
         is filled in with the sysname of the DHCP snooping.

         'userDefine' indicates the node identifier
         is filled in with the string defined by the object
         of unisDhcpSnoop2IfOpt82CIDNodeStr.
         If the value is set to 'userDefine', the value of
         unisDhcpSnoop2IfOpt82CIDNodeStr must also be set to
         a non-zero length string."
    ::= { unisDhcpSnoop2IfConfigEntry 10 }

unisDhcpSnoop2IfOpt82CIDNodeStr      OBJECT-TYPE
    SYNTAX     OCTET STRING(SIZE(0..50))
    MAX-ACCESS read-write
    STATUS     current
    DESCRIPTION
        "The string defined by user to fill in the
         node identifier in the verbose mode.

         If the value of unisDhcpSnoop2IfOpt82CIDMode is NOT
         'verbose', or the value of unisDhcpSnoop2IfOpt82CIDNodeType
         is NOT 'userDefine', it is set to a zero-length string
         automatically.
         Otherwise it must be set to a non-zero length string.

         The SET operation of this object must be with the SET
         operation of unisDhcpSnoop2IfOpt82CIDMode and
         unisDhcpSnoop2IfOpt82CIDNodeType."
    ::= { unisDhcpSnoop2IfConfigEntry 11 }

unisDhcpSnoop2IfOpt82CIDStr      OBJECT-TYPE
    SYNTAX      OCTET STRING(SIZE(0|3..63))
    MAX-ACCESS  read-write
    STATUS      current
    DESCRIPTION
        "The string defined by user to fill in the circuit ID
         suboption of option 82 in the user-define mode.

         If the value of unisDhcpSnoop2IfOpt82CIDMode is
         NOT 'userDefine', it is set to a zero-length string
         automatically.
         Otherwise it must be set to a non-zero length string.

         The SET operation of this object must be with the SET
         operation of unisDhcpSnoop2IfOpt82CIDMode."
    ::= { unisDhcpSnoop2IfConfigEntry 12 }

unisDhcpSnoop2IfOpt82CIDFormat    OBJECT-TYPE
    SYNTAX      INTEGER
    {
        hex(1),
        ascii(2),
        undefine(3)
    }
    MAX-ACCESS  read-write
    STATUS      current
    DESCRIPTION
        "The format of the circuit ID suboption of DHCP
         option 82.

         'hex' is the hex format.

         'ascii' is the ascii format.

         'undefine' is the undefine format.

         If the value of unisDhcpSnoop2IfOpt82CIDMode is
         'normal', this object is set with 'hex' automatically
         and cannot be set with 'undefine'.

         If the value of unisDhcpSnoop2IfOpt82CIDMode is
         'verbose', the default value of this object is 'undefine'.

         If the value of unisDhcpSnoop2IfOpt82CIDMode is
         'userDefine', this object is set with 'ascii' automatically
         and cannot be set with other value.

         The SET operation of this object must be with the SET
         operation of unisDhcpSnoop2IfOpt82CIDMode."
    ::= { unisDhcpSnoop2IfConfigEntry 13 }

unisDhcpSnoop2IfOpt82RIDMode OBJECT-TYPE
    SYNTAX      INTEGER
    {
        normal(1),
        sysname(2),
        userDefine(3)
    }
    MAX-ACCESS  read-write
    STATUS      current
    DESCRIPTION
        "The mode of filling in the remote ID suboption
         of DHCP option 82.

         'normal' is the standard mode.

         'userDefine' is the user-defined mode.

         'sysname' is the sysname mode.

         If the value of this object is set to 'userDefine',
         unisDhcpSnoop2IfOpt82RIDStr must also be set."
    DEFVAL      { normal }
    ::= { unisDhcpSnoop2IfConfigEntry 14 }

unisDhcpSnoop2IfOpt82RIDStr  OBJECT-TYPE
    SYNTAX      OCTET STRING (SIZE(0..63))
    MAX-ACCESS  read-write
    STATUS      current
    DESCRIPTION
        "The string defined by user to fill in the
         remote ID in the user-defined mode.

         If the value of unisDhcpSnoop2IfOpt82RIDMode is
         NOT 'userDefine', this object is set with a zero-length
         string automatically.
         Otherwise it must be set with a non-zero length string.

         The SET operation of this object must be with the SET
         operation of unisDhcpSnoop2IfOpt82RIDMode."
    ::= { unisDhcpSnoop2IfConfigEntry 15 }

unisDhcpSnoop2IfOpt82RIDFormat    OBJECT-TYPE
    SYNTAX      INTEGER
    {
        hex(1),
        ascii(2)
    }
    MAX-ACCESS  read-write
    STATUS      current
    DESCRIPTION
        "The format of DHCP option 82 remote ID in 'normal' mode.

         'hex' is the hex format.

         'ascii' is the ascii format.

         If the value of unisDhcpSnoop2IfOpt82RIDMode is
         'sysname' or 'userDefine', this object is set with 'ascii'
         automatically and cannot be set with other value.

         If the value of unisDhcpSnoop2IfOpt82RIDMode is
         'normal', the default value of this object is 'hex'.

         The SET operation of this object must be with the SET
         operation of unisDhcpSnoop2IfOpt82RIDMode."
    ::= { unisDhcpSnoop2IfConfigEntry 16 }

-- ==================================================================
-- 3rd Table of unisDhcpSnoop2Tables: unisDhcpSnoop2IfVlanCIDTable
-- ==================================================================
unisDhcpSnoop2IfVlanCIDTable   OBJECT-TYPE
    SYNTAX      SEQUENCE OF UnisDhcpSnoop2IfVlanCIDEntry
    MAX-ACCESS  not-accessible
    STATUS      current
    DESCRIPTION
        "A table containing the information of the circuit ID
         suboption of DHCP option 82 in VLAN."
    ::= { unisDhcpSnoop2Tables 3 }

unisDhcpSnoop2IfVlanCIDEntry  OBJECT-TYPE
    SYNTAX      UnisDhcpSnoop2IfVlanCIDEntry
    MAX-ACCESS  not-accessible
    STATUS      current
    DESCRIPTION
        "An entry containing the information of the circuit ID
         suboption of DHCP option 82 in VLAN."
    INDEX { ifIndex, unisDhcpSnoop2IfVlanCIDVlanIndex }
    ::= { unisDhcpSnoop2IfVlanCIDTable 1 }

UnisDhcpSnoop2IfVlanCIDEntry   ::=
    SEQUENCE
    {
        unisDhcpSnoop2IfVlanCIDVlanIndex          Unsigned32,
        unisDhcpSnoop2IfVlanCIDStr                OCTET STRING,
        unisDhcpSnoop2IfVlanCIDRowStatus          RowStatus
    }

unisDhcpSnoop2IfVlanCIDVlanIndex OBJECT-TYPE
    SYNTAX      Unsigned32(1..4094)
    MAX-ACCESS  not-accessible
    STATUS      current
    DESCRIPTION
        "VLAN ID."
    ::= { unisDhcpSnoop2IfVlanCIDEntry 1 }

unisDhcpSnoop2IfVlanCIDStr      OBJECT-TYPE
    SYNTAX      OCTET STRING(SIZE(3..63))
    MAX-ACCESS  read-create
    STATUS      current
    DESCRIPTION
        "The string defined by user to fill in the
         circuit ID suboption of option 82."
    ::= { unisDhcpSnoop2IfVlanCIDEntry 2 }

unisDhcpSnoop2IfVlanCIDRowStatus    OBJECT-TYPE
     SYNTAX      RowStatus
     MAX-ACCESS  read-create
     STATUS      current
     DESCRIPTION
         "Operation status of this table entry.
          Three actions are used: active,
          createAndGo, destroy."
     ::= { unisDhcpSnoop2IfVlanCIDEntry 3 }

-- ==================================================================
-- 4th Table of unisDhcpSnoop2Tables: unisDhcpSnoop2IfVlanRIDTable
-- ==================================================================
unisDhcpSnoop2IfVlanRIDTable   OBJECT-TYPE
    SYNTAX      SEQUENCE OF UnisDhcpSnoop2IfVlanRIDEntry
    MAX-ACCESS  not-accessible
    STATUS      current
    DESCRIPTION
        "A table containing the information of the remote ID
         suboption of DHCP option 82 in VLAN."
    ::= { unisDhcpSnoop2Tables 4 }

unisDhcpSnoop2IfVlanRIDEntry  OBJECT-TYPE
    SYNTAX      UnisDhcpSnoop2IfVlanRIDEntry
    MAX-ACCESS  not-accessible
    STATUS      current
    DESCRIPTION
        "An entry containing the information of the remote ID
         suboption of DHCP option 82 in VLAN."
    INDEX { ifIndex, unisDhcpSnoop2IfVlanRIDVlanIndex }
    ::= { unisDhcpSnoop2IfVlanRIDTable 1 }

UnisDhcpSnoop2IfVlanRIDEntry   ::=
    SEQUENCE
    {
        unisDhcpSnoop2IfVlanRIDVlanIndex              Unsigned32,
        unisDhcpSnoop2IfVlanRIDMode                   INTEGER,
        unisDhcpSnoop2IfVlanRIDStr                    OCTET STRING,
        unisDhcpSnoop2IfVlanRIDRowStatus              RowStatus
    }

unisDhcpSnoop2IfVlanRIDVlanIndex    OBJECT-TYPE
    SYNTAX      Unsigned32(1..4094)
    MAX-ACCESS  not-accessible
    STATUS      current
    DESCRIPTION
        "VLAN ID."
    ::= { unisDhcpSnoop2IfVlanRIDEntry 1 }

unisDhcpSnoop2IfVlanRIDMode    OBJECT-TYPE
    SYNTAX      INTEGER
    {
        sysname(1),
        userDefine(2)
    }
    MAX-ACCESS  read-create
    STATUS      current
    DESCRIPTION
        "The mode of filling in the remote ID suboption
         of DHCP option 82 in VLAN.

         'sysname' indicates using the device sysname to fill in
         the suboption.

         'userDefine' indicates using the string defined
         by unisDhcpSnoop2IfVlanRIDStr to fill in the suboption.

         If the value of this object is set to 'userDefine',
         unisDhcpSnoop2IfVlanRIDStr must also be set."
    ::= { unisDhcpSnoop2IfVlanRIDEntry 2 }

unisDhcpSnoop2IfVlanRIDStr      OBJECT-TYPE
    SYNTAX      OCTET STRING(SIZE(0..63))
    MAX-ACCESS  read-create
    STATUS      current
    DESCRIPTION
        "The string used to fill in the remote ID suboption.

         If the value of unisDhcpSnoop2IfVlanRIDMode is NOT 'userDefine',
         this object is set with a zero-length string automatically.
         Otherwise it must be set with a non-zero length string.

         The SET operation of this object must be with the SET
         operation of unisDhcpSnoop2IfVlanRIDMode."
    ::= { unisDhcpSnoop2IfVlanRIDEntry 3 }

unisDhcpSnoop2IfVlanRIDRowStatus    OBJECT-TYPE
     SYNTAX      RowStatus
     MAX-ACCESS  read-create
     STATUS      current
     DESCRIPTION
         "Operation status of this table entry.
          Three actions are used: active,
          createAndGo, destroy."
     ::= { unisDhcpSnoop2IfVlanRIDEntry 4 }

END
