-- =====================================================================
-- Copyright (c) 2020 Unisyue Technologies Co., Ltd.  All rights reserved.
--
-- Description:
--      This MIB module is for configuring and monitoring VSAN (Virtual
--      Storage Area Network) and domain management related entities.
-- Reference:
-- Version: V1.2
-- History:
--   V1.0 Initial version created by qiaoxinghua 2013-02-27
--   V1.1 Added unisVsanDmDomainIdChangeNotify and
--        unisVsanDmDomainIdChangeNotifyEnable by qiaoxinghua 2014-3-4
--   V1.2 Added unisVsanName and unisVsanWorkingMode
--        to unisVsanTable by chengzhipeng 2014-05-09
--        Added unisVsanFcIdTable and unisVsanFcIdPersistencyTable by wangyuqiang 2014-07-25
-- =====================================================================
UNIS-VSAN-MIB DEFINITIONS ::= BEGIN

IMPORTS
    OBJECT-TYPE, MODULE-IDENTITY, NOTIFICATION-TYPE, Counter32,
    Integer32
        FROM SNMPv2-SMI
    RowStatus, TruthValue
        FROM SNMPv2-TC
    SnmpAdminString
        FROM SNMP-FRAMEWORK-MIB
    UnisFcVsanIndex, UnisFcNameIdOrZero, UnisFcDomainPriority, UnisFcDomainId,
    UnisFcNameId, UnisFcAddressId, UnisFcDomainIdOrZero, UnisFcDmState, UnisFcDomainIdList
        FROM UNIS-FC-TC-MIB
    ifIndex
        FROM IF-MIB
    unisCommon
        FROM UNIS-OID-MIB;

unisSan MODULE-IDENTITY
    LAST-UPDATED   "201407251840Z"
    ORGANIZATION
        "Unisyue Technologies Co., Ltd."
    CONTACT-INFO
        ""
    DESCRIPTION
        "This MIB module is for configuring and monitoring VSAN
         and domain management related entities."
    REVISION       "201407251840Z"
    DESCRIPTION
        "Added unisVsanFcIdTable and unisVsanFcIdPersistencyTable."
    REVISION       "201405091840Z"
    DESCRIPTION
        "Added unisVsanName and unisVsanWorkingMode."
    REVISION       "201403041550Z"
    DESCRIPTION
        "Added unisVsanDmDomainIdChangeNotify and
         unisVsanDmDomainIdChangeNotifyEnable."
    REVISION       "201302280940Z"
    DESCRIPTION
        "Initial version of this MIB module."

    ::= { unisCommon 127 }

--
-- Node definitions
--
unisVsan OBJECT IDENTIFIER ::= { unisSan 1 }

unisVsanMibObjects OBJECT IDENTIFIER ::= { unisVsan 1 }

unisVsanDmConfiguration OBJECT IDENTIFIER ::= { unisVsanMibObjects 1 }

-- VSAN Table
unisVsanTable  OBJECT-TYPE
    SYNTAX      SEQUENCE OF UnisVsanEntry
    MAX-ACCESS  not-accessible
    STATUS      current
    DESCRIPTION
        "A table contains all the VSANs configured on the device.  It can
         be used to manage and monitor the VSANs on local device."
    ::= { unisVsanDmConfiguration 1 }

unisVsanEntry OBJECT-TYPE
    SYNTAX      UnisVsanEntry
    MAX-ACCESS  not-accessible
    STATUS      current
    DESCRIPTION
        "An entry that contains information about a VSAN in the unisVsanTable."
    INDEX { unisVsanIndex }
    ::= { unisVsanTable 1 }

UnisVsanEntry ::=
    SEQUENCE {
        unisVsanIndex
            UnisFcVsanIndex,
        unisVsanCoreSwitchName
            UnisFcNameIdOrZero,
        unisVsanRowStatus
            RowStatus,
        unisVsanName
            SnmpAdminString,
        unisVsanWorkingMode
            Integer32
       }

unisVsanIndex OBJECT-TYPE
    SYNTAX      UnisFcVsanIndex
    MAX-ACCESS  accessible-for-notify
    STATUS      current
    DESCRIPTION
        "The identifier of the VSAN."
    ::= { unisVsanEntry 1 }

unisVsanCoreSwitchName OBJECT-TYPE
    SYNTAX      UnisFcNameIdOrZero (SIZE(8 | 16))
    MAX-ACCESS  read-only
    STATUS      current
    DESCRIPTION
        "The Core Switch_Name of the VSAN, which is indicated by
         the switch's WWN(World Wide Name)."
    ::= { unisVsanEntry 2 }

unisVsanRowStatus OBJECT-TYPE
    SYNTAX      RowStatus
    MAX-ACCESS  read-create
    STATUS      current
    DESCRIPTION
        "RowStatus. Now only three states are supported:
         createAndGo, active, and destroy."
    ::= { unisVsanEntry 3 }

unisVsanName OBJECT-TYPE
    SYNTAX      SnmpAdminString(SIZE(0..32))
    MAX-ACCESS  read-create
    STATUS      current
    DESCRIPTION
        "The name of the VSAN.
         The default value of this object will be the
         string 'VSANxxxx' where xxxx is value of VSAN index
         expressed as 4 digits.  For example, if VSAN index is
         10, the default value of this object is 'VSAN0010'."
    ::= { unisVsanEntry 4 }

unisVsanWorkingMode OBJECT-TYPE
    SYNTAX      Integer32
    MAX-ACCESS  read-create
    STATUS      current
    DESCRIPTION
        "This object specifies the working modes the VSAN supports.
         The object has three available values:
         1: non-FCoE mode.
         2: FCF mode.
         3: NPV mode.

         The working mode of VSAN 4079 is always non-FCoE mode and cannot be
         converted.
         If the switch mode is not FCF-NPV mode, then the 'SET' operation
         on this object results in error.
         When creating a VSAN, the 'SET' operation including this object
         results in error.
         When the switch mode is FCF mode, working modes of all user VSANs
         are FCF mode.
         When the switch mode is NPV mode, working modes of all user VSANs
         are NPV mode.
         When the switch mode is FCF-NPV mode, the default working mode of
         a user VSAN is NPV mode.  If a VSAN has been created, the working mode
         can be converted from NPV mode to FCF mode, or vice versa."
    ::= { unisVsanEntry 5 }

-- DM Configuration
unisVsanDmTable     OBJECT-TYPE
    SYNTAX      SEQUENCE OF UnisVsanDmEntry
    MAX-ACCESS  not-accessible
    STATUS      current
    DESCRIPTION
        "A table contains domain management related configurations
         and information of VSANs.
         An entry in this table is created when corresponding VSAN
         is created, as well as deleted when the VSAN is deleted."
    ::= { unisVsanDmConfiguration 2 }

unisVsanDmEntry  OBJECT-TYPE
    SYNTAX      UnisVsanDmEntry
    MAX-ACCESS  not-accessible
    STATUS      current
    DESCRIPTION
        "An entry of domain management related configurations
         and information of a specified VSAN."
    INDEX { unisVsanIndex }
    ::= { unisVsanDmTable 1}

UnisVsanDmEntry ::=
    SEQUENCE {
              unisVsanDmDomainConfigureEnable     TruthValue,
              unisVsanDmFabricNameConfigured      UnisFcNameIdOrZero,
              unisVsanDmPriorityConfigured        UnisFcDomainPriority,
              unisVsanDmAllowedDomainIdList       UnisFcDomainIdList,
              unisVsanDmDomainIdConfigured        UnisFcDomainIdOrZero,
              unisVsanDmDomainIdTypeConfigured    INTEGER,
              unisVsanDmAutoReconfigureEnable     TruthValue,
              unisVsanDmDomainRestart             INTEGER,
              unisVsanDmState                     UnisFcDmState,
              unisVsanDmDomainIdAssigned          UnisFcDomainIdOrZero,
              unisVsanDmPrincipalSwitchWWN        UnisFcNameId,
              unisVsanDmLocalSwitchWWN            UnisFcNameId,
              unisVsanDmPrincipalSwRunPriority    UnisFcDomainPriority,
              unisVsanDmLocalSwRunPriority        UnisFcDomainPriority,
              unisVsanDmPrincipalSwSlctCnt        Counter32,
              unisVsanDmLocalPrincipalSwSlctCnt   Counter32,
              unisVsanDmBFCnt                     Counter32,
              unisVsanDmRCFCnt                    Counter32
             }

unisVsanDmDomainConfigureEnable  OBJECT-TYPE
    SYNTAX          TruthValue
    MAX-ACCESS      read-write
    STATUS          current
    DESCRIPTION
        "To enable or disable the fabric configuration function
         in this VSAN.
         true:  enabled, the fabric will be built dynamically.
         false: disabled, the fabric should be built statically
                by manual configurations."
    DEFVAL          { true }
    ::= { unisVsanDmEntry 1 }

unisVsanDmFabricNameConfigured    OBJECT-TYPE
    SYNTAX          UnisFcNameIdOrZero
    MAX-ACCESS      read-write
    STATUS          current
    DESCRIPTION
        "Specifies the fabric name in this VSAN, and will use a
         zero-length octet string as default value if not configured.
         The fabric name specified here takes effect only if the
         value of unisVsanDmDomainConfigureEnable is 'false', and the
         same fabric name should be configured for all switches in
         this VSAN.
         If the value of unisVsanDmDomainConfigureEnable is 'true',
         the principal switch WWN is used as fabric name.
         The value should be set to zero-length when canceling
         a configured fabric name."
    ::= { unisVsanDmEntry 2 }

unisVsanDmPriorityConfigured    OBJECT-TYPE
    SYNTAX          UnisFcDomainPriority
    MAX-ACCESS      read-write
    STATUS          current
    DESCRIPTION
        "Specifies the priority of a switch in this VSAN, which
         is used during principal switch selection to cause one
         Switch to be favored over another."
    DEFVAL         { 128 }
    ::= { unisVsanDmEntry 3 }

unisVsanDmAllowedDomainIdList    OBJECT-TYPE
    SYNTAX          UnisFcDomainIdList
    MAX-ACCESS      read-write
    STATUS          current
    DESCRIPTION
        "Specifies the list of domain IDs that are allowed in the
         VSAN, and the configuration has different meanings in
         different scenarios:

         1. Principal switch: Can only assign domains IDs within
            the allowed domain ID list.  If the allowed domain ID
            list configured does not include any of the already
            assigned domain IDs or manually configured domain IDs,
            the configuration will fail.

         2. Non-principal switch: The manually configured domain
            ID must be within the allowed domain ID list, or
            the configuration will fail.  Besides, the domain ID
            assigned by principal switch must within the allowed
            domain ID list, or the switch will refuse the assigned
            domain ID and isolate the upstream interface.  If the
            runtime domain ID for a switch is beyond the new
            configured ID list, the configuration will fail.
         The default value is a zero-length octet string.  If This
         value is set with zero-length, the configuration will be
         cancelled in this VSAN."
    ::= { unisVsanDmEntry 4 }

unisVsanDmDomainIdConfigured    OBJECT-TYPE
    SYNTAX          UnisFcDomainIdOrZero
    MAX-ACCESS      read-write
    STATUS          current
    DESCRIPTION
        "Used to configure or cancel a domain ID for a switch in
         this VSAN.

         When this value is not zero, the domain ID type should
         be specified together via unisVsanDmDomainIdTypeConfigured,
         or the default value of preferred type will be taken.
         The zero value is used to cancel the domain ID configured,
         and then, there is no need to specify its type.

         When statically build a fabric, the configured domain ID
         is the actual domain ID of the switch.  If this object is
         not manually configured, the switch will isolate all of
         its E_ports in this VSAN no matter what domain ID type is
         configured.

         When dynamically build a fabric, the configured domain ID
         is desired by the switch, but the domain ID assigned to
         the switch may not be the desired one.
         If a non-principal switch fails to obtain any domain ID
         from the principal switch, the non-principal switch will
         isolate the upstream link.
         If a non-principal switch obtains a domain ID from the
         principal switch other than the desired one, different
         actions will be taken according to different domain ID
         type configured:
          - If configured static type, The non-principal switch
            will isolate the upstream link and refuse other domain
            IDs assigned by the principal switch.
          - If configured preferred type, the non-principal switch
            will use the domain ID assigned by the principal switch."
    DEFVAL         { 0 }
    ::= { unisVsanDmEntry 5 }

unisVsanDmDomainIdTypeConfigured    OBJECT-TYPE
    SYNTAX          INTEGER {
                             static(1),
                             preferred(2)
                            }
    MAX-ACCESS      read-write
    STATUS          current
    DESCRIPTION
         "Specifies the type of configured domain ID, which can be
          static type or preferred type."
    DEFVAL         { preferred }
    ::= { unisVsanDmEntry 6 }

unisVsanDmAutoReconfigureEnable    OBJECT-TYPE
    SYNTAX          TruthValue
    MAX-ACCESS      read-write
    STATUS          current
    DESCRIPTION
        "Used to specify whether a disruptive reconfiguration will
         be automatically performed when the domain ID lists overlaps
         in fabric merging.

         The fabric reconfiguration function takes effect only when
         the value of unisVsanDmDomainConfigureEnable is 'true'."
    DEFVAL         { false }
    ::= { unisVsanDmEntry 7 }

unisVsanDmDomainRestart    OBJECT-TYPE
    SYNTAX          INTEGER  {
                              noOperation(1),
                              nonDisruptive(2),
                              disruptive(3)
                             }
    MAX-ACCESS      read-write
    STATUS          current
    DESCRIPTION
        "Used to manually trigger a disruptive or non-disruptive
         reconfiguration of the fabric."
    DEFVAL         { noOperation }
    ::= { unisVsanDmEntry 8 }

unisVsanDmState         OBJECT-TYPE
    SYNTAX          UnisFcDmState
    MAX-ACCESS      read-only
    STATUS          current
    DESCRIPTION
        "Indicates the managing state of the domain in this VSAN."
    ::= { unisVsanDmEntry 9 }

unisVsanDmDomainIdAssigned    OBJECT-TYPE
    SYNTAX          UnisFcDomainIdOrZero
    MAX-ACCESS      read-only
    STATUS          current
    DESCRIPTION
        "Indicates the Domain ID of the local switch in this
         VSAN or zero if no Domain ID has been assigned."
    ::= { unisVsanDmEntry 10 }

unisVsanDmPrincipalSwitchWWN    OBJECT-TYPE
    SYNTAX          UnisFcNameId
    MAX-ACCESS      read-only
    STATUS          current
    DESCRIPTION
        "Indicates the WWN of the principal switch in this VSAN,
         or zero-length string if the identity of the principal
         switch is unknown."
    ::= { unisVsanDmEntry 11 }

unisVsanDmLocalSwitchWWN       OBJECT-TYPE
    SYNTAX          UnisFcNameId
    MAX-ACCESS      read-only
    STATUS          current
    DESCRIPTION
        "Indicates the WWN of the local switch in this VSAN."
    ::= { unisVsanDmEntry 12 }

unisVsanDmPrincipalSwRunPriority    OBJECT-TYPE
    SYNTAX          UnisFcDomainPriority
    MAX-ACCESS      read-only
    STATUS          current
    DESCRIPTION
        "Indicates the running priority of the principal switch in
         this VSAN."
    ::= { unisVsanDmEntry 13 }

unisVsanDmLocalSwRunPriority    OBJECT-TYPE
    SYNTAX          UnisFcDomainPriority
    MAX-ACCESS      read-only
    STATUS          current
    DESCRIPTION
        "Indicates the running priority of the local switch in
         this VSAN."
    ::= { unisVsanDmEntry 14 }

unisVsanDmPrincipalSwSlctCnt    OBJECT-TYPE
    SYNTAX          Counter32
    MAX-ACCESS      read-only
    STATUS          current
    DESCRIPTION
        "The times that local switch has participated in principal
         switch selection in this VSAN."
    ::= { unisVsanDmEntry 15 }

unisVsanDmLocalPrincipalSwSlctCnt    OBJECT-TYPE
    SYNTAX          Counter32
    MAX-ACCESS      read-only
    STATUS          current
    DESCRIPTION
        "The times that local switch was elected as principal switch
         in this VSAN."
    ::= { unisVsanDmEntry 16 }

unisVsanDmBFCnt   OBJECT-TYPE
    SYNTAX          Counter32
    MAX-ACCESS      read-only
    STATUS          current
    DESCRIPTION
        "The times that local switch has participated in a BF(Build
         Fabric) process in this VSAN."
    ::= { unisVsanDmEntry 17 }

unisVsanDmRCFCnt    OBJECT-TYPE
    SYNTAX          Counter32
    MAX-ACCESS      read-only
    STATUS          current
    DESCRIPTION
        "The times that local switch has participated in a RCF
         (Reconfigure Fabric) process in this VSAN."
    ::= { unisVsanDmEntry 18 }

-- DM If Configuration
unisVsanDmIfConfigTable  OBJECT-TYPE
    SYNTAX      SEQUENCE OF UnisVsanDmIfConfigEntry
    MAX-ACCESS  not-accessible
    STATUS      current
    DESCRIPTION
        "A table contains the FC(Fibre Channel) related interface
         configurations about domain management of a VSAN."
    ::= { unisVsanDmConfiguration 3 }

unisVsanDmIfConfigEntry  OBJECT-TYPE
    SYNTAX      UnisVsanDmIfConfigEntry
    MAX-ACCESS  not-accessible
    STATUS      current
    DESCRIPTION
        "An entry used for managing the FC related interface
         configurations about domain management of a VSAN.
         An entry can be created when any object in this table is
         set to non-default value, and be deleted when the objects
         in this table are set to default value."
    INDEX { ifIndex,
            unisVsanIndex }
    ::= { unisVsanDmIfConfigTable 1}

UnisVsanDmIfConfigEntry ::=
    SEQUENCE {
              unisVsanDmIfConfigRcfReject
                TruthValue
             }

unisVsanDmIfConfigRcfReject  OBJECT-TYPE
    SYNTAX          TruthValue
    MAX-ACCESS      read-write
    STATUS          current
    DESCRIPTION
        "Used to specify whether the RCF(Reconfigure Fabric) requests
         received in this VSAN should be rejected.
          - true:  the received RCF will be rejected.
          - false: the received RCF will be accepted."
    DEFVAL          { false }
    ::= { unisVsanDmIfConfigEntry 1 }


-- VSAN FC ID Table

unisVsanFcIdTable OBJECT-TYPE
    SYNTAX          SEQUENCE OF UnisVsanFcIdEntry
    MAX-ACCESS      not-accessible
    STATUS          current
    DESCRIPTION
        "This table contains FC ID information for each VSAN."
    ::= { unisVsanDmConfiguration 4 }

unisVsanFcIdEntry OBJECT-TYPE
    SYNTAX          UnisVsanFcIdEntry
    MAX-ACCESS      not-accessible
    STATUS          current
    DESCRIPTION
        "This entry provides FC ID information for a VSAN."
    INDEX  { unisVsanIndex }
    ::= { unisVsanFcIdTable 1 }

UnisVsanFcIdEntry ::= SEQUENCE {
        unisVsanFreeFcIds                    Counter32,
        unisVsanAssignedFcIds                Counter32,
        unisVsanFcIdPersistency              TruthValue,
        unisVsanFcIdPurge                    INTEGER
}

unisVsanFreeFcIds OBJECT-TYPE
        SYNTAX      Counter32
        MAX-ACCESS  read-only
        STATUS      current
        DESCRIPTION
               "The number of FC IDs that are unassigned on this VSAN."
        ::= { unisVsanFcIdEntry 1 }

unisVsanAssignedFcIds OBJECT-TYPE
        SYNTAX      Counter32
        MAX-ACCESS  read-only
        STATUS      current
        DESCRIPTION
               "The number of FC IDs that are assigned on this VSAN."
        ::= { unisVsanFcIdEntry 2 }

unisVsanFcIdPersistency OBJECT-TYPE
    SYNTAX          TruthValue
    MAX-ACCESS      read-write
    STATUS          current
    DESCRIPTION
           "Enable or disable FC ID persistency on this VSAN.

           If this object is set to 'true', then all the FC ID
           assigned on this VSAN are made persistent on this VSAN, and
           all login entries automatically created in the
           unisVsanFcIdPersistencyTable with unisVsanFcIdPersistencyWwn
           equal to either WWN of the logged-in Nx_Port for which the
           FC ID was assigned and unisVsanFcIdPersistencyType equal
           to 'dynamic'.

           If this object is set to 'false', then all the entries on
           this VSAN in dmFcIdPersistencyTable are deleted."
    DEFVAL { true }
    ::= { unisVsanFcIdEntry 3 }

unisVsanFcIdPurge OBJECT-TYPE
        SYNTAX      INTEGER {
                      noOp (1),
                      enable (2)
                    }
        MAX-ACCESS  read-write
        STATUS      current
        DESCRIPTION
               "This object is used to purge the FC ID
                persistency database on this VSAN.

               If the value of this object is 'enable', then
               all entries on this VSAN in the unisVsanFcIdPersistencyTable with
               unisVsanFcIdPersistencyType is 'dynamic' and
               unisVsanFcIdPersistencyUsed is 'false' are
               purged from the persistency database."
        ::= { unisVsanFcIdEntry 4 }

-- FC ID Persistency Table

unisVsanFcIdPersistencyTable OBJECT-TYPE
    SYNTAX          SEQUENCE OF UnisVsanFcIdPersistencyEntry
    MAX-ACCESS      not-accessible
    STATUS          current
    DESCRIPTION
           "This table contains the FC IDs which are in the FC ID
           persistency database of each VSAN.

           If the FC ID persistency is enabled, FC devices would get
           the same FC IDs even if they disappear and appear again.

           The FC ID persistency database contains information
           about the FC IDs which are assigned to FC devices
           either statically (configured) or dynamically.

           An entry is automatically created when a FC ID is
           assigned and unisVsanFcIdPersistency is 'true' on this VSAN.

           The entries can also be created and deleted via
           the unisVsanFcIdPersistencyRowStatus object.

           If the object unisVsanFcIdPurge is set to 'enable', an entry is
           deleted if its unisVsanFcIdPersistencyType is 'dynamic' and
           unisVsanFcIdPersistencyUsed is 'false'.

           If the unisVsanFcIdPersistency is 'false', no
           entry can be created.

           If the unisVsanDmDomainIdAssigned is changed on a VSAN, then all the
           entries on that VSAN in this table are deleted."
    ::= { unisVsanDmConfiguration 5 }

unisVsanFcIdPersistencyEntry OBJECT-TYPE
    SYNTAX          UnisVsanFcIdPersistencyEntry
    MAX-ACCESS      not-accessible
    STATUS          current
    DESCRIPTION
        "This entry provides FC ID persistency information for a VSAN."
    INDEX  { unisVsanIndex, unisVsanFcIdPersistencyWwn }
    ::= { unisVsanFcIdPersistencyTable 1 }

UnisVsanFcIdPersistencyEntry ::= SEQUENCE {
       unisVsanFcIdPersistencyWwn           UnisFcNameId,
       unisVsanFcIdPersistencyFcId          UnisFcAddressId,
       unisVsanFcIdPersistencyUsed          TruthValue,
       unisVsanFcIdPersistencyType          INTEGER,
       unisVsanFcIdPersistencyRowStatus     RowStatus
}

unisVsanFcIdPersistencyWwn OBJECT-TYPE
        SYNTAX      UnisFcNameId
        MAX-ACCESS  not-accessible
        STATUS      current
        DESCRIPTION
               "This is either the port WWN of the FC device if the
               local port is an F_port.  The local port is the port on
               the local device to which the FC device is attached."
        ::= { unisVsanFcIdPersistencyEntry 1 }

unisVsanFcIdPersistencyFcId OBJECT-TYPE
        SYNTAX      UnisFcAddressId
        MAX-ACCESS  read-create
        STATUS      current
        DESCRIPTION
               "The FC ID assigned for this WWN on this VSAN.

               This object cannot be changed if either the value of
               unisVsanFcIdPersistencyUsed is 'true' or if the
               new value being set is already assigned on this VSAN."
        ::= { unisVsanFcIdPersistencyEntry 2 }

unisVsanFcIdPersistencyUsed OBJECT-TYPE
    SYNTAX          TruthValue
    MAX-ACCESS      read-only
    STATUS          current
    DESCRIPTION
           "This object indicates this FC ID is used or not."
    ::= { unisVsanFcIdPersistencyEntry 3 }

unisVsanFcIdPersistencyType OBJECT-TYPE
    SYNTAX      INTEGER {
                   static (1),
                   dynamic (2)
                }
    MAX-ACCESS  read-create
    STATUS      current
    DESCRIPTION
           "The type of persistency of this FC ID."
    DEFVAL { static }
    ::= { unisVsanFcIdPersistencyEntry 4 }

unisVsanFcIdPersistencyRowStatus OBJECT-TYPE
    SYNTAX      RowStatus
    MAX-ACCESS  read-create
    STATUS      current
    DESCRIPTION
           "An entry cannot be created if unisVsanFcIdPersistency is 'false'.
            An entry cannot be deleted if unisVsanFcIdPersistencyUsed is 'true'."
    ::= { unisVsanFcIdPersistencyEntry 5 }

-- DM Information
unisVsanDmInformation  OBJECT IDENTIFIER ::= { unisVsanMibObjects 2 }

unisVsanDmDatabaseTable OBJECT-TYPE
    SYNTAX SEQUENCE OF UnisVsanDmDatabaseEntry
    MAX-ACCESS         not-accessible
    STATUS             current
    DESCRIPTION
        "A table specifies the information of the switch
         about all the Domain IDs which have been assigned
         in each of the VSANs."
    ::= { unisVsanDmInformation 1 }

unisVsanDmDatabaseEntry OBJECT-TYPE
    SYNTAX      UnisVsanDmDatabaseEntry
    MAX-ACCESS  not-accessible
    STATUS      current
    DESCRIPTION
        "An object in the unisVsanDmDatabaseTable contains one
         Domain ID and the corresponding WWN of the switch in
         one VSAN."
    INDEX { unisVsanIndex,
            unisVsanDmDatabaseDomainId }
    ::= { unisVsanDmDatabaseTable 1 }

UnisVsanDmDatabaseEntry ::=
    SEQUENCE {
        unisVsanDmDatabaseDomainId
          UnisFcDomainId,
        unisVsanDmDatabaseSwitchWWN
          UnisFcNameId
       }

unisVsanDmDatabaseDomainId OBJECT-TYPE
    SYNTAX          UnisFcDomainId
    MAX-ACCESS      not-accessible
    STATUS          current
    DESCRIPTION
        "The Domain ID which has been assigned."
    ::= { unisVsanDmDatabaseEntry 1 }

unisVsanDmDatabaseSwitchWWN OBJECT-TYPE
    SYNTAX          UnisFcNameId
    MAX-ACCESS      read-only
    STATUS          current
    DESCRIPTION
        "The WWN of the switch to which the corresponding
         Domain ID has been assigned in the particular VSAN."
    ::= { unisVsanDmDatabaseEntry 2 }

unisVsanDmIfInfoTable OBJECT-TYPE
    SYNTAX SEQUENCE OF UnisVsanDmIfInfoEntry
    MAX-ACCESS         not-accessible
    STATUS             current
    DESCRIPTION
        "A table specifies the information of an interface
         in each of the VSANs."
    ::= { unisVsanDmInformation 2 }

unisVsanDmIfInfoEntry OBJECT-TYPE
    SYNTAX      UnisVsanDmIfInfoEntry
    MAX-ACCESS  not-accessible
    STATUS      current
    DESCRIPTION
        "A conceptual row in the unisVsanDmIfInfoTable indicates the
         role information of the interface in the particular VSAN."
    INDEX { ifIndex,
            unisVsanIndex }
    ::= { unisVsanDmIfInfoTable 1 }

UnisVsanDmIfInfoEntry ::=
    SEQUENCE {
          unisVsanDmIfInfoRole
            INTEGER
          }

unisVsanDmIfInfoRole OBJECT-TYPE
    SYNTAX INTEGER {
                      nonPrincipal(1),
                      principalUpstream(2),
                      principalDownstream(3),
                      isolated(4),
                      unknown(5)
                   }
    MAX-ACCESS      read-only
    STATUS          current
    DESCRIPTION
        "The role of the interface in the VSAN.  The value specifications
         are listed as follows:

         nonPrincipal         - The state of the interface is not principal
                                interface in the VSAN.
         principalUpstream    - The state of the interface is upstream
                                principal interface in the VSAN.
         principalDownstream  - The state of the interface is downstream
                                principal interface in the VSAN.
         isolated             - The state of the interface is isolated in
                                the VSAN.
         unknown              - The state of the interface is unknown in
                                the VSAN."
    ::= { unisVsanDmIfInfoEntry 1 }

-- DM Notifications
unisVsanDmNotifications OBJECT IDENTIFIER ::= { unisVsanMibObjects 3 }
unisVsanDmNotificationPrefix  OBJECT IDENTIFIER
    ::= { unisVsanDmNotifications 0 }

unisVsanDmDomainIdNotAssignedNotify NOTIFICATION-TYPE
    OBJECTS {unisVsanIndex,
             unisVsanDmLocalSwitchWWN}
    STATUS current
    DESCRIPTION
        "This event will be triggered if a Domain ID is not
         assigned or configured, then the E_ports may be isolated
         in the VSAN. The conditions are listed as follows:

         1. If the switch has enabled the fabric configuration and
            a request for a configured static Domain ID is rejected
            or no other Domain ID is assigned, the E_ports will be
            isolated in the particular VSAN.
         2. If the switch does not enable the fabric configuration
            and a Domain ID is not configured, all of its E_ports
            will be isolated in the particular VSAN.

         The notification contains the WWN of the Switch and
         the index of the VSAN in which the event occurred."
   ::= { unisVsanDmNotificationPrefix 1 }

unisVsanDmNewPrincipalSwitchNotify NOTIFICATION-TYPE
    OBJECTS {unisVsanIndex,
             unisVsanDmLocalSwitchWWN}
    STATUS current
    DESCRIPTION
        "If a switch becomes the new Principal Switch in a VSAN, this
         notification is sent immediately after the election.

         The notification contains the WWN of the new Principal Switch
         and the index of the VSAN in which the transition occurred."
   ::= { unisVsanDmNotificationPrefix 2 }

unisVsanDmFabricChangeNotify NOTIFICATION-TYPE
    OBJECTS         { unisVsanIndex }
    STATUS          current
    DESCRIPTION
        "This event will be triggered if a switch sends or receives a
         Build Fabric (BF) or a Reconfigure Fabric (RCF) message in a
         VSAN.

         The conditions a switch can receive or send a BF or a RCF are
         listed as follows:
         1. Two isolated fabrics in a VSAN merge into one fabric.  If
            the Domain ID lists do not overlap, the sent or received
            message is BF, other cases, it is RCF.
         2. If an upstream principal link which connects to principal
            switch and other switches become disconnected, the sent or
            received message is BF.
         3. A BF or RCF process is triggered manually by configuration.
         The notification contains the index of the VSAN in which a BF
         or a RCF was sent or received."
   ::= { unisVsanDmNotificationPrefix 3 }

unisVsanDmDomainIdChangeNotify NOTIFICATION-TYPE
    OBJECTS         { unisVsanIndex,
                      unisVsanDmDomainIdAssigned,
                      unisVsanDmLocalSwitchWWN
                    }
    STATUS          current
    DESCRIPTION
        "This event will be triggered if the Domain ID of the local switch
         changed in a VSAN."
    ::= { unisVsanDmNotificationPrefix 4 }

unisVsanDmNotificationSwitch  OBJECT IDENTIFIER
   ::= { unisVsanDmNotifications 1 }

unisVsanDmFabricChangeNotifyEnable OBJECT-TYPE
    SYNTAX          TruthValue
    MAX-ACCESS      read-write
    STATUS          current
    DESCRIPTION
        "Specifies whether the unisVsanDmFabricChangeNotify can be sent
         when a BF or RCF message was sent or received by a switch."
    DEFVAL          { false }
    ::= { unisVsanDmNotificationSwitch 1 }

unisVsanDmDomainIdChangeNotifyEnable OBJECT-TYPE
    SYNTAX          TruthValue
    MAX-ACCESS      read-write
    STATUS          current
    DESCRIPTION
        "Specifies whether the unisVsanDmDomainIdChangeNotify can be sent
         when the Domain ID of the local switch changed in a VSAN."
    DEFVAL          { false }
    ::= { unisVsanDmNotificationSwitch 2 }
END
