-- ==========================================================================
-- Copyright (c) 2020 Unisyue Technologies Co., Ltd.  All rights reserved.
--
-- Description: The purpose of this MIB file is to provide the definition of
--              voice call record.
-- Reference:
-- Version: V1.1
-- History:
-- V1.0 2008-02-17 Initial version, created by Tian Xiaoqiang, Qu Jin
-- V1.1 2009-12-09 Add g729br8 to "UnisCodecType", Wang Tong
-- ==========================================================================
UNIS-VOICE-CALL-HISTORY-MIB DEFINITIONS ::= BEGIN
IMPORTS
        OBJECT-TYPE, MODULE-IDENTITY, Integer32, Gauge32
    FROM SNMPv2-SMI
        InetAddressType, InetAddress
    FROM INET-ADDRESS-MIB
        InterfaceIndexOrZero
    FROM IF-MIB
        AbsoluteCounter32
    FROM DIAL-CONTROL-MIB
        TEXTUAL-CONVENTION, DisplayString, TimeStamp
    FROM SNMPv2-TC
        unisVoice
    FROM UNIS-OID-MIB;

unisVoCallHistory MODULE-IDENTITY
    LAST-UPDATED "200802170000Z"
    ORGANIZATION
        "Unisyue Technologies Co., Ltd."
    CONTACT-INFO
        ""
    DESCRIPTION
        "This MIB file is to provide the definition of voice call
        history record information."
    REVISION "200802170000Z"
    DESCRIPTION
        "The initial version of this MIB file."
    ::= { unisVoice 16 }

-- ======================================
--          Type declaration
-- ======================================

UnisGUid ::= TEXTUAL-CONVENTION
STATUS       current
DESCRIPTION
        "Represents a global call identifier.  The global call identifier is
         used as a unique identifier for an end-to-end call.  A zero length
         UnisGUid indicates no value for the global call identifier."
SYNTAX       OCTET STRING(SIZE(0..16))

UnisCodecType      ::= TEXTUAL-CONVENTION
STATUS       current
DESCRIPTION
        "Type of Codec."
SYNTAX  INTEGER
        {
        g711a(1),
        g711u(2),
        g723r53(3),
        g723r63(4),
        g729r8(5),
        g729a(6),
        g726r16(7),
        g726r24(8),
        g726r32(9),
        g726r40(10),
        unknown(11),
        g729br8(12)
        }

unisVoiceCallHistoryObjects OBJECT IDENTIFIER ::= { unisVoCallHistory 1 }

-- ===========================================================================
--                        unisCallHistoryTable
-- ===========================================================================
-- callHistoryTable
-- Table to store the past call information.  The destination number
-- and the call connect and disconnect time, and the disconnection
-- cause are stored.  These calls could be circuit switched or virtual
-- circuits.  History of each and every call is stored, of successful
-- calls as well as of unsuccessful and rejected calls.  An entry will
-- be created when a call is cleared.

unisCallHistoryTable OBJECT-TYPE
        SYNTAX      SEQUENCE OF UnisCallHistoryEntry
        MAX-ACCESS  not-accessible
        STATUS      current
        DESCRIPTION
            "A table containing information about specific
             calls to a specific destination."
        ::= { unisVoiceCallHistoryObjects 1 }

unisCallHistoryEntry OBJECT-TYPE
        SYNTAX      UnisCallHistoryEntry
        MAX-ACCESS  not-accessible
        STATUS      current
        DESCRIPTION
            "The information regarding a single connection."
        INDEX       { unisCallHistoryIndex }
        ::= { unisCallHistoryTable 1 }


UnisCallHistoryEntry ::=
        SEQUENCE {
            unisCallHistoryIndex                     Integer32,
            unisCallHistorySetupTime                 TimeStamp,
            unisCallHistoryConnectTime               TimeStamp,
            unisCallHistoryTerminateTime             TimeStamp,
            unisCallHistoryPeerAddress               DisplayString,
            unisCallHistoryPeerId                    Integer32,
            unisCallHistoryLogicalIfIndex            InterfaceIndexOrZero,
            unisCallHistoryCallOrigin                INTEGER,
            unisCallHistoryChargedUnits              AbsoluteCounter32,
            unisCallHistoryInfoType                  INTEGER,
            unisCallHistoryTransmitPackets           AbsoluteCounter32,
            unisCallHistoryTransmitBytes             AbsoluteCounter32,
            unisCallHistoryReceivePackets            AbsoluteCounter32,
            unisCallHistoryReceiveBytes              AbsoluteCounter32
        }

unisCallHistoryIndex OBJECT-TYPE
        SYNTAX      Integer32 (1..2147483647)
        MAX-ACCESS  not-accessible
        STATUS      current
        DESCRIPTION
            "The index of the call history table.  It's a monotonically
             increasing integer for the sole purpose of indexing call
             disconnection events.  When it reaches to the maximum value,
             the value will back to 1."
        ::= { unisCallHistoryEntry 1 }

unisCallHistorySetupTime OBJECT-TYPE
        SYNTAX      TimeStamp
        MAX-ACCESS  read-only
        STATUS      current
        DESCRIPTION
            "The value of sysUpTime when the call was started."
        ::= { unisCallHistoryEntry 2 }

unisCallHistoryConnectTime OBJECT-TYPE
        SYNTAX      TimeStamp
        MAX-ACCESS  read-only
        STATUS      current
        DESCRIPTION
            "The value of sysUpTime when the call was connected.
             If the call is not connected, this object will have a
             value of zero."
        ::= { unisCallHistoryEntry 3 }

unisCallHistoryTerminateTime OBJECT-TYPE
        SYNTAX      TimeStamp
        MAX-ACCESS  read-only
        STATUS      current
        DESCRIPTION
            "The value of sysUpTime when the call was terminated."
        ::= { unisCallHistoryEntry 4 }

unisCallHistoryPeerAddress OBJECT-TYPE
        SYNTAX      DisplayString
        MAX-ACCESS  read-only
        STATUS      current
        DESCRIPTION
            "The number this call was connected to.  If the number is
             not available, it will have a length of zero."
        ::= { unisCallHistoryEntry 5 }

unisCallHistoryPeerId OBJECT-TYPE
        SYNTAX      Integer32 (0..2147483647)
        MAX-ACCESS  read-only
        STATUS      current
        DESCRIPTION
            "This object identifies a single peer.  This is the Id value
             of the peer table entry to which this call was made.  If a
             peer table entry for this call does not exist or is unknown,
             the value of this object will be zero."
        ::= { unisCallHistoryEntry 6 }

unisCallHistoryLogicalIfIndex OBJECT-TYPE
        SYNTAX      InterfaceIndexOrZero
        MAX-ACCESS  read-only
        STATUS      current
        DESCRIPTION
            "This is the ifIndex value of the logical interface through
             which this call was made.  For ISDN media, this would be
             the ifIndex of the B channel which was used for this call.
             If the ifIndex value is unknown, the value of this object
             will be zero."
        ::= { unisCallHistoryEntry 7 }

unisCallHistoryCallOrigin OBJECT-TYPE
        SYNTAX      INTEGER {
            originate(1),
            answer(2),
            callback(3)
        }
        MAX-ACCESS  read-only
        STATUS      current
        DESCRIPTION
            "The call origin.
             originate        The call that is initiated.
             answer           The call that is accepted.
             callback         Either rejects the call and then calls back,
                              or uses the 'Reverse charging' information
                              element if it is available. Note that callback(3)
                              is supposed to control charging, not security,
                              and applies to callback prior to accepting a call.
                              Callback for security reasons can be handled using
                              PPP callback."
        ::= { unisCallHistoryEntry 8 }

unisCallHistoryChargedUnits OBJECT-TYPE
        SYNTAX      AbsoluteCounter32
        MAX-ACCESS  read-only
        STATUS      current
        DESCRIPTION
            "The number of charged units for this connection.
             For incoming calls or if charging information is
             not supplied by the switch, the value of this object
             will be zero."
        ::= { unisCallHistoryEntry 9 }

unisCallHistoryInfoType OBJECT-TYPE
        SYNTAX      INTEGER {
            other(1),
            speech(2),
            unrestrictedDigital(3),
            unrestrictedDigital56(4),
            restrictedDigital(5),
            audio31(6),
            audio7(7),
            video(8),
            packetSwitched(9),
            fax(10)
        }
        MAX-ACCESS  read-only
        STATUS      current
        DESCRIPTION
            "The information type for this call.
             other                          E.g. for non-isdn media.
             speech                         Speech.
             unrestrictedDigital            Unrestricted digital information
                                            with 64k rate adaption.
             unrestrictedDigital56          Unrestricted digital information
                                            with 56k rate adaption.
             restrictedDigital              Restricted digital information.
             audio31                        3.1 kHz audio.
             audio7                         7 kHz audio.
             video                          Video.
             packetSwitched                 Packetswitch.
             fax                            Fax."
        ::= { unisCallHistoryEntry 10 }

unisCallHistoryTransmitPackets OBJECT-TYPE
        SYNTAX      AbsoluteCounter32
        MAX-ACCESS  read-only
        STATUS      current
        DESCRIPTION
            "The number of packets which were transmitted while this
             call was active."
        ::= { unisCallHistoryEntry 11 }

unisCallHistoryTransmitBytes OBJECT-TYPE
        SYNTAX      AbsoluteCounter32
        MAX-ACCESS  read-only
        STATUS      current
        DESCRIPTION
            "The number of bytes which were transmitted for this call."
        ::= { unisCallHistoryEntry 12 }

unisCallHistoryReceivePackets OBJECT-TYPE
        SYNTAX      AbsoluteCounter32
        MAX-ACCESS  read-only
        STATUS      current
        DESCRIPTION
            "The number of packets which were received for this call."
        ::= { unisCallHistoryEntry 13 }

unisCallHistoryReceiveBytes OBJECT-TYPE
        SYNTAX      AbsoluteCounter32
        MAX-ACCESS  read-only
        STATUS      current
        DESCRIPTION
            "The number of bytes which were received for this call."
        ::= { unisCallHistoryEntry 14 }

-- ===========================================================================
--                        unisVoiceCallHistoryTable
-- ===========================================================================

unisVoiceCallHistoryTable OBJECT-TYPE
        SYNTAX      SEQUENCE OF UnisVoiceCallHistoryEntry
        MAX-ACCESS  not-accessible
        STATUS      current
        DESCRIPTION
            "This table is the voice extension to the call history table
            of DIAL-CONTROL-MIB.  It contains voice encapsulation call
            leg information that is derived from the statistics of lower
            layer telephony interface."
        ::= { unisVoiceCallHistoryObjects 2 }

unisVoiceCallHistoryEntry OBJECT-TYPE
        SYNTAX      UnisVoiceCallHistoryEntry
        MAX-ACCESS  not-accessible
        STATUS      current
        DESCRIPTION
            "The information regarding a extended voice call history information."
        INDEX { unisCallHistoryIndex }
        ::= { unisVoiceCallHistoryTable 1 }

UnisVoiceCallHistoryEntry ::= SEQUENCE {
        unisVoCallHistoryConnectionId    UnisGUid,
        unisVoCallHistoryTxDuration      Gauge32,
        unisVoCallHistoryVoiceTxDuration Gauge32,
        unisVoCallHistoryFaxTxDuration   Gauge32,
        unisVoCallHistoryCoderType       UnisCodecType,
        unisVoCallHistoryImgPageCount    Gauge32
    }

unisVoCallHistoryConnectionId OBJECT-TYPE
        SYNTAX      UnisGUid
        MAX-ACCESS  read-only
        STATUS      current
        DESCRIPTION
            "The global call identifier of circuit switched network for
            the gateway call."
        ::= { unisVoiceCallHistoryEntry 1 }

unisVoCallHistoryTxDuration OBJECT-TYPE
        SYNTAX      Gauge32
        MAX-ACCESS  read-only
        STATUS      current
        DESCRIPTION
            "Duration of transmit path open from this peer to the
            voice gateway for the call.  The units is milliseconds."
        ::= { unisVoiceCallHistoryEntry 2 }

unisVoCallHistoryVoiceTxDuration OBJECT-TYPE
        SYNTAX      Gauge32
        MAX-ACCESS  read-only
        STATUS      current
        DESCRIPTION
            "Duration of voice transmitted from this peer to voice
            gateway for this call.  The voice utilization rate can be
            obtained by dividing this by unisVoCallHistoryTxDuration object.
            The units is milliseconds."
        ::= { unisVoiceCallHistoryEntry 3 }

unisVoCallHistoryFaxTxDuration OBJECT-TYPE
        SYNTAX      Gauge32
        MAX-ACCESS  read-only
        STATUS      current
        DESCRIPTION
            "Duration of fax transmitted from this peer to voice gateway
            for this call.  The fax utilization rate can be obtained by
            dividing this by unisVoCallHistoryTxDuration object.  The units
            is milliseconds."
        ::= { unisVoiceCallHistoryEntry 4 }

unisVoCallHistoryCoderType OBJECT-TYPE
        SYNTAX      UnisCodecType
        MAX-ACCESS  read-only
        STATUS      current
        DESCRIPTION
            "The negotiated coder type.  It specifies the encode type to
            the PSTN leg of a call."
        ::= { unisVoiceCallHistoryEntry 5 }

unisVoCallHistoryImgPageCount OBJECT-TYPE
        SYNTAX      Gauge32
        MAX-ACCESS  read-only
        STATUS      current
        DESCRIPTION
            "The number of fax related image pages are received or
            transmitted via the peer for the call.  The units is page."
        ::= { unisVoiceCallHistoryEntry 6 }

-- ===========================================================================
--                        unisVoiceVoIPCallHistoryTable
-- ===========================================================================
unisVoiceVoIPCallHistoryTable OBJECT-TYPE
        SYNTAX      SEQUENCE OF UnisVoiceVoIPCallHistoryEntry
        MAX-ACCESS  not-accessible
        STATUS      current
        DESCRIPTION
            "This table is the VoIP extension to the call active table of
            DIAL-CONTROL-MIB.  It contains VoIP call leg information about
            specific VoIP call destination."
        ::= { unisVoiceCallHistoryObjects 3 }

unisVoiceVoIPCallHistoryEntry OBJECT-TYPE
        SYNTAX      UnisVoiceVoIPCallHistoryEntry
        MAX-ACCESS  not-accessible
        STATUS      current
        DESCRIPTION
            "The information regarding a extended VoIP call history
            information."
        INDEX {unisCallHistoryIndex }
        ::= { unisVoiceVoIPCallHistoryTable 1 }

UnisVoiceVoIPCallHistoryEntry ::= SEQUENCE {
        unisVoVoIPCallHistoryConnectionId    UnisGUid,
        unisVoVoIPCallHistoryRemSigIPType    InetAddressType,
        unisVoVoIPCallHistoryRemSigIPAddr    InetAddress,
        unisVoVoIPCallHistoryRemSigPort      Integer32,
        unisVoVoIPCallHistoryRemMedIPType    InetAddressType,
        unisVoVoIPCallHistoryRemMedIPAddr    InetAddress,
        unisVoVoIPCallHistoryRemMedPort      Integer32,
        unisVoVoIPCallHistorySessProtocol    INTEGER,
        unisVoVoIPCallHistoryCoderType       UnisCodecType
    }

unisVoVoIPCallHistoryConnectionId OBJECT-TYPE
        SYNTAX      UnisGUid
        MAX-ACCESS  read-only
        STATUS      current
        DESCRIPTION
            "The global call identifier of packet-switched network for the
            gateway call."
        ::= { unisVoiceVoIPCallHistoryEntry 1 }

unisVoVoIPCallHistoryRemSigIPType OBJECT-TYPE
        SYNTAX      InetAddressType
        MAX-ACCESS  read-only
        STATUS      current
        DESCRIPTION
            "The type of remote system signalling IP address for the VoIP call."
        ::= { unisVoiceVoIPCallHistoryEntry 2 }

unisVoVoIPCallHistoryRemSigIPAddr OBJECT-TYPE
        SYNTAX      InetAddress
        MAX-ACCESS  read-only
        STATUS      current
        DESCRIPTION
            "Remote system signalling IP address for the VoIP call."
        ::= { unisVoiceVoIPCallHistoryEntry 3 }

unisVoVoIPCallHistoryRemSigPort OBJECT-TYPE
        SYNTAX      Integer32(0..65535)
        MAX-ACCESS  read-only
        STATUS      current
        DESCRIPTION
            "Remote system UDP listener signalling port to which to
            transmit voice packets."
        ::= { unisVoiceVoIPCallHistoryEntry 4 }

unisVoVoIPCallHistoryRemMedIPType OBJECT-TYPE
        SYNTAX      InetAddressType
        MAX-ACCESS  read-only
        STATUS      current
        DESCRIPTION
            "The type of remote system media IP address for the VoIP call."
        ::= { unisVoiceVoIPCallHistoryEntry 5 }

unisVoVoIPCallHistoryRemMedIPAddr OBJECT-TYPE
        SYNTAX      InetAddress
        MAX-ACCESS  read-only
        STATUS      current
        DESCRIPTION
            "Remote system media IP address for the VoIP call."
        ::= { unisVoiceVoIPCallHistoryEntry 6 }

unisVoVoIPCallHistoryRemMedPort OBJECT-TYPE
        SYNTAX      Integer32(0..65535)
        MAX-ACCESS  read-only
        STATUS      current
        DESCRIPTION
            "Remote system UDP listener media port to which to transmit voice
            packets."
        ::= { unisVoiceVoIPCallHistoryEntry 7 }

unisVoVoIPCallHistorySessProtocol OBJECT-TYPE
        SYNTAX INTEGER {
            unknown(1),
            h323(2),
            sip(3)
            }
        MAX-ACCESS  read-only
        STATUS      current
        DESCRIPTION
            "The object specifies the session protocol to be used for internet
            call between local and remote router via IP backbone.
            unknown        The protocol is unknown.
            h323           The protocol is H323.
            sip            The protocol is session initiation."
        ::= { unisVoiceVoIPCallHistoryEntry 8 }

unisVoVoIPCallHistoryCoderType OBJECT-TYPE
        SYNTAX      UnisCodecType
        MAX-ACCESS  read-only
        STATUS      current
        DESCRIPTION
            "The negotiated coder type.  It specifies the encode type to the
            VoIP leg of a call."
        ::= { unisVoiceVoIPCallHistoryEntry 9 }

END
