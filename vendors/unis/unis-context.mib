-- ===========================================================================================================
-- Copyright (c) 2020 Unisyue Technologies Co., Ltd.  All rights reserved.
--
-- Description: context MIB
-- Reference:
-- Version: V1.0
-- History:
-- revision 1.0 2014-3-18 created by c08124
--
-- ============================================================================================================
UNIS-CONTEXT-MIB DEFINITIONS ::= BEGIN

IMPORTS
    unisCommon
        FROM UNIS-OID-MIB
    Integer32, OBJECT-TYPE, MODULE-IDENTITY, NOTIFICATION-TYPE
        FROM SNMPv2-SMI
    DisplayString
        FROM SNMPv2-TC;

unisContext MODULE-IDENTITY
    LAST-UPDATED "201403180000Z"
    ORGANIZATION
        "Unisyue Technologies Co., Ltd."
    CONTACT-INFO
        ""
    DESCRIPTION
        "This MIB contains objects for managing context operations."

    REVISION "201403180000Z"
    DESCRIPTION
        "Initial revision of this MIB module."
    ::= { unisCommon 154 }

unisContextTables OBJECT IDENTIFIER ::= { unisContext 1 }

unisContextControl OBJECT IDENTIFIER ::= { unisContextTables 1 }


unisContextControlTable OBJECT-TYPE
    SYNTAX SEQUENCE OF UnisContextControlEntry
    MAX-ACCESS not-accessible
    STATUS current
    DESCRIPTION
        "This table is used to configure contexts for a device and
         show context status info."
    ::= { unisContextControl 1 }


unisContextControlEntry OBJECT-TYPE
    SYNTAX UnisContextControlEntry
    MAX-ACCESS not-accessible
    STATUS current
    DESCRIPTION
        "An entry of the unisContextControlTable.
         Each entry corresponds to one context."
    INDEX { unisContextIndex }
    ::= { unisContextControlTable 1 }

UnisContextControlEntry ::=
    SEQUENCE
        {
            unisContextIndex
                Integer32,
            unisContextName
                DisplayString
        }

unisContextIndex OBJECT-TYPE
    SYNTAX Integer32 (1..2147483647)
    MAX-ACCESS accessible-for-notify
    STATUS current
    DESCRIPTION
        "The value range of Context ID depends on the device model."
    ::= { unisContextControlEntry 1 }


unisContextName OBJECT-TYPE
    SYNTAX DisplayString (SIZE (1..15))
    MAX-ACCESS read-only
    STATUS current
    DESCRIPTION
        "Specifies the context name,
         a case-sensitive string of 1 to 15 characters.
         The context name cannot be modified once created."
    ::= { unisContextControlEntry 2 }


unisContextNotification OBJECT IDENTIFIER ::= { unisContext 8 }

unisContextNotificationObjects OBJECT IDENTIFIER ::= { unisContextNotification 0 }

unisContextStateChangeToActive NOTIFICATION-TYPE
    OBJECTS {unisContextIndex, unisContextName}
    STATUS current
    DESCRIPTION
        "The unisContextStateChangeToActive trap indicates
         that the context status has changed to active."
    ::= { unisContextNotificationObjects 1 }

unisContextStateChangeToInactive NOTIFICATION-TYPE
    OBJECTS {unisContextIndex, unisContextName}
    STATUS current
    DESCRIPTION
        "The unisContextStateChangeToInactive trap indicates
         that the context status has changed to inactive."
    ::= { unisContextNotificationObjects 2 }

END
