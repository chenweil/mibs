-- ===========================================================================================================
-- Copyright (c) 2020 Unisyue Technologies Co., Ltd.  All rights reserved.
--
-- Description: System Management MIB
-- Reference:
-- Version: V2.8
-- History:
--  revision 1.0 2002-12-20 created by xuqingwei
--  revision 1.1 2004-4-16  added the support for XRN  by xuqingwei
--  revision 1.2 2004-4-16  added 'unisSysImageType' in unisSysImageTable for dual image  by changxiangqing
--  revision 1.3 2004-5-14  convert MIB object name from unisXXX to unis, etc.
--  revision 1.31 2004-7-16 1. modified 'unisSysImageSize' in unisSysImageTable by zhaolina
--                      2.modified SYNTAX of 'unisSysReloadImage','unisSysImageIndex','unisSysCFGFileIndex'
--                           from (1..2147483647) to (0..2147483647) by zhaolina
--  revision 1.5 2004-8-1  1. added 'secure' attribute for unisSysImageType in unisSysImageTable by zhaolina
--                         2.modified 'MAX-ACCESS' of unisSysReloadTag from 'read-create' to 'read-write' by zhaolina
--                         3.modified DESCRIPTION of unisSysReloadNotification by zhaolina
--                         4.modified DESCRIPTION of unisSysImageType,unisSysImageIndex,unisSysImageTable and unisSysReloadImage by zhaolina
--  revision 1.6 2004-9-8  1.modified DESCRIPTION of unisSysImageType by wangyingxia
--                         2.added the trap object unisSysStartUpNotification by wangyingxia
--                         3.added unisSysStartUpNotification into the NOTIFICATION OF unisSystemManMIBNotifications
--  revision 1.7 2004-10-12 updated by gaolong
--               Change all underscore('_') characters to hyphen characters('-') because underscore character is not allowed in MIB module.
--               Remove unisSysCurEntPhysicalIndex from unisSysCurGroup because this object is not accessible.
--  revision 1.8 2004-11-08 Change the description of unisSysReloadScheduleIndex by gaolong
--  revision 1.9 2005-04-08 updated by songjie.
--               1. added the support of summer time.
--               2. correct word errors and adjust file format.
--  revision 2.0 2005-12-26 updated by jinyi
--               added unisSysCurBtmFileName, unisSysCurUpdateBtmFileName,
--               unisSysBtmLoadMaxNumber, and unisSysBtmLoadTable.
--  revision 2.1 2006-04-03 updated by shuaixiaojuan
--               modified descriptions of some objects.
--  revision 2.2 2009-06-07 Change the MAX-ACCESS of unisSysLocalClock.
--          V2.3 2010-03-17 add unisSysLocalClockString by jinyi
--  revision V2.4 2011-08-30 add  unisSysPackage, unisSysIpePackage by z02031
--  revision V2.5 2013-10-18 add unisSysPackageLoadAttribute, unisSysPackageModel, unisSysIpeFileModel,
--                unisSysIpePackageModel and unisSysSetBootImage by z03030 and z08715
--  revision V2.6 2015-07-07 add unisSysClockProtocolGroup, unisSysClockProtocol, unisSysClockProtocolSrcMdc
--                and unisSysClockProtocolSrcContext by l09650
--  revision V2.7 2017-05-27 add unisSysLocalClockString2 by h12133
--                2018-01-10 added 'interface' attribute for unisSysClockProtocol in unisSysClockProtocolGroup by t16382
--  revision V2.8 2020-02-21 added 'gnss' attribute for unisSysClockProtocol in unisSysClockProtocolGroup by d04404
-- ============================================================================================================
UNIS-SYS-MAN-MIB DEFINITIONS ::= BEGIN

IMPORTS
    OBJECT-GROUP, MODULE-COMPLIANCE, NOTIFICATION-GROUP
        FROM SNMPv2-CONF
    Integer32, OBJECT-TYPE, MODULE-IDENTITY, NOTIFICATION-TYPE, TimeTicks, Unsigned32
        FROM SNMPv2-SMI
    DateAndTime, DisplayString, RowStatus, TruthValue
        FROM SNMPv2-TC
    SnmpTagList, SnmpTagValue
        FROM SNMP-TARGET-MIB
    unisCommon
        FROM UNIS-OID-MIB;


unisSystemMan MODULE-IDENTITY
    LAST-UPDATED "202002210000Z"
    ORGANIZATION
        "Unisyue Technologies Co., Ltd."
    CONTACT-INFO
        ""
    DESCRIPTION
        "This MIB contains objects to manage the system.
         It focuses on the display of current configure file and image
         file,and the definition of reloading image.
         Add the support for XRN."
    REVISION     "202002210000Z"
    DESCRIPTION  "added 'gnss' attribute for unisSysClockProtocol in unisSysClockProtocolGroup."
    REVISION     "201801100000Z"
    DESCRIPTION  "added 'interface' attribute for unisSysClockProtocol in unisSysClockProtocolGroup."
    REVISION     "201706120000Z"
    DESCRIPTION  "Add unisSysLocalClockString2."
    REVISION     "201507270000Z"
    DESCRIPTION  "Add unisSysClockProtocolGroup, unisSysClockProtocol, unisSysClockProtocolSrcMdc
--                and unisSysClockProtocolSrcContext."
    REVISION "200404081345Z"        -- April 08, 2004 at 13:45 GMT
    DESCRIPTION
        " "
    ::= { unisCommon 3 }


-- XRN brief introduction:
--    Expandable resilient networking (XRN) is a technology to construct expandable
--    resilient networks. With XRN feature, you can connect several devices into a
--    combined device and treat them as a single one. The combined device is called
--    Fabric, while the member devices are units.




--
-- Node definitions
--

unisSystemManMIBObjects OBJECT IDENTIFIER ::= { unisSystemMan 1 }


unisSysClock OBJECT IDENTIFIER ::= { unisSystemManMIBObjects 1 }

unisSysLocalClock OBJECT-TYPE
    SYNTAX DateAndTime
    MAX-ACCESS read-write
    STATUS current
    DESCRIPTION
        "
        This node gives the current local time of the system.
        The unit of it is DateAndTime.
        "
    ::= { unisSysClock 1 }

unisSysSummerTime OBJECT IDENTIFIER ::= { unisSysClock 2 }

unisSysSummerTimeEnable OBJECT-TYPE
    SYNTAX INTEGER
    {
        enable(1),
        disable(2)
    }
    MAX-ACCESS read-only
    STATUS current
    DESCRIPTION
        "This node indicates the status of summer time.
        If the value of this node is enable, means that summer time is
        enabled.
        If the value is disable, means that summer time is disabled.
        "
    ::= { unisSysSummerTime 1 }

unisSysSummerTimeZone OBJECT-TYPE
    SYNTAX DisplayString (SIZE (0..255))
    MAX-ACCESS read-write
    STATUS current
    DESCRIPTION
        "
        This node describes the name of time zone in summer.
        The string is only used to display in local time when summer
        time is running.
        That the value of unisSysLocalClock has the time zone information
        means that summer time is running.
        "
    ::= { unisSysSummerTime 2 }

unisSysSummerTimeMethod OBJECT-TYPE
    SYNTAX INTEGER
    {
        oneOff(1),
        repeating(2)
    }
    MAX-ACCESS read-write
    STATUS current
    DESCRIPTION
        "
        This node provides the execute method of summer time.
        oneOff(1):   means that summer time only takes effect at specified time.
        repeating(2): means that summer time takes effect in specified month/day
                      once a year.
        "
    ::= { unisSysSummerTime 3 }

unisSysSummerTimeStart OBJECT-TYPE
    SYNTAX DateAndTime (SIZE(8))
    MAX-ACCESS read-write
    STATUS current
    DESCRIPTION
        "
        This node provides the start time of summer time.
        "
    ::= { unisSysSummerTime 4 }

unisSysSummerTimeEnd OBJECT-TYPE
    SYNTAX DateAndTime (SIZE(8))
    MAX-ACCESS read-write
    STATUS current
    DESCRIPTION
        "
        This node provides the end time of summer time.
        The end time must be more than start time one day and less
        than start time one year.
        "
    ::= { unisSysSummerTime 5 }

unisSysSummerTimeOffset OBJECT-TYPE
    SYNTAX Integer32 (0..86399)
    MAX-ACCESS read-write
    STATUS current
    DESCRIPTION
        "
        This node provides the offset time of summer time.
        The offset time(in seconds) means that how much time need to be
        appended to the local time.
        "
    ::= { unisSysSummerTime 6 }

unisSysLocalClockString OBJECT-TYPE
    SYNTAX OCTET STRING(SIZE (16..24))
    MAX-ACCESS read-write
    STATUS current
    DESCRIPTION
        "This node gives the current local time of the system.
        For example, Tuesday May 26, 2002 at 1:30:15 would be
        displayed as: 2002-5-26T13:30:15.0Z"
    ::= { unisSysClock 3 }

unisSysClockProtocolGroup OBJECT IDENTIFIER ::= { unisSysClock 4 }

unisSysLocalClockString2 OBJECT-TYPE
    SYNTAX OCTET STRING(SIZE (14..19))
    MAX-ACCESS read-write
    STATUS current
    DESCRIPTION
        "This node gives the current local time of the system.
        For example, 1:30:15 on Tuesday, May 26th, 2002 will be
        displayed as: 2002/05/26/01/30/15.
        2002/5/26/1/30/15 or 2002/05/26/01/30/15 will be applied in a write operation."
    ::= { unisSysClock 5 }

unisSysClockProtocol OBJECT-TYPE
    SYNTAX INTEGER
        {
        none(1),
        ntp(2),
        ptp(3),
        interface(4),
        gnss(5)
         }
    MAX-ACCESS read-write
    STATUS current
    DESCRIPTION
        "Writing none(1) to this object indicates to use the local system time.
        When the value is set to none(1), unisSysClockProtocolSrcMdc and
        unisSysClockProtocolSrcContext cannot be written and the value will be
        set to invalid.  Change system time will be performed through the node
        of unisSysLocalClock and unisSysSummerTime.
        Writing ntp(2) to this object indicates to use NTP time source.
        NTP means Network Time Protocol.  To get the system time through NTP,
        NTP must be configured successfully.  NTP time source can be obtained
        from non-default MDC and non-default context.
        When ntp(2) is set, the system time can't be changed manually.
        Support for this keyword depends on the device model.

        Writing ptp(3) to this object indicates to use PTP time source.
        PTP means Precision Time Protocol.  To get clock time through PTP, PTP
        must be configured successfully.  PTP time source can be obtained from
        non-default MDC but cannot be obtained from non-default context.
        When ptp(3) is set, the system time can't be changed manually.
        Support for this keyword depends on the device model.

        Writing interface(4) to this object indicates to get time source from interface.
        To get clock time through interface, interface must be configured successfully.
        When interface(4) is set, the system time can't be changed manually.
        Support for this keyword depends on the device model.

        Writing gnss(5) to this object indicates to get time source from Global
        Natvigtion Satelite System(GNSS).GNSS time source can be obtained from
        non-default MDC and non-default context. When gnss(5) is set, the system time
        can't be changed manually.
        Support for this keyword depends on the device model.

        All MDCs on the device share the same time source and use the same system time.
        The shared time source can be one of the following items:
        Local system time - the time signal that is generated by the local
        crystal oscillator
        Remote time source - the time signal that is obtained by the specified MDC
        from another device on the network."
    ::= { unisSysClockProtocolGroup 1 }

unisSysClockProtocolSrcMdc OBJECT-TYPE
    SYNTAX Integer32 (0..2147483647)
    MAX-ACCESS read-write
    STATUS current
    DESCRIPTION
        "The MDC ID that is used for the system time source.
        This node is valid when the clock protocol is NTP or PTP.
        If MDC is not supported on this system, this node is invalid.
        If the device supports MDC, the system time will be obtained
        from NTP or PTP on the specified MDC.
        If the device supports context and MDC, the most recent configuration of
        unisSysClockProtocolSrcContext and unisSysClockProtocolSrcMdc takes
        effect if set multiple times, and another one will be set to zero as an
        invalid value."
     DEFVAL { 1 }
    ::= { unisSysClockProtocolGroup 2 }

unisSysClockProtocolSrcContext OBJECT-TYPE
    SYNTAX Integer32 (0..2147483647)
    MAX-ACCESS read-write
    STATUS current
    DESCRIPTION
        "The context ID that is used for the system time source.
        This node is valid when the clock protocol is NTP or PTP.
        If context is not supported on this system, this node is invalid.
        If the system supports context, the system time will be obtained from
        NTP or PTP on the specified context.
        If the device supports context and MDC, the most recent configuration of
        unisSysClockProtocolSrcContext and unisSysClockProtocolSrcMdc takes
        effect if set multiple times, and another one will be set to zero as an
        invalid value."
    DEFVAL { 1 }
    ::= { unisSysClockProtocolGroup 3 }

unisSysCurrent OBJECT IDENTIFIER ::= { unisSystemManMIBObjects 2 }

unisSysCurTable OBJECT-TYPE
    SYNTAX SEQUENCE OF UnisSysCurEntry
    MAX-ACCESS not-accessible
    STATUS current
    DESCRIPTION
        "
        The current status of system. A configuration file, an image
        file and bootrom information are used to describe the current status.
        "
    ::= { unisSysCurrent 1 }

unisSysCurEntry OBJECT-TYPE
    SYNTAX UnisSysCurEntry
    MAX-ACCESS not-accessible
    STATUS current
    DESCRIPTION
        "
        An entry of unisSysCurTable.
        "
    INDEX { unisSysCurEntPhysicalIndex }
    ::= { unisSysCurTable 1 }

UnisSysCurEntry ::=
    SEQUENCE {
        unisSysCurEntPhysicalIndex       Integer32,
        unisSysCurCFGFileIndex           Integer32,
        unisSysCurImageIndex             Integer32,
        unisSysCurBtmFileName            OCTET STRING,
        unisSysCurUpdateBtmFileName      OCTET STRING
     }

unisSysCurEntPhysicalIndex OBJECT-TYPE
    SYNTAX Integer32 (0..2147483647)
    MAX-ACCESS not-accessible
    STATUS current
    DESCRIPTION
        "The value of this object is the entity index
         which depends on the implementation of ENTITY-MIB.
         If ENTITY-MIB is not supported, the value for this object is the unit ID for XRN devices ,
         0 for non-XRN device which has only one mainboard,
         the board number for non-XRN device which have several mainboards.
        "
    ::= { unisSysCurEntry 1 }

unisSysCurCFGFileIndex OBJECT-TYPE
    SYNTAX Integer32 (0..2147483647)
    MAX-ACCESS read-only
    STATUS current
    DESCRIPTION
        "
        The startup configuration file currently used by the specified entity.
        If the value of it is zero, no configuration file is used. It will be
        the value of corresponding unisSysCFGFileIndex in unisSysCFGFileTable.
        "
    ::= { unisSysCurEntry 2 }

unisSysCurImageIndex OBJECT-TYPE
    SYNTAX Integer32 (0..2147483647)
    MAX-ACCESS read-only
    STATUS current
    DESCRIPTION
        "The image file currently used by the specified entity.
        It will be the value of corresponding unisSysImageIndex
        in unisSysImageTable."
    ::= { unisSysCurEntry 3 }

unisSysCurBtmFileName OBJECT-TYPE
    SYNTAX OCTET STRING(SIZE (1..64))
    MAX-ACCESS read-only
    STATUS current
    DESCRIPTION
        "The bootrom file currently used by the specified entity."
    ::= { unisSysCurEntry 4 }

unisSysCurUpdateBtmFileName OBJECT-TYPE
    SYNTAX OCTET STRING(SIZE (1..64))
    MAX-ACCESS read-only
    STATUS current
    DESCRIPTION
        "
        The default value of this object is the same as the value of
        unisSysCurBtmFileName. The value will be changed after updating
        the bootrom successfully. This bootrom will take effect on next
        startup.
        "
    ::= { unisSysCurEntry 5 }

-- Begin define reload group
unisSysReload OBJECT IDENTIFIER ::= { unisSystemManMIBObjects 3 }

unisSysReloadSchedule OBJECT-TYPE
    SYNTAX Integer32 (0..2147483647)
    MAX-ACCESS read-write
    STATUS current
    DESCRIPTION
        "
        The object points one row in unisSysReloadScheduleTable.
        Its value is equal to the value of unisSysReloadScheduleIndex.
        When a reload action is finished, the value of it
        would be zero which means no any reload schedule is selected.
        "
    ::= { unisSysReload 1 }

unisSysReloadAction OBJECT-TYPE
    SYNTAX INTEGER
        {
        reloadUnavailable(1),
        reloadOnSchedule(2),
        reloadAtOnce(3),
        reloadCancel(4)
        }
    MAX-ACCESS read-write
    STATUS current
    DESCRIPTION
        "
        Writing reloadOnSchedule(2) to this object performs the reload operation on schedule.
        If unisSysReloadScheduleTime is not set, the value of unisSysReloadAction can't be set to
        'reloadOnSchedule(2)'.

        Writing reloadAtOnce(3)to this object performs the reload operation at once,
        regardless of the unisSysReloadScheduleTime.

        When reloadCancel(4)is set, the scheduled reload action will be cancelled and the value of
        unisSysReloadAction will be 'reloadUnavailable(1)',the value of unisSysReloadSchedule will be
        0, unisSysReloadTag will be given a value of zero length, but the content of
        unisSysReloadScheduleTable will remain.


        The unisSysReloadSchedule and unisSysReloadTag  determine the reload entity(ies) in mutually
        exclusive way. And the unisSysReloadSchedule will be handled at first. If the value of
        unisSysReloadSchedule is invalid, then the unisSysReloadTag will be handled.

        If the value of unisSysReloadSchedule is valid, the value of unisSysReloadTag is ignored and a
        reload action will be implemented to the entity specified by unisSysReloadEntity in the entry
        pointed by unisSysReloadSchedule.

        If unisSysReloadSchedule is valid, but the entry unisSysReloadSchedule pointing to is not active,
        the reload action will be ignored , and an inconsistent value will be returned.


        If multiple entities are required to be reloaded at the same time, the value of unisSysReloadTag
        must be specified to select the reload parameters in the unisSysReloadSceduelTable, and
        unisSysReloadSchedule must have the value of '0'.

        If the whole fabric is to be reloaded in an XRN device, all the units in the fabric must
        have at least one entry in the unisSysReloadSceduelTable with the same tag in unisSysReloadSceduelTagList.

        When a reload action is done, or there is no reload action, the value
        should be reloadUnavailable(1).
        "
    ::= { unisSysReload 2 }

unisSysReloadScheduleTable OBJECT-TYPE
    SYNTAX SEQUENCE OF UnisSysReloadScheduleEntry
    MAX-ACCESS not-accessible
    STATUS current
    DESCRIPTION
        "
        A reload parameters set table.

        The table is exclusively used for reloading.

        When reloading action finished, the value of the table may be empty or still exist.
        If the mainboard in non-XRN device or all the units of the fabric in XRN device are
        reloaded,then the table will be refreshed.
        "
    ::= { unisSysReload 3 }

unisSysReloadScheduleEntry OBJECT-TYPE
    SYNTAX UnisSysReloadScheduleEntry
    MAX-ACCESS not-accessible
    STATUS current
    DESCRIPTION
        "Entry of unisSysReloadScheduleTable."
    INDEX { unisSysReloadScheduleIndex }
    ::= { unisSysReloadScheduleTable 1 }

UnisSysReloadScheduleEntry ::=
    SEQUENCE {
        unisSysReloadScheduleIndex           Integer32,
        unisSysReloadEntity                  Integer32,
        unisSysReloadCfgFile                 Integer32,
        unisSysReloadImage                   Integer32,
        unisSysReloadReason                  DisplayString,
        unisSysReloadScheduleTime            DateAndTime,
        unisSysReloadRowStatus               RowStatus,
        unisSysReloadScheduleTagList         SnmpTagList
     }

unisSysReloadScheduleIndex OBJECT-TYPE
    SYNTAX Integer32 (1..2147483647)
    MAX-ACCESS not-accessible
    STATUS current
    DESCRIPTION
        "The index of unisSysReloadScheduleTable. There are two parts
        for this index depicted as follows:

        31                  15                  0
        +++++++++++++++++++++++++++++++++++++++++
        + physical index     +     random index +
        ( bit 16..31 )              ( bit 0..15 )
        +++++++++++++++++++++++++++++++++++++++++
        From bit0 to bit15 (two bytes), if the row is automatic created,
        the value is zero, and if the row is created by users, then the
        value is determined by the users.

        From bit16 to bit31 (two bytes) is the physical index the same as the
        entPhysicalIndex specified in ENTITY-MIB. For XRN devices,
        physical index is the value of a chassis entPhysicalIndex. 0 for non-XRN
        device which has only one main board, the board number for non-XRN device
        which have multiple main boards."
    ::= { unisSysReloadScheduleEntry 1 }

unisSysReloadEntity OBJECT-TYPE
    SYNTAX Integer32 (0..2147483647)
    MAX-ACCESS read-create
    STATUS current
    DESCRIPTION
        "
        The value of unisSysReloadEntity indicates an entry in entPhysicalTable,
        which is the physical entity to be reloaded.

        If ENTITY-MIB is not supported,the value for this object is the unit ID for XRN devices ,
        0 for non-XRN device which has only one mainboard,
        the board number for non-XRN device which have several mainboards.

        Each entity has only one row in unisSysReloadScheduleTable.
        "
    ::= { unisSysReloadScheduleEntry 2 }

unisSysReloadCfgFile OBJECT-TYPE
    SYNTAX Integer32 (0..2147483647)
    MAX-ACCESS read-create
    STATUS current
    DESCRIPTION
        "
        The value indicates an entry in unisSysCFGFileTable.
        It defines a configuration file for reload action.
        It is the value of corresponding unisSysCFGFileIndex in unisSysCFGFileTable.
        The zero value means no configuration file has been set for this entry, and
        no configuration file is used during system reloading.
        "
    ::= { unisSysReloadScheduleEntry 3 }

unisSysReloadImage OBJECT-TYPE
    SYNTAX Integer32 (0..2147483647)
    MAX-ACCESS read-create
    STATUS current
    DESCRIPTION
        "
        The value indicates an entry in unisSysImageTable.
        It defines an image file for reload action.
        It is the value of corresponding unisSysImageIndex in unisSysImageTable.

        If dual image is supported, the main image attribute can be
        set through this object or by unisSysImageType of unisSysImageTable
        of the entity. It is strongly suggested to set this attribute by
        the latter.

        If main image attribute is set here, the unisSysImageType in unisSysImageTable
        of the corresponding entity will be updated, and vice versa.

        Before reboot, the device will check the validation of the entry. If the file does
        not exist, the device will not reboot and a trap will be send to NMS.
        "
    ::= { unisSysReloadScheduleEntry 4 }

unisSysReloadReason OBJECT-TYPE
    SYNTAX DisplayString (SIZE (0..255))
    MAX-ACCESS read-create
    STATUS current
    DESCRIPTION
        "
        The reason of system's reloading.
        It is a zero length octet string when not set.
        "
    ::= { unisSysReloadScheduleEntry 5 }

unisSysReloadScheduleTime OBJECT-TYPE
    SYNTAX DateAndTime (SIZE(8))
    MAX-ACCESS read-create
    STATUS current
    DESCRIPTION
        "
        Specify the local time at which the reload action will
        occur. we will only take octet strings
        with length 8 for this object which indicates the
        local time of the switch. The maximum scheduled
        interval between the specified time and the current
        system clock time is 24 days .

            field  octets  contents                  range
            -----  ------  --------                  -----
              1      1-2   year                      0..65536
              2       3    month                     1..12
              3       4    day                       1..31
              4       5    hour                      0..23
              5       6    minutes                   0..59
              6       7    seconds                   0..60

         For example, Tuesday May 26, 1992 at 1:30:15 PM would be
         displayed as:

                    1992-5-26,13:30:15

        If the set value is less than the value of unisSysLocalClock
        or beyond the maximum scheduled time limit, a bad value error
        occurred.
        The value of all-zero octet strings indicates system reload
        at once if the reload action is reloadOnSchedule(2).
        "
    ::= { unisSysReloadScheduleEntry 6 }

unisSysReloadRowStatus OBJECT-TYPE
    SYNTAX RowStatus
    MAX-ACCESS read-create
    STATUS current
    DESCRIPTION
        "
        If one of the value of unisSysReloadEntity,unisSysReloadImage
        is invalid, the value of unisSysReloadRowStatus can not be set to the value
        of ACTIVE.

        A valid entry means the specified element is available in current system.
        "
    ::= { unisSysReloadScheduleEntry 7 }

unisSysReloadScheduleTagList OBJECT-TYPE
    SYNTAX SnmpTagList
    MAX-ACCESS read-create
    STATUS current
    DESCRIPTION
    "
    It specifies a tag list for the entry.
    "
    ::= { unisSysReloadScheduleEntry 8 }

unisSysReloadTag OBJECT-TYPE
    SYNTAX SnmpTagValue
    MAX-ACCESS read-write
    STATUS current
    DESCRIPTION
        "This object contains a single tag value which is used
        to select entries in the unisSysReloadScheduleTable.

        In the unisSysReloadScheduleTable,any entry that contains
        a tag value which is equal to the value of this object is
        selected.

        For example, the value of unisSysReloadTag is 'TOM',and the
        unisSysReloadScheduleTagList of each unisSysReloadScheduleTable
        entry are as follows:
        1)'TOM,ROBERT,MARY'
        2)'TOM,DAVE'
        3)'DAVE,MARY'
        Since there are 'TOM' in 1) and 2),so 1) and 2) are selected.


        If this object contains a value of zero length, no entries
        are selected.
        "
    ::= { unisSysReload 4 }
-- End define reload group
unisSysImage OBJECT IDENTIFIER ::= { unisSystemManMIBObjects 4 }

unisSysImageNum OBJECT-TYPE
    SYNTAX Integer32 (0..2147483647)
    MAX-ACCESS read-only
    STATUS current
    DESCRIPTION
        "
        The number of system images. It indicates the
        total entries of unisSysImageTable.
        "
    ::= { unisSysImage 1 }

unisSysImageTable OBJECT-TYPE
    SYNTAX SEQUENCE OF UnisSysImageEntry
    MAX-ACCESS not-accessible
    STATUS current
    DESCRIPTION
        "The system image management table.


        When 'copy srcfile destfile' is executed via the CLI, if destfile is not existed,
        then unisSysImageType of the new file will be 'none'; otherwise unisSysImageType keeps its current value.
        When 'move srcfile destfile' is executed via the CLI, unisSysImageType and unisSysImageIndex
         remain the same while unisSysImageLocation changes.
        When 'rename srcfile' is executed via the CLI,unisSysImageType and unisSysImageIndex remain the same
        while unisSysImageName changes.
        When 'delete srcfile' is executed via the CLI, the file is deleted from unisSysImageTable
        while index of the file keeps and will not be allocated.
        "
    ::= { unisSysImage 2 }

unisSysImageEntry OBJECT-TYPE
    SYNTAX UnisSysImageEntry
    MAX-ACCESS not-accessible
    STATUS current
    DESCRIPTION
        "
        An entity image entry. Each entry consists of information of an entity image.
        The unisSysImageIndex exclusively defines an image file.
        "
    INDEX { unisSysImageIndex }
    ::= { unisSysImageTable 1 }

UnisSysImageEntry ::=
    SEQUENCE {
        unisSysImageIndex            Integer32,
        unisSysImageName             DisplayString,
        unisSysImageSize             Integer32,
        unisSysImageLocation         DisplayString,
        unisSysImageType             INTEGER
     }

unisSysImageIndex OBJECT-TYPE
    SYNTAX Integer32 (0..2147483647)
    MAX-ACCESS not-accessible
    STATUS current
    DESCRIPTION
        "There are two parts for the index depicted as follows:

        31                15             0
        +++++++++++++++++++++++++++++++++++
        + physical index   +  image index +
        +++++++++++++++++++++++++++++++++++

        From bit0 to bit15 (two bytes) is the image index;Image file Index
        is a monotonically increasing integer for the sole purpose of indexing
        events.  When it reaches the maximum value, an extremely unlikely event,
        the agent wraps the value back to 1 and may flush existing entries.

        From bit16 to bit31 (two bytes) is the physical index the same as the
        entPhysicalIndex specified in ENTITY-MIB.
        If ENTITY-MIB is not supported,the value for this object is the unit ID for XRN
        devices ,0 for non-XRN device which has only one main board,the board number for
        non-XRN device which have several main boards.


        Any index beyond the above range will not be supported.

        If a file is added in, its unisSysImageIndex will be the maximum image index plus one.
                        If the image file is removed, renamed, or moved from one place to another,
                        its unisSysImageIndex is not reallocated.
                        If the image file's content is replaced, its unisSysImageIndex will not change.

        "
    ::= { unisSysImageEntry 1 }

unisSysImageName OBJECT-TYPE
    SYNTAX DisplayString (SIZE (0..255))
    MAX-ACCESS read-only
    STATUS current
    DESCRIPTION
        "The file name of the image. It MUST NOT contain the path of the file."
    ::= { unisSysImageEntry 2 }

unisSysImageSize OBJECT-TYPE
    SYNTAX Integer32 (1..2147483647)
    MAX-ACCESS read-only
    STATUS current
    DESCRIPTION
        "
        Size of the file in bytes.
        "
    ::= { unisSysImageEntry 3 }

unisSysImageLocation OBJECT-TYPE
    SYNTAX DisplayString (SIZE (0..255))
    MAX-ACCESS read-only
    STATUS current
    DESCRIPTION
        "
        The directory path of the image.
        Its form should be the same as what defined in file system.
        Currently it is defined as follows:
        For mainboard:   flash:/
        For slave mainboard and subboards: slotN#flash:/
        For XRN devices: unitN>slotN#flash:/
        "
    ::= { unisSysImageEntry 4 }

unisSysImageType OBJECT-TYPE
    SYNTAX INTEGER
        {
        main(1),
        backup(2),
        none(3),
        secure(4),
        main-backup(5),
        main-secure(6),
        backup-secure(7),
        main-backup-secure(8)
        }
    MAX-ACCESS read-write
    STATUS current
    DESCRIPTION
        "
        It indicates the reloading sequence attribute of the image.

        For devices which support dual image:

        If the value is 'main(1)',the image will be the first image
        in the next reloading procedure. If the value is 'backup(2)',
        the image will be used if the main image fails. If the value
        is 'secure(4)', the image will be used if the main image and
        backup image both fail. If the value is 'none(3)',the image will
        not be used in the next reloading procedure.

        At the same time,you also can specify the main image by
        unisSysReloadImage in unisSysReloadScheduleTable. If the
        image is different from previous main image, the previous main image
        will not be main image again. And the image table will update with
        this variation. Vice versa, if you have defined the reload schedule,
        and then you define a new main image through unisSysImageType when you
        are waiting the reload schedule to be executed, the real main image
        will be the latest one.


        It is strongly suggested to define the main image here, not by unisSysReloadImage
        in unisSysReloadScheduleTable.

        There are some rules for setting the value of unisSysImageType:

        a)When a new image file is defined as 'main' or 'backup' file,the unisSysImageType
          of old 'main' or 'backup' file will automatically be 'none'.
        b)It is forbidden to set 'none' attribute manually.
        c)It is forbidden to set 'secure' attribute manually.
        d)If 'main' image is set to 'backup', the file keeps 'main'. And vice versa.
          At this time, the file has 'main-backup' property.
        e)If the secure image is set to 'main' or 'backup', the file has 'main-secure' or 'backup-secure'property.
        f)If the secure image is set to 'main' and 'backup', the file has the 'main-backup-secure' property.
        g)If the none image is set to 'main' or 'backup', the file has the 'main' or 'backup' property.

        The following table describes whether it is ok to set to another state
        directly from original state.

                        +--------------+-----------+-------------+-------------+
                        |   set to     | set to    |  set to     |   set to    |
                        |              |           |             |             |
             original   |    'main'    | 'backup'  |  'none'     |  'secure'   |
             state      |              |           |             |             |
          --------------+--------------+-----------+-------------+-------------+
                        |              |           |             |             |
             main       |     ---      |   yes     |   no        |   no        |
                        |              |           |             |             |
                        |              |           |             |             |
          --------------+--------------+-----------+-------------|-------------+
                        |              |           |             |             |
             backup     |     yes      |   ---     |   no        |   no        |
                        |              |           |             |             |
          --------------+--------------+-----------+-------------|-------------+
                        |              |           |             |             |
                        |              |           |             |             |
              none      |     yes      |   yes     |   ---       |   no        |
                        |              |           |             |             |
          --------------+--------------+-----------+-------------+-------------+
                        |              |           |             |             |
              secure    |     yes      |   yes     |   no        |   ---       |
                        |              |           |             |             |
                        |              |           |             |             |
          --------------+--------------+-----------+-------------+-------------+

        If there is one main image in the system, one row of UnisSysReloadScheduleEntry
        whose  unisSysReloadImage is equal to the main image's unisSysImageIndex will be
        created automatically. But if any row is deleted, it will not be created
        automatically in unisSysReloadScheduleTable.




        For the device which doesn't support dual image(main/backup):

        Only 'main' and 'none' is supported and it only can be set from none to main.
        When a new image file is defined as 'main' file,the unisSysImageType of old 'main'
        file will automatically be 'none'.
        "
    ::= { unisSysImageEntry 5 }

-- End define sysImage group

unisSysCFGFile OBJECT IDENTIFIER ::= { unisSystemManMIBObjects 5 }

unisSysCFGFileNum OBJECT-TYPE
    SYNTAX Integer32 (0..2147483647)
    MAX-ACCESS read-only
    STATUS current
    DESCRIPTION
        "
        The number of the configuration files in the system. It indicates the
        total entries of unisSysCFGFileTable.
        "
    ::= { unisSysCFGFile 1 }

unisSysCFGFileTable OBJECT-TYPE
    SYNTAX SEQUENCE OF UnisSysCFGFileEntry
    MAX-ACCESS not-accessible
    STATUS current
    DESCRIPTION
        "A table of configuration files in this system.
         At present, the system doesn't support dual configure file,
         it should act as 'dual image' if dual configure file is
         supported.
        "
    ::= { unisSysCFGFile 2 }

unisSysCFGFileEntry OBJECT-TYPE
    SYNTAX UnisSysCFGFileEntry
    MAX-ACCESS not-accessible
    STATUS current
    DESCRIPTION
        "
        A configuration file entry. Each entry consists of information of
        a configuration file.
        unisSysCFGFileIndex exclusively decides a configuration file.
        "
    INDEX { unisSysCFGFileIndex }
    ::= { unisSysCFGFileTable 1 }

UnisSysCFGFileEntry ::=
    SEQUENCE {
        unisSysCFGFileIndex          Integer32,
        unisSysCFGFileName           DisplayString,
        unisSysCFGFileSize           Integer32,
        unisSysCFGFileLocation       DisplayString
     }

unisSysCFGFileIndex OBJECT-TYPE
    SYNTAX Integer32 (0..2147483647)
    MAX-ACCESS not-accessible
    STATUS current
    DESCRIPTION
       "There are two parts for the index depicted as follows:

        31                15             0
        +++++++++++++++++++++++++++++++++++
        + physical index  + cfgFile index +
        +++++++++++++++++++++++++++++++++++

        From bit0 to bit15 (two bytes) is the configuration file index; the
        configuration file index is a monotonically increasing integer for
        the sole purpose of indexing events. When it reaches the maximum
        value, an extremely unlikely event, the agent wraps the value back
        to 1 and may flush existing entries.

        From bit16 to bit31 (two bytes) is the physical index the same
        as the entPhysicalIndex specified in ENTITY-MIB.
        If ENTITY-MIB is not supported, the value for this object is the unit ID for XRN
        devices ,0 for non-XRN device which has only one slot,the board number for
        non-XRN device which have several slots.

        Any index beyond the above range will not be supported.
        "
    ::= { unisSysCFGFileEntry 1 }

unisSysCFGFileName OBJECT-TYPE
    SYNTAX DisplayString (SIZE (0..255))
    MAX-ACCESS read-only
    STATUS current
    DESCRIPTION
        "
        Configuration file name. The name should not include the colon (:)
        character as it is a special separator character used
        to delineate the device name, partition name and the
        file name.
        "
    ::= { unisSysCFGFileEntry 2 }

unisSysCFGFileSize OBJECT-TYPE
    SYNTAX Integer32 (1..2147483647)
    MAX-ACCESS read-only
    STATUS current
    DESCRIPTION
        "
        Size of the file in bytes. Note that it does
        not include the size of the filesystem file header.
        File size will always be non-zero.
        "
    ::= { unisSysCFGFileEntry 3 }

unisSysCFGFileLocation OBJECT-TYPE
    SYNTAX DisplayString (SIZE (0..255))
    MAX-ACCESS read-only
    STATUS current
    DESCRIPTION
        "
        The directory path of the image.
        Its form should be the same as what defined in filesystem.
        Currently it is defined as follows:
        For mainboard:   flash:/
        For slave mainboard and subboards: slotN#flash:/
        For XRN devices: unitN>slotN#flash:/
        "
    ::= { unisSysCFGFileEntry 4 }
-- End define CFGFile group

-- Begin define bootrom group
unisSysBtmFile OBJECT IDENTIFIER ::= { unisSystemManMIBObjects 6 }

unisSysBtmFileLoad OBJECT IDENTIFIER ::= { unisSysBtmFile 1 }

unisSysBtmLoadMaxNumber OBJECT-TYPE
    SYNTAX Integer32
    MAX-ACCESS read-only
    STATUS current
    DESCRIPTION
        "
        This object shows the maximum number of unisSysBtmLoadEntry in
        each device/unit.
        "
    ::= { unisSysBtmFileLoad 1 }

unisSysBtmLoadTable OBJECT-TYPE
    SYNTAX SEQUENCE OF UnisSysBtmLoadEntry
    MAX-ACCESS not-accessible
    STATUS current
    DESCRIPTION
        "
        This table is used to update the bootrom and show the results of
        the update operation.
        The bootrom files are listed at the unisFlhFileTable.  These files
        are used to update bootrom.
        "
    ::= { unisSysBtmFile 2 }

unisSysBtmLoadEntry OBJECT-TYPE
    SYNTAX UnisSysBtmLoadEntry
    MAX-ACCESS not-accessible
    STATUS current
    DESCRIPTION
        "
        Entries in the unisSysBtmLoadTable are created and deleted using
        the unisSysBtmRowStatus object.

        When a new row is being created and the number of entries is
        unisSysBtmLoadMaxNumber, the row with minimal value of
        unisSysBtmLoadTime and the value of unisSysBtmFileType is none(2),
        should be destroyed automatically.
        "
    INDEX { unisSysBtmLoadIndex }
    ::= { unisSysBtmLoadTable 1 }

UnisSysBtmLoadEntry ::=
    SEQUENCE {
        unisSysBtmLoadIndex          Integer32,
        unisSysBtmFileName           OCTET STRING,
        unisSysBtmFileType           INTEGER,
        unisSysBtmRowStatus          RowStatus,
        unisSysBtmErrorStatus        INTEGER,
        unisSysBtmLoadTime           TimeTicks
     }

unisSysBtmLoadIndex OBJECT-TYPE
    SYNTAX Integer32 (1..2147483647)
    MAX-ACCESS not-accessible
    STATUS current
    DESCRIPTION
        "
        The index of unisSysBtmLoadTable. There are two parts for this
        index depicted as follows:

        31                  15                  0
        +++++++++++++++++++++++++++++++++++++++++
        + physical index     +     random index +
        ( bit 16..31 )              ( bit 0..15 )
        +++++++++++++++++++++++++++++++++++++++++

        From bit0 to bit15 (two bytes), if the row is created by command
        line, the value is determined by system, and if the row is created
        by SNMP, the value is determined by users.

        From bit16 to bit31 (two bytes) is the physical index the same as
        the entPhysicalIndex specified in ENTITY-MIB.

        If ENTITY-MIB is not supported, the value of this object is the
        unit ID for XRN devices, 0 for non-XRN device which has only one
        main board, the board number for non-XRN device which has multiple
        main boards.
       "
    ::= { unisSysBtmLoadEntry 1 }

unisSysBtmFileName OBJECT-TYPE
    SYNTAX OCTET STRING(SIZE (1..64))
    MAX-ACCESS read-create
    STATUS current
    DESCRIPTION
        "
        The bootrom file name is determined by the users.  The file must
        exist in corresponding entity.

        The validity of the bootrom file will be identified by system.
        If the file is invalid, the bootrom should fail to be updated,
        and the value of unisSysBtmErrorStatus should be failed(4).
        "
    ::= { unisSysBtmLoadEntry 2 }

unisSysBtmFileType OBJECT-TYPE
    SYNTAX INTEGER
       {
       main(1),
       none(2)
       }
    MAX-ACCESS read-create
    STATUS current
    DESCRIPTION
        "
        main(1) - The effective bootrom file.
        none(2) - The noneffective file.

        When bootrom is being updated, this object must be set to main(1).

        When bootrom is updated successfully, this object should be
        main(1), and the former object with the same physical index should
        be none(2).

        When bootrom failed to be updated, this object should be none(2).
        "
    ::= { unisSysBtmLoadEntry 3 }

unisSysBtmRowStatus OBJECT-TYPE
    SYNTAX RowStatus
    MAX-ACCESS read-create
    STATUS current
    DESCRIPTION
        "
        Only support active(1), createAndGo(4), destroy(6).  When a row
        is created successfully, the value of this object should be active(1),
        the value of unisSysBtmFileName and unisSysBtmFileType can not be
        modified by users.

        When bootrom is being updated, the value of unisSysBtmErrorStatus
        is inProgress(2).

        When bootrom failed to be updated, the value of unisSysBtmErrorStatus
        should be failed(4).

        When bootrom is updated successfully, the value of unisSysBtmErrorStatus
        should be success(3).  The value of unisSysCurUpdateBtmFileName
        should change to the new bootrom file name.

        When another row is created successfully with the same physical
        index, and the update is successful, then the value of former
        unisSysBtmFileType should be none(2) automatically.

        If a row is destroyed, unisSysCurUpdateBtmFileName should not change.

        If a device/unit reboots, unisSysBtmLoadTable should be empty.
        "
    ::= { unisSysBtmLoadEntry 4 }

unisSysBtmErrorStatus OBJECT-TYPE
    SYNTAX INTEGER
       {
       invalidFile(1),
       inProgress(2),
       success(3),
       failed(4)
       }
    MAX-ACCESS read-only
    STATUS current
    DESCRIPTION
        "
        This object shows the status of the specified operation after
        creating a row.
        invalidFile(1) - file is invalid.
        inProgress(2)  - the operation is in progress.
        success(3)     - the operation was done successfully.
        failed(4)      - the operation failed.
        "
    ::= { unisSysBtmLoadEntry 5 }

unisSysBtmLoadTime OBJECT-TYPE
    SYNTAX TimeTicks
    MAX-ACCESS read-only
    STATUS current
    DESCRIPTION
        "
        This object indicates operation time.
        "
    ::= { unisSysBtmLoadEntry 6 }

-- End define Bootrom group

unisSysPackage OBJECT IDENTIFIER ::= { unisSystemManMIBObjects 7 }

unisSysPackageNum OBJECT-TYPE
    SYNTAX Integer32 (0..2147483647)
    MAX-ACCESS read-only
    STATUS current
    DESCRIPTION
        "
        The number of software packages.  It indicates the
        total entries of unisSysPackageTable.
        "
    ::= { unisSysPackage 1 }

unisSysPackageTable OBJECT-TYPE
    SYNTAX SEQUENCE OF UnisSysPackageEntry
    MAX-ACCESS not-accessible
    STATUS current
    DESCRIPTION
        "The system package management table.
        "
    ::= { unisSysPackage 2 }

unisSysPackageEntry OBJECT-TYPE
    SYNTAX UnisSysPackageEntry
    MAX-ACCESS not-accessible
    STATUS current
    DESCRIPTION
        "
        An software package entry.  Each entry consists of information of
        an software package.
        "
    INDEX { unisSysPackageIndex }
    ::= { unisSysPackageTable 1 }

UnisSysPackageEntry ::=
    SEQUENCE {
        unisSysPackageIndex            Integer32,
        unisSysPackageName             DisplayString,
        unisSysPackageSize             Unsigned32,
        unisSysPackageLocation         DisplayString,
        unisSysPackageType             INTEGER,
        unisSysPackageAttribute        INTEGER,
        unisSysPackageStatus           INTEGER,
        unisSysPackageDescription      DisplayString,
        unisSysPackageFeature          DisplayString,
        unisSysPackageVersion          DisplayString,
        unisSysPackageLoadAttribute    INTEGER,
        unisSysPackageModel            DisplayString
    }

unisSysPackageIndex OBJECT-TYPE
    SYNTAX Integer32 (1..2147483647)
    MAX-ACCESS not-accessible
    STATUS current
    DESCRIPTION
        "There are two parts for the index depicted as follows:

        31                15             0
        +++++++++++++++++++++++++++++++++++
        + physical index   +  package index +
        +++++++++++++++++++++++++++++++++++

        From bit0 to bit15 (two bytes) is the Package index; Package file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its unisSysPackageIndex will be the maximum
        image index plus one.
        If the package file is removed, renamed, or moved from one place to
        another, its unisSysPackageIndex is not reallocated.
        If the package file's content is replaced, its unisSysPackageIndex will
        not change.
        "
    ::= { unisSysPackageEntry 1 }

unisSysPackageName OBJECT-TYPE
    SYNTAX DisplayString (SIZE (0..255))
    MAX-ACCESS read-only
    STATUS current
    DESCRIPTION
        "
        The file name of the package.  It MUST NOT contain the path
        of the file.
        "
    ::= { unisSysPackageEntry 2 }

unisSysPackageSize OBJECT-TYPE
    SYNTAX Unsigned32 (1..4294967295)
    MAX-ACCESS read-only
    STATUS current
    DESCRIPTION
        "
        Size of the file in bytes.
        "
    ::= { unisSysPackageEntry 3 }

unisSysPackageLocation OBJECT-TYPE
    SYNTAX DisplayString (SIZE (0..255))
    MAX-ACCESS read-only
    STATUS current
    DESCRIPTION
        "
        The directory path of the package.
        Its form should be the same as what defined in file system.
        Currently it is defined as follows:
        For mainboard:   flash:/
        For slave mainboard and subboards: slotN#flash:/
        "
    ::= { unisSysPackageEntry 4 }

unisSysPackageType OBJECT-TYPE
    SYNTAX INTEGER
        {
        boot(1),
        system(2),
        feature(3),
        patch(4)
        }
    MAX-ACCESS read-only
    STATUS current
    DESCRIPTION
        "
        It indicates the type of the package file.
        boot    :  kernel, file system, memory management and other
                   core components.
        system  :  interface management, configuration management and other
                   basic system package.
        feature :  feature packages, providing different services.
        patch   :  patch file contains fixes for a specific defect.
        "
    ::= { unisSysPackageEntry 5 }

unisSysPackageAttribute OBJECT-TYPE
    SYNTAX INTEGER
        {
        none(1),
        primary(2),
        secondary(3),
        primarySecondary(4)
        }
    MAX-ACCESS read-write
    STATUS current
    DESCRIPTION
        "
        It indicates the attribute of the package file.
        If the value is 'primary', the package will be the first package
        in the next reloading procedure.  If the value is 'secondary',
        the package will be used if the primary package fails.
        If the value is 'none', it will not be used in the next reloading
        procedure.
        "
    ::= { unisSysPackageEntry 6 }

unisSysPackageStatus OBJECT-TYPE
    SYNTAX INTEGER
        {
        active(1),
        inactive(2)
        }
    MAX-ACCESS read-only
    STATUS current
    DESCRIPTION
    "
    It indicates the status of the package file.  If this file is used in the
    current system, its status is 'active'.
    "
    ::= { unisSysPackageEntry 7 }

unisSysPackageDescription OBJECT-TYPE
    SYNTAX DisplayString (SIZE (0..255))
    MAX-ACCESS read-only
    STATUS current
    DESCRIPTION
    "
    It is the description of the package.
    "
    ::= { unisSysPackageEntry 8 }

unisSysPackageFeature OBJECT-TYPE
    SYNTAX DisplayString (SIZE (0..255))
    MAX-ACCESS read-only
    STATUS current
    DESCRIPTION
    "
    Indicate the feature of the package.  Different package files
    could be the same feature.
    "
    ::= { unisSysPackageEntry 9 }

unisSysPackageVersion OBJECT-TYPE
    SYNTAX DisplayString (SIZE (0..255))
    MAX-ACCESS read-only
    STATUS current
    DESCRIPTION
    "
    Indicate the version of the package.
    "
    ::= { unisSysPackageEntry 10 }

unisSysPackageLoadAttribute OBJECT-TYPE
    SYNTAX INTEGER
    {
        none(1),
        primary(2),
        secondary(3),
        primarySecondary(4)
    }
    MAX-ACCESS read-write
    STATUS current
    DESCRIPTION
    "File attribute of the startup image for an extended device to load from
    the parent device.  Examples of extended devices include PEXs and firewall
    modules.  The none attribute is returned if the image is not for extended
    devices, or if the load attribute is not specified."
    ::= { unisSysPackageEntry 11 }

unisSysPackageModel OBJECT-TYPE
    SYNTAX DisplayString (SIZE (0..63))
    MAX-ACCESS read-only
    STATUS current
    DESCRIPTION
    "Indicates whether the image file is for an extended device or the parent
    device.  Examples of extended devices include PEXs and firewall modules."
    ::= { unisSysPackageEntry 12 }

-- begin package operate table
unisSysPackageOperateEntryLimit OBJECT-TYPE
    SYNTAX Integer32 (0..2147483647)
    MAX-ACCESS read-write
    STATUS current
    DESCRIPTION
        "
        The maximum number of the entries in unisSysPackageOperateTable.
        "
    ::= { unisSysPackage 3 }

unisSysPackageOperateTable OBJECT-TYPE
    SYNTAX SEQUENCE OF UnisSysPackageOperateEntry
    MAX-ACCESS not-accessible
    STATUS current
    DESCRIPTION
        "A table of package file operate."
   ::= { unisSysPackage 4 }

unisSysPackageOperateEntry OBJECT-TYPE
    SYNTAX UnisSysPackageOperateEntry
    MAX-ACCESS not-accessible
    STATUS current
    DESCRIPTION
        "
        An operate request entry.
        "
    INDEX { unisSysPackageOperateIndex }
    ::= { unisSysPackageOperateTable 1 }

UnisSysPackageOperateEntry ::=
    SEQUENCE {
        unisSysPackageOperateIndex                   Integer32,
        unisSysPackageOperatePackIndex               Integer32,
        unisSysPackageOperateStatus                  INTEGER,
        unisSysPackageOperateRowStatus               RowStatus,
        unisSysPackageOperateResult                  INTEGER
     }

unisSysPackageOperateIndex OBJECT-TYPE
    SYNTAX Integer32 (1..2147483647)
    MAX-ACCESS not-accessible
    STATUS current
    DESCRIPTION
        "
        The unique index value of a row in this table.
        "
    ::= { unisSysPackageOperateEntry 1 }

unisSysPackageOperatePackIndex OBJECT-TYPE
    SYNTAX Integer32 (1..2147483647)
    MAX-ACCESS   read-create
    STATUS current
    DESCRIPTION
        "
        Specify the package file in the unisSysPackageTable.
        "
    ::= { unisSysPackageOperateEntry 2 }

unisSysPackageOperateStatus OBJECT-TYPE
    SYNTAX INTEGER
        {
        active(1),
        inactive(2)
        }
    MAX-ACCESS read-create
    STATUS current
    DESCRIPTION
        "
        activate or deactivate a package in the unisSysPackageTable.
        "
    ::= { unisSysPackageOperateEntry 3 }

unisSysPackageOperateRowStatus OBJECT-TYPE
    SYNTAX  RowStatus
    MAX-ACCESS read-create
    STATUS current
    DESCRIPTION
        "
        the status of this table entry.
        When the status is active all the
        object's value in the entry is not
        allowed to modified.
        "
    ::= { unisSysPackageOperateEntry 4 }

unisSysPackageOperateResult OBJECT-TYPE
    SYNTAX  INTEGER
      {
        opInProgress(1),
        opSuccess(2),
        opUnknownFailure(3),
        opInvalidFile(4),
        opNotSupport(5)
      }
    MAX-ACCESS read-only
    STATUS current
    DESCRIPTION
        "
        the result of the operation.
        "
    ::= { unisSysPackageOperateEntry 5 }
-- End define sysPackage group

-- Begin define sysIpe group
unisSysIpeFile OBJECT IDENTIFIER ::= { unisSystemManMIBObjects 8 }

unisSysIpeFileNum OBJECT-TYPE
    SYNTAX Integer32 (0..2147483647)
    MAX-ACCESS read-only
    STATUS current
    DESCRIPTION
        "
        The number of software IPE(Image Package Envelop) files.
        It indicates the total entries of unisSysIpeFileTable.
        "
    ::= { unisSysIpeFile 1 }

unisSysIpeFileTable OBJECT-TYPE
    SYNTAX SEQUENCE OF UnisSysIpeFileEntry
    MAX-ACCESS not-accessible
    STATUS current
    DESCRIPTION
        "The system IPE file manage table.
        "
    ::= { unisSysIpeFile 2 }

unisSysIpeFileEntry OBJECT-TYPE
    SYNTAX UnisSysIpeFileEntry
    MAX-ACCESS not-accessible
    STATUS current
    DESCRIPTION
        "
        An IPE package file entry.  Each entry consists of information of
        an IPE package file.
        unisSysIpeFileIndex exclusively decides an IPE file.
        "
    INDEX { unisSysIpeFileIndex }
    ::= { unisSysIpeFileTable 1 }

UnisSysIpeFileEntry ::=
    SEQUENCE {
        unisSysIpeFileIndex            Integer32,
        unisSysIpeFileName             DisplayString,
        unisSysIpeFileSize             Unsigned32,
        unisSysIpeFileLocation         DisplayString,
        unisSysIpeFileModel            SnmpTagList
     }

unisSysIpeFileIndex OBJECT-TYPE
    SYNTAX Integer32 (1..2147483647)
    MAX-ACCESS not-accessible
    STATUS current
    DESCRIPTION
        "There are two parts for the index depicted as follows:

        31                15             0
        +++++++++++++++++++++++++++++++++++
        + physical index   +  IPE   index +
        +++++++++++++++++++++++++++++++++++

        From bit0 to bit15 (two bytes) is the IPE file index; IPE file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its unisSysIpeFileIndex will be the maximum image
        ndex plus one.
        If the IPE file is removed, renamed, or moved from one place to
        another, its unisSysIpeFileIndex is not reallocated.
        If the IPE file's content is replaced, its unisSysIpeFileIndex will not
        change.
        "
    ::= { unisSysIpeFileEntry 1 }

unisSysIpeFileName OBJECT-TYPE
    SYNTAX DisplayString (SIZE (0..255))
    MAX-ACCESS read-only
    STATUS current
    DESCRIPTION
        "
        The file name of the IPE file.  It MUST NOT contain the path of
        the file.
        "
    ::= { unisSysIpeFileEntry 2 }

unisSysIpeFileSize OBJECT-TYPE
    SYNTAX Unsigned32 (1..4294967295)
    MAX-ACCESS read-only
    STATUS current
    DESCRIPTION
        "
        Size of the file in bytes.
        "
    ::= { unisSysIpeFileEntry 3 }

unisSysIpeFileLocation OBJECT-TYPE
    SYNTAX DisplayString (SIZE (0..255))
    MAX-ACCESS read-only
    STATUS current
    DESCRIPTION
        "
        The directory path of the IPE file.
        Its form should be the same as what defined in file system.
        Currently it is defined as follows:
        For mainboard:   flash:/
        For slave mainboard and subboards: slotN#flash:/
        "
    ::= { unisSysIpeFileEntry 4 }

unisSysIpeFileModel OBJECT-TYPE
    SYNTAX SnmpTagList
    MAX-ACCESS read-only
    STATUS current
    DESCRIPTION
        "Device models for which the IPE file contains software images.  For
        the ease of software upgrade, an IPE file might contain software images
        for a parent device and extended devices.  Examples of extended devices
        include PEXs and firewall modules."
    ::= { unisSysIpeFileEntry 5 }

-- Begin define Ipe-package
unisSysIpePackageTable OBJECT-TYPE
    SYNTAX SEQUENCE OF UnisSysIpePackageEntry
    MAX-ACCESS not-accessible
    STATUS current
    DESCRIPTION
        "
        The IPE package file table.  It shows the package files in
        the IPE file.
        "
    ::= { unisSysIpeFile 3 }

unisSysIpePackageEntry OBJECT-TYPE
    SYNTAX UnisSysIpePackageEntry
    MAX-ACCESS not-accessible
    STATUS current
    DESCRIPTION
        "
        An entry of the unisIpePackageTable.  Indexed by
        unisSysIpeFileIndex and unisSysIpePackageIndex.
        "
    INDEX { unisSysIpeFileIndex, unisSysIpePackageIndex }
    ::= { unisSysIpePackageTable 1 }

UnisSysIpePackageEntry ::=
    SEQUENCE {
        unisSysIpePackageIndex            Integer32,
        unisSysIpePackageName             DisplayString,
        unisSysIpePackageSize             Unsigned32,
        unisSysIpePackageType             INTEGER,
        unisSysIpePackageDescription      DisplayString,
        unisSysIpePackageFeature          DisplayString,
        unisSysIpePackageVersion          DisplayString,
        unisSysIpePackageModel            DisplayString
     }

unisSysIpePackageIndex OBJECT-TYPE
    SYNTAX Integer32 (1..2147483647)
    MAX-ACCESS not-accessible
    STATUS current
    DESCRIPTION
        "
        It is the IPE package index; IPE Package Index
        is a monotonically increasing integer for the sole purpose of indexing
        events.  When it reaches the maximum value, an extremely unlikely
        event, the agent wraps the value back to 1 and may flush existing
        entries.

        Any index beyond the above range will not be supported.
        "
    ::= { unisSysIpePackageEntry 1 }

unisSysIpePackageName OBJECT-TYPE
    SYNTAX DisplayString (SIZE (0..255))
    MAX-ACCESS read-only
    STATUS current
    DESCRIPTION
        "The file name of the package file."
    ::= { unisSysIpePackageEntry 2 }

unisSysIpePackageSize OBJECT-TYPE
    SYNTAX Unsigned32 (1..4294967295)
    MAX-ACCESS read-only
    STATUS current
    DESCRIPTION
        "
        Size of the package file in bytes.
        "
    ::= { unisSysIpePackageEntry 3 }

unisSysIpePackageType OBJECT-TYPE
    SYNTAX INTEGER
        {
        boot(1),
        system(2),
        feature(3),
        patch(4)
        }
    MAX-ACCESS read-only
    STATUS current
    DESCRIPTION
        "
        It indicates the type of the package file.
        boot    : kernel, file system, memory management and
                  other core components.
        system  : interface management, configuration management and
                  other basic system package.
        feature : feature packages, providing different services.
        patch   : patch file contains fixes for a specific defect.
        "
    ::= { unisSysIpePackageEntry 4 }

unisSysIpePackageDescription OBJECT-TYPE
    SYNTAX DisplayString (SIZE (0..255))
    MAX-ACCESS read-only
    STATUS current
    DESCRIPTION
    "
    It is the description of the package.
    "
    ::= { unisSysIpePackageEntry 5 }

unisSysIpePackageFeature OBJECT-TYPE
    SYNTAX DisplayString (SIZE (0..255))
    MAX-ACCESS read-only
    STATUS current
    DESCRIPTION
    "
    Indicate the feature of the package.
    "
    ::= { unisSysIpePackageEntry 6 }

unisSysIpePackageVersion OBJECT-TYPE
    SYNTAX DisplayString (SIZE (0..255))
    MAX-ACCESS read-only
    STATUS current
    DESCRIPTION
    "
    The version of the package.
    "
    ::= { unisSysIpePackageEntry 7 }

unisSysIpePackageModel OBJECT-TYPE
    SYNTAX DisplayString (SIZE (0..63))
    MAX-ACCESS read-only
    STATUS current
    DESCRIPTION
    "Indicates whether the image package file is for an extended device, the
    parent device, or both.  Examples of extended devices include PEXs and
    firewall modules."
    ::= { unisSysIpePackageEntry 8 }
-- End define Ipe-package

-- Begin define Ipe File operate table
unisSysIpeFileOperateTable OBJECT-TYPE
    SYNTAX SEQUENCE OF UnisSysIpeFileOperateEntry
    MAX-ACCESS not-accessible
    STATUS current
    DESCRIPTION
        "A table of IPE file operate."
   ::= { unisSysIpeFile 4 }

unisSysIpeFileOperateEntry OBJECT-TYPE
    SYNTAX UnisSysIpeFileOperateEntry
    MAX-ACCESS not-accessible
    STATUS current
    DESCRIPTION
        "
        An operate request entry.
        "
    INDEX { unisSysIpeFileOperateIndex }
    ::= { unisSysIpeFileOperateTable 1 }

UnisSysIpeFileOperateEntry ::=
    SEQUENCE {
        unisSysIpeFileOperateIndex                   Integer32,
        unisSysIpeFileOperateFileIndex               Integer32,
        unisSysIpeFileOperateAttribute               INTEGER,
        unisSysIpeFileOperateRowStatus               RowStatus,
        unisSysIpeFileOperateResult                  INTEGER
     }

unisSysIpeFileOperateIndex OBJECT-TYPE
    SYNTAX Integer32 (1..2147483647)
    MAX-ACCESS not-accessible
    STATUS current
    DESCRIPTION
        "
        The unique index value of a row in this table.
        "
    ::= { unisSysIpeFileOperateEntry 1 }

unisSysIpeFileOperateFileIndex OBJECT-TYPE
    SYNTAX Integer32 (1..2147483647)
    MAX-ACCESS   read-create
    STATUS current
    DESCRIPTION
        "
        Specify the IPE file in the unisSysIpeFileTable.  This IPE file
        will be unpacked to package files.
        "
    ::= { unisSysIpeFileOperateEntry 2 }

unisSysIpeFileOperateAttribute OBJECT-TYPE
    SYNTAX INTEGER
        {
        none(1),
        primary(2),
        secondary(3),
        primarySecondary(4)
        }
    MAX-ACCESS read-create
    STATUS current
    DESCRIPTION
        "
        It indicates the attribute of the IPE file when it is used in the reloading.
        If the value is 'primary', the packages in the IPE file will be the
        first packages in the next reloading procedure.
        If the value is 'secondary', the package in the IPE file will be used
        if the primary packages fails.
        If the value is 'none', the IPE file is only unpacked,
        will not be used in the reloading procedure.
        "
    ::= { unisSysIpeFileOperateEntry 3 }

unisSysIpeFileOperateRowStatus OBJECT-TYPE
    SYNTAX  RowStatus
    MAX-ACCESS read-create
    STATUS current
    DESCRIPTION
        "
        the status of this table entry.
        When the status is active all the
        object's value in the entry is not
        allowed to modified.
        "
    ::= { unisSysIpeFileOperateEntry 4 }

unisSysIpeFileOperateResult OBJECT-TYPE
    SYNTAX  INTEGER
      {
        opInProgress(1),
        opSuccess(2),
        opUnknownFailure(3),
        opInvalidFile(4),
        opDeviceFull(5),
        opFileOpenError(6)
      }
    MAX-ACCESS read-only
    STATUS current
    DESCRIPTION
        "
        the result of the operation.
        "
    ::= { unisSysIpeFileOperateEntry 5 }
-- End define IpePackage operate table

unisSysSetBootImage OBJECT IDENTIFIER ::= { unisSystemManMIBObjects 9 }

unisSysSetBootImageOp OBJECT IDENTIFIER ::= { unisSysSetBootImage 1 }

unisSysSetBootImageAction OBJECT-TYPE
    SYNTAX INTEGER
        {
        none(1),
        done(2),
        bootLoadPrimary(3),
        bootLoadSecondary(4),
        bootLoadPrimarySecondary(5),
        bootPrimary(6),
        bootSecondary(7),
        bootPrimarySecondary(8),
        loadPrimary(9),
        loadSecondary(10),
        loadPrimarySecondary(11)
        }
    MAX-ACCESS read-write
    STATUS current
    DESCRIPTION
        "Sets images as primary startup images, secondary startup images, or
        both.  Primary startup images are also called 'main' startup images.
        For extended devices, startup images saved on their local media are
        called 'local startup images,' and images saved on the parent device
        are called 'remote startup images.'
        none: Returns a success without setting image attributes.
        done: Clears data for the previous startup image operation.  This
        object must be set 'done' before each startup image operation.

        -------------------------+-----------------------+---------------------------------------------------
            Action               |   Parent devices      |                  Extended devices
        -------------------------+-----------------------+---------------------------------------------------
        bootLoadPrimary          | Sets images as the    | Sets images as the primary startup images
                                 | primary startup       |
                                 | images                | With storage medium: Sets both local and
                                 |                       |                      remote startup images
                                 |                       | Without storage medium: Sets remote startup images
        -------------------------+-----------------------+---------------------------------------------------
        bootLoadSecondary        | Sets images as the    | Sets images as the backup startup images
                                 | backup startup images |
                                 |                       | With storage medium: Sets both local and
                                 |                       |                      remote startup images
                                 |                       | Without storage medium: Sets remote startup images
        -------------------------+-----------------------+---------------------------------------------------
        bootLoadPrimarySecondary | Sets images as both   | Sets images as both the primary and backup startup
                                 | the primary and       | images
                                 | backup startup images | With storage medium: Sets both local and
                                 |                       |                      remote startup images
                                 |                       | Without storage medium: Sets remote startup images
        -------------------------+-----------------------+---------------------------------------------------
        bootPrimary              | Sets images as the    | Sets images as the primary startup images
                                 | primary startup       |
                                 | images                | With storage medium: Sets local startup images
                                 |                       | Without storage medium: N/A
        -------------------------+-----------------------+---------------------------------------------------
        bootSecondary            | Sets images as the    | Sets images as the backup startup images
                                 | backup startup images |
                                 |                       | With storage medium: Sets local startup images
                                 |                       | Without storage medium: N/A
        -------------------------+-----------------------+---------------------------------------------------
        bootPrimarySecondary     | Sets images as both   | Sets images as both the primary and backup startup
                                 | the primary and       | images
                                 | backup startup images | With storage medium: Sets local startup images
                                 |                       | Without storage medium: N/A
        -------------------------+-----------------------+---------------------------------------------------
        loadPrimary              | N/A                   | Sets images as the remote primary startup images
        -------------------------+-----------------------+---------------------------------------------------
        loadSecondary            | N/A                   | Sets images as the remote backup startup images
        -------------------------+-----------------------+---------------------------------------------------
        loadPrimarySecondary     | N/A                   | Sets images as both the remote primary and
                                 |                       | backup startup images
        -------------------------+-----------------------+---------------------------------------------------
        "
    ::= { unisSysSetBootImageOp 1 }

unisSysSetBootImageFileOverWrite OBJECT-TYPE
    SYNTAX TruthValue
    MAX-ACCESS read-write
    STATUS current
    DESCRIPTION
        "Determines whether to overwrite the existing image file with the same
        name as the downloaded image file. "
    DEFVAL { false }
    ::= { unisSysSetBootImageOp 2 }

unisSysSetBootImageRemoveIpeFile OBJECT-TYPE
    SYNTAX TruthValue
    MAX-ACCESS read-write
    STATUS current
    DESCRIPTION
        "Determines whether the IPE file will be removed when the startup
        images are set successfully.  If this object is set to TRUE,
        the IPE file will be removed."
    DEFVAL { false }
    ::= { unisSysSetBootImageOp 3 }

unisSysSetBootImageStatus OBJECT-TYPE
    SYNTAX INTEGER
        {
        none(1),
        doing(2),
        success(3),
        failed(4)
        }
    MAX-ACCESS read-only
    STATUS current
    DESCRIPTION
        "Status of the startup image set operation."
    ::= { unisSysSetBootImageOp 4 }

unisSysSetBootImageFailedReason OBJECT-TYPE
    SYNTAX DisplayString (SIZE (0..255))
    MAX-ACCESS read-only
    STATUS current
    DESCRIPTION
        "Startup image operation failure reason.  The field is empty if the
        operation was successful."
    ::= { unisSysSetBootImageOp 5 }

unisSysBootPackageTable OBJECT-TYPE
    SYNTAX SEQUENCE OF UnisSysBootPackageEntry
    MAX-ACCESS not-accessible
    STATUS current
    DESCRIPTION
        "Table of images to be set as startup images.  It should be used when
         unisSysBootIpeTable is empty."
    ::= { unisSysSetBootImage 2 }

unisSysBootPackageEntry OBJECT-TYPE
    SYNTAX UnisSysBootPackageEntry
    MAX-ACCESS not-accessible
    STATUS current
    DESCRIPTION
        "Entry of the image table."
    INDEX { unisSysBootPackageIndex }
    ::= { unisSysBootPackageTable 1 }

UnisSysBootPackageEntry ::=
    SEQUENCE {
        unisSysBootPackageIndex
            Integer32,
        unisSysBootPackageRowStatus
            RowStatus
     }

unisSysBootPackageIndex OBJECT-TYPE
    SYNTAX Integer32 (1..2147483647)
    MAX-ACCESS not-accessible
    STATUS current
    DESCRIPTION
        "Index of the software images.  The index must be included
        in unisSysPackageTable."
    ::= { unisSysBootPackageEntry 1 }

unisSysBootPackageRowStatus OBJECT-TYPE
    SYNTAX RowStatus
    MAX-ACCESS read-create
    STATUS current
    DESCRIPTION
        "Row status of the image entry."
    ::= { unisSysBootPackageEntry 2 }

unisSysBootIpeTable OBJECT-TYPE
    SYNTAX SEQUENCE OF UnisSysBootIpeEntry
    MAX-ACCESS not-accessible
    STATUS current
    DESCRIPTION
        "Table of the IPE files to be set for startup.  It should be used when
        unisSysBootPackageTable is empty."
    ::= { unisSysSetBootImage 3 }

unisSysBootIpeEntry OBJECT-TYPE
    SYNTAX UnisSysBootIpeEntry
    MAX-ACCESS not-accessible
    STATUS current
    DESCRIPTION
        "Entry in the IPE file table."
    INDEX { unisSysBootIpeIndex }
    ::= { unisSysBootIpeTable 1 }

UnisSysBootIpeEntry ::=
    SEQUENCE
        {
        unisSysBootIpeIndex
            Integer32,
        unisSysBootIpeRowStatus
            RowStatus
        }

unisSysBootIpeIndex OBJECT-TYPE
    SYNTAX Integer32 (1..2147483647)
    MAX-ACCESS not-accessible
    STATUS current
    DESCRIPTION
        "IPE file index.  The index must be included in unisSysIpeFileTable."
    ::= { unisSysBootIpeEntry 1 }

unisSysBootIpeRowStatus OBJECT-TYPE
    SYNTAX RowStatus
    MAX-ACCESS read-create
    STATUS current
    DESCRIPTION
        "Row status of the IPE file table entry."
    ::= { unisSysBootIpeEntry 2 }

unisSysSetBootImageResultTable OBJECT-TYPE
    SYNTAX SEQUENCE OF UnisSysSetBootImageResultEntry
    MAX-ACCESS not-accessible
    STATUS current
    DESCRIPTION
        "Table of startup image operation results.  This table shows the
        result for each card."
    ::= { unisSysSetBootImage 4 }

unisSysSetBootImageResultEntry OBJECT-TYPE
    SYNTAX UnisSysSetBootImageResultEntry
    MAX-ACCESS not-accessible
    STATUS current
    DESCRIPTION
        "Entry in the startup image operation result table."
    INDEX { unisSysSetBootImageResultIndex }
    ::= { unisSysSetBootImageResultTable 1 }

UnisSysSetBootImageResultEntry ::=
    SEQUENCE {
        unisSysSetBootImageResultIndex
            Integer32,
        unisSysSetBootImageResultStatusOfEachCard
            INTEGER,
        unisSysSetBootImageFailedReasonOfEachCard
            DisplayString
     }

unisSysSetBootImageResultIndex OBJECT-TYPE
    SYNTAX Integer32 (1..65535)
    MAX-ACCESS not-accessible
    STATUS current
    DESCRIPTION
        "Index of a startup image operation result.  It is identical to the
        entity index of each card."
    ::= { unisSysSetBootImageResultEntry 1 }

unisSysSetBootImageResultStatusOfEachCard OBJECT-TYPE
    SYNTAX INTEGER
        {
        none(1),
        doing(2),
        success(3),
        failed(4)
        }
    MAX-ACCESS read-only
    STATUS current
    DESCRIPTION
        "Status of the startup image set operation."
    ::= { unisSysSetBootImageResultEntry 2 }

unisSysSetBootImageFailedReasonOfEachCard OBJECT-TYPE
    SYNTAX DisplayString (SIZE (0..255))
    MAX-ACCESS read-only
    STATUS current
    DESCRIPTION
        "Reason of the startup image set failure for a card.  It is empty if
        the operation was successful."
    ::= { unisSysSetBootImageResultEntry 3 }
-- End define Boot/Load image table

unisSystemManMIBNotifications OBJECT IDENTIFIER ::= { unisSystemMan 2 }


unisSysClockChangedNotification NOTIFICATION-TYPE
    OBJECTS { unisSysLocalClock }
    STATUS current
    DESCRIPTION
        "
        A clock changed notification is generated when the current
        local date and time for the system has been manually changed.
        The value of unisSysLocalClock reflects new date and time.
        "
    ::= { unisSystemManMIBNotifications 1 }


unisSysReloadNotification NOTIFICATION-TYPE
    OBJECTS { unisSysReloadImage, unisSysReloadCfgFile, unisSysReloadReason, unisSysReloadScheduleTime, unisSysReloadAction
         }
    STATUS current
    DESCRIPTION
        "
        A unisSysReloadNotification will be sent before the corresponding entity is
                        rebooted. It will also be sent if the entity fails to reboot because the clock
                        has changed.
        "
    ::= { unisSystemManMIBNotifications 2 }


    unisSysStartUpNotification NOTIFICATION-TYPE
            OBJECTS { unisSysImageType }
            STATUS current
            DESCRIPTION
            "
            a unisSysStartUpNotification trap will be sent when the system starts up with 'main' image file failed,
            a trap will be sent to indicate which type the current image file (I.e backup or secure)is.
            "
            ::={ unisSystemManMIBNotifications 3}


-- conformance and Compliance define
unisSystemManMIBConformance OBJECT IDENTIFIER ::= { unisSystemMan 3 }


unisSystemManMIBCompliances OBJECT IDENTIFIER ::= { unisSystemManMIBConformance 1 }


unisSystemManMIBCompliance MODULE-COMPLIANCE
    STATUS current
    DESCRIPTION
        "
        The compliance statement for entities which implement
        the system management MIB.
        "
    MODULE -- this module
        MANDATORY-GROUPS { unisSysClockGroup, unisSysReloadGroup, unisSysImageGroup,
                           unisSysCFGFileGroup, unisSystemManNotificationGroup,
                           unisSysCurGroup
             }
        GROUP unisSystemBtmLoadGroup
        DESCRIPTION
        "
        The unisSystemBtmLoadGroup is optional for system.
        "
    ::= { unisSystemManMIBCompliances 1 }


unisSystemManMIBGroups OBJECT IDENTIFIER ::= { unisSystemManMIBConformance 2 }


unisSysClockGroup OBJECT-GROUP
    OBJECTS { unisSysLocalClock, unisSysSummerTimeEnable, unisSysSummerTimeZone, unisSysSummerTimeMethod,
        unisSysSummerTimeStart, unisSysSummerTimeEnd, unisSysSummerTimeOffset }
    STATUS current
    DESCRIPTION
        "A collection of objects providing mandatory system clock information."
    ::= { unisSystemManMIBGroups 1 }


-- A collection of objects providing mandatory system image
-- information.
unisSysReloadGroup OBJECT-GROUP
    OBJECTS { unisSysReloadSchedule, unisSysReloadAction, unisSysReloadImage, unisSysReloadCfgFile, unisSysReloadReason,
        unisSysReloadScheduleTagList,unisSysReloadTag,unisSysReloadScheduleTime, unisSysReloadEntity, unisSysReloadRowStatus }
    STATUS current
    DESCRIPTION
        "A collection of objects providing mandatory system reload."
    ::= { unisSystemManMIBGroups 2 }


unisSysImageGroup OBJECT-GROUP
    OBJECTS { unisSysImageNum, unisSysImageName, unisSysImageSize, unisSysImageLocation,
              unisSysImageType }
    STATUS current
    DESCRIPTION
        "A collection of objects providing mandatory system image information."
    ::= { unisSystemManMIBGroups 3 }


unisSysCFGFileGroup OBJECT-GROUP
    OBJECTS { unisSysCFGFileNum, unisSysCFGFileName, unisSysCFGFileSize, unisSysCFGFileLocation }
    STATUS current
    DESCRIPTION
        "
        A collection of objects providing mandatory system
        configuration file information.
        "
    ::= { unisSystemManMIBGroups 4 }


unisSysCurGroup OBJECT-GROUP
    OBJECTS { unisSysCurCFGFileIndex, unisSysCurImageIndex }
    STATUS current
    DESCRIPTION
        "A collection of system current status."
    ::= { unisSystemManMIBGroups 5 }


unisSystemManNotificationGroup NOTIFICATION-GROUP
    NOTIFICATIONS { unisSysClockChangedNotification, unisSysReloadNotification,
                    unisSysStartUpNotification }
    STATUS current
    DESCRIPTION
        "A collection of notifications."
    ::= { unisSystemManMIBGroups 6 }


unisSystemBtmLoadGroup OBJECT-GROUP
    OBJECTS { unisSysCurBtmFileName, unisSysCurUpdateBtmFileName,
                    unisSysBtmLoadMaxNumber, unisSysBtmFileName,
                    unisSysBtmFileType, unisSysBtmRowStatus,
                    unisSysBtmErrorStatus, unisSysBtmLoadTime }
    STATUS current
    DESCRIPTION
        "A collection of objects providing system update bootrom information."
    ::= { unisSystemManMIBGroups 7 }

END
