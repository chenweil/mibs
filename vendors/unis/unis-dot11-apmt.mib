-- =============================================================================
-- Copyright (c) 2020 Unisyue Technologies Co., Ltd.  All rights reserved.
--
-- Description:
--   The file defines a MIB to provide AP object information such as
--   performance statistic and notification events.
-- Reference:
-- Version: V3.4
-- History:
--   V1.0 2006-05-10 Initial version, created by shiyang (Richard)
--   V1.1 2007-02-01 modified by xingjichen(Daniel)
--        Changed DESCRIPTION of unisDot11APRxStatisTable,
--        unisDot11APTxStatisTable,unisDot11APMtRadioFailTrap,
--        unisDot11APMtRadioFailRecoverTrap.
--   V1.2 2007-04-27 modified by shiyang(Richard)
--        Add new nodes of unisDot11APChannelChgMode and unisDot11APChgWorkMode.
--        Split unisDot11APObjectTable table into unisDot11APObjectStatusTable
--        and unisDot11APObjectTable.
--        Rename unisDot11APRadioRelationTable as unisDot11APRadioTable.
--        Rename unisDot11APBSSRelationTable as unisDot11APBSSTable.
--   V1.3 2007-06-19 modified by Banasree
--        Add new table of unisDot11APIfTable for unisDot11APObjectGroup.
--        Add new table of unisDot11APAssocStatisTable for unisDot11APStatisGroup.
--        Add new node of unisDot11CurrAPName, unisDot11CurrAPModelName,
--        unisDot11CurrAPImageName, unisDot11CurrAPSoftwareVersion,
--        unisDot11CurrAPIPNetMask, unisDot11CurrRadioModeSupport for
--        unisDot11APObjectTable.
--        Add new node of unisDot11Channel, unisDot11TxPowerLevel,
--        unisDot11APRadioIfIndex, unisDot11AntennaGain for unisDot11APRadioTable.
--        Add new node of unisDot11APManufacturer, unisDot11APCPUType,
--        unisDot11APCPUClockSpeed, unisDot11APMemoryType, unisDot11APMemorySize,
--        unisDot11APFlashType, unisDot11APFlashSize for unisDot11APModelTable
--        Add unisDot11APReset node to the unisDot11APObjectStatusTable.
--        Add unisDot11RxFrameErrorRatio to the unisDot11APRxStatisTable.
--        Add_unisDot11TxFrameRetryRatio to the unisDot11APTxStatisTable.
--   V1.4 2007-12-21 modified by wanghao (Kumar)
--        Add unisDot11BSSRxStatisTable, unisDot11BSSTxStatisTable,
--        unisDot11BSSAssocStatisTable for BSS statistics.
--        Add unisDot11APCpuUsage to unisDot11APObjectStatusTable.
--        Add unisDot11MaxBandwidth to unisDot11APRadioTable.
--        Add unisDot11RxPhyErrorCnt, unisDot11RxMICErrorCnt,
--        unisDot11RxDataFrameBytes to unisDot11APRxStatisTable.
--        Add unisDot11TxDataFrameCnt, unisDot11TxDataFrameBytes to
--        unisDot11APTxStatisTable.
--        Add unisDot11ApStationExDeAuthenSum, unisDot11ApStationCurAssocSum to
--        unisDot11APAssocStatisTable.
--   V1.5 2008-02-25 modified by wanghao (Kumar)
--        Add unisDot11ResourceUseRatio to unisDot11APRadioTable.
--   V1.6 2008-07-09 modified by ChangHuifeng
--        Add unisDot11APConnectionType to unisDot11APObjectStatusTable.
--   V1.7 2008-11-07 modified by Wang Lu and Li Yugang
--        Add unisDot11APLinkStatisTable and unisDot11RadioAssocStatisTable.
--        Add unisDot11CurrIfNumber to unisDot11APObjectTable.
--        Add unisDot11RadioModeSupport, unisDot11TxPowerLevel2 and
--        unisDot11PowerMgmtStatus to unisDot11APRadioTable.
--        Add unisDot11SSID to unisDot11APBSSTable.
--        Add unisDot11APIfSpeed, unisDot11APIfInDataRate and
--        unisDot11APIfOutDataRate to unisDot11APIfTable
--        Add unisDot11RadioRxAverSnr to unisDot11APRxStatisTable.
--        Add unisDot11APMtTimeSynFail, unisDot11APMtChlIntfDetected,
--        unisDot11APMtIntfAPDetected, unisDot11APMtIntfStaDetected,
--        unisDot11APMtIPChange, unisDot11APFlashWriteFailure,
--        unisDot11APSysReboot, unisDot11APMtAvailChlTooLow and
--        unisDot11APImgDwldSuccess to unisDot11APMtTraps.
--        Add unisDot11APIntfDevMACAddress and unisDot11APMtTrapOldIPAddr to
--        unisDot11APMtTrapVarObjects.
--        Add unisDot11ChannelSwitchTimes to unisDot11APRadioTable.
--        Add unisDot11RxPayloadBytes, unisDot11RxTrafficSpeed to
--        unisDot11APRxStatisTable.
--        Add unisDot11TxMSDUCnt, unisDot11TxDiscardMSDUCnt,
--        unisDot11RetryMSDUCnt, unisDot11TxPayloadBytes,
--        unisDot11TxTrafficSpeed to unisDot11APTxStatisTable.
--        Add unisDot11ApStaCurAuthSuccSum, unisDot11AllStationUpSumTime,
--        unisDot11ApStationAssocReqSum to unisDot11APAssocStatisTable.
--        Add unisDot11BSSRxFrameErrorRatio, unisDot11BSSRxPayloadBytes to
--        unisDot11BSSRxStatisTable.
--        Add unisDot11BSSTxPayloadBytes to unisDot11BSSTxStatisTable.
--        Add unisDot11BSSStationAssocReqSum to unisDot11BSSAssocStatisTable.
--        Add new tables unisDot11RadioMngFrameStatisTable,
--        unisDot11APAuthFailStatisTable, unisDot11APAssocFailStatisTable,
--        unisDot11APReassocStatisTable, unisDot11APUserAuthStatisTable,
--        unisDot11APDeauthStatisTable, unisDot11APDeassocStatisTable to
--        unisDot11APStatisGroup.
--   V1.8 2009-04-17 modified by WangChunsheng
--        Add unisDot11AntennaType to unisDot11APRadioTable.
--   V1.9 2009-05-07 modified by Li Yugang, Wang Shaojie, Jin Yi
--        Add unisDot11CurrAPElementID to unisDot11APObjectTable.
--        Add unisDot11DiversitySelectionRx, unisDot11MaxTxPwrLvl,
--        unisDot11PwrAttRange, unisDot11AvgRxSignalStrength,
--        unisDot11HighestRxSignalStrength, unisDot11LowestRxSignalStrength
--        unisDot11RadioIfUpdownTimes, unisDot11RadioIfLastChange
--        to unisDot11APRadioTable.
--        Add unisDot11CurrSSIDResourceUseRatio to unisDot11APBSSTable.
--        Add new table unisDot11APSSIDObjectTable, unisDot11APSysInfoTable
--        to unisDot11APObjectGroup.
--        Add unisDot11TxErrFrameRatio, unisDot11TxFrameRate
--        to unisDot11APTxStatisTable.
--        Add unisDot11BSSRxUniFrameCnt, unisDot11BSSRxNonUniFrameCnt,
--        unisDot11BSSRxAuthenFrameCnt to unisDot11BSSRxStatisTable.
--        Add unisDot11BSSTxRetryCnt, unisDot11BSSTxUniFrameCnt,
--        unisDot11BSSTxNonUniFrameCnt, unisDot11BSSTxAuthenFrameCnt
--        to unisDot11BSSTxStatisTable.
--        Add new table unisDot11APAssocFailStatis2Table, unisDot11APIfStatisTable
--        to unisDot11APStatisGroup.
--        Add unisDot11APInterfDetectedTrap,
--        unisDot11APInterfClearTrap, unisDot11StaInterfDetectedTrap,
--        unisDot11StaInterfClearTrap, unisDot11OtherDevIntDetectedTrap,
--        unisDot11OtherDevIntClearTrap, unisDot11APModuleTroubleTrap,
--        unisDot11APModuleTroubleClearTrap, unisDot11APRadioDownTrap,
--        unisDot11APRadioDownRecovTrap, unisDot11APStaFullTrap,
--        unisDot11APStaFullRecoverTrap, unisDot11DFSFreeCntBelowThrRecov,
--        unisDot11APCpuUsageHigh, unisDot11APCpuUsageHighRecover,
--        unisDot11APMemUsageHigh, unisDot11APMemUsageHighRecover
--        to unisDot11APMtTraps.
--        Add unisDot11CurrInterfDetectedNum, unisDot11StaFullReason,
--        unisDot11StaLimitNumber, unisDot11APRadioDownReason,
--        unisDot11InterfMacList to unisDot11APMtTrapVarObjects.
--        Add unisDot11APLastImgDownloadTime to unisDot11APObjectStatusTable.
--   V2.0 2009-07-29 modified by Heziqi
--        Add new node unisDot11CurrAPMode for unisDot11APObjectTable.
--        Add new node unisDot11APEssVlanId and unisDot11APBSSResourceUseRatio
--        for unisDot11APBSSTable.
--        Add new node unisDot11APTrapUserCnt and unisDot11APTrapUserThreshold
--        for unisDot11APMtTrapVarObjects.
--        Add unisDot11APUserCntOverFlow for unisDot11APMtNotifyGroup.
--        Add new node unisDot11TxDiscardFrameRatio, unisDot11TxFrameRate,
--        unisDot11TxMgtFrameCnt and unisDot11TxCtrlFrameCnt
--        for unisDot11APTxStatisTable.
--        Add new node unisDot11APIPv6Address for unisDot11APObjectStatusTable.
--        Add new node unisDot11CurrAPIPv6Address for unisDot11APObjectTable.
--        Add unisDot11RadioMngFrmStatisTable.
--   V2.1 2009-08-07 modified by wang shaojie, Jin Yi
--        Add unisDot11APIfInBrdcastPkts, unisDot11APIfOutBrdcastPkts,
--        unisDot11APIfInMulcastPkts, unisDot11APIfOutMulcastPkts,
--        unisDot11APIfInPayloadOctets, unisDot11APIfOutPayloadOctets to
--        unisDot11APIfStatisTable.
--        Add new node unisDot11APLastRegisterTime to unisDot11APObjectStatusTable
--        Add new node unisDot11TxMACErrCnt, unisDot11TxErrFrameCnt to
--        unisDot11APTxStatisTable.
--        Add new variable bindings unisDot11APMtChanlChgCount to
--        unisDot11APMtRdoChanlChgTrap.
--   V2.2 2009-12-01 modified by Wang Shaojie, duyanbing
--        Add new table unisDot11APIdleListTable to unisDot11APObjectGroup.
--        Add new table unisDot11APPacketSizeStatisTable,
--        unisDot11APPacketRateStatisTable, unisDot11APPacketMCSRateStatisTable to
--        unisDot11APStatisGroup.
--        Add new node unisDot11RxUcastDataFrameCnt, unisDot11RxNUcastDataFrameCnt
--        to unisDot11APRxStatisTable.
--        Add new node unisDot11TxUcastDataFrameCnt, unisDot11TxNUcastDataFrameCnt
--        to unisDot11APTxStatisTable.
--        Add new node unisDot11CurrAPSSIDNumber to unisDot11APObjectTable.
--        Add new node unisDot11AllStationUpSumTimeTicks to
--        unisDot11APAssocStatisTable
--        Add new node unisDot11RxTotalDiscardFrameCnt to unisDot11APRxStatisTable.
--        Added unisDot11APMtTrapSwitch.
--        2010-02-23 modified by Wang Shaojie
--        Add unisDot11APMtDetectedIntfAP, unisDot11APMtDetectedIntfSTA,
--        unisDot11APMtDetectedIntfOtherDev to unisDot11APMtTraps.
--        Add unisDot11APMtFormerApVersion, unisDot11APMtAPID, unisDot11APMtRadioID
--        unisDot11APMtChannel, unisDot11APMtInterfMacAdd to
--        unisDot11APMtTrapVarObjects.
--        2010-03-15 modified by Deng Gaoliang
--        Add unisDot11APAssocFailStatis3Table
--        Add unisDot11APFlashSizeInBytes
--        Remove unisDot11APMtTrapSwitch
--        2010-05-31 modified by LiuChen, Wang Chunsheng, Wang Shaojie
--        Add new table unisDot11APSysInfoByAPIDTable.
--        Add new node unisDot11CurrAPManufacturer, unisDot11CurrAPMemorySize,
--        unisDot11CurrAPMemSizeInBytes, unisDot11CurrAPFlashSize,
--        unisDot11CurrAPFlashSizeInBytes to unisDot11APObjectTable.
--        Add new table unisDot11APUserSecAuthStatisTable to unisDot11APStatisGroup.
--        Add new table unisDot11APUserInfoStatisTable to unisDot11APStatisGroup.
--        2010-08-05 modified by LiuChen, Yinjunjie
--        Add new node unisDot11CurrAPReleasedVersion to unisDot11APObjectTable.
--        Add new node unisDot11BSSStationCurAuthSum to unisDot11BSSAssocStatisTable.
--        Add new node unisDot11APMtAdjChannel.
--        Add unisDot11DetcAdjChlIntfAP, unisDot11DetcAdjChlIntfAPClear
--        to unisDot11APMtTraps.
--        2010-08-05 modified by Yinjunjie
--        Add new table unisDot11APReassocStatis2Table
--        2010-09-16 Change names from unisDot11APIfLastChange and
--        unisDot11APIfLastChange2 to unisDot11APIfStatusKeepTime and
--        unisDot11APIfStatusKeepTime2 by shuaixiaojuan
--   V2.3 2010-10-11 modified by Wuxiaopeng
--        Add new node unisDot11APIfInDataOctets2, unisDot11APIfOutDataOctets2,
--        to unisDot11APIfStatisByAPIDTable.
--        Add new node unisDot11APMacAddress2 to unisDot11APSysInfoByAPIDTable.
--        Modify node unisDot11APChgWorkMode.
--   V2.4 2011-07-13 modified by Yu Bo
--        Add new node unisDot11RxTotalIPCheckErrPacketCnt to unisDot11APRxStatisTable
--        Add new node unisDot11APConfigPortalStaNum to unisDot11APSSIDObjectTable
--        2011-08-08 modified by Donglaqi
--        Add new node unisDot11AllUserOnlineTime to unisDot11APUserSecAuthStatisTable
--        2011-08-10 modified by limingjin
--        Add new node unisDot11RadioModeSupport2 to unisDot11APRadioTable
--        Add new node unisDot11CurrRadioModeSupport2 to unisDot11APObjectTable
--   V2.5 2011-09-27 modified by Limingjin
--        Add unisDot11TrafficTable
--        2011-09-28 modified by Li Honghao & jiaolibin
--        Add new table unisDot11APEchoStatisTable
--        Add unisDot11APEchoAvgDelay, unisDot11APEchoRequestCnt,
--        unisDot11APEchoRespLossCnt to unisDot11APEchoStatisTable
--        Add unisDot11APMtFirstTrapTime to unisDot11APMtTrapVarObjects and
--        varialbe bindings unisDot11APMtFirstTrapTime for
--        unisDot11APInterfClearTrap, unisDot11StaInterfDetectedTrap,
--        unisDot11StaInterfClearTrap, unisDot11OtherDevIntDetectedTrap,
--        unisDot11OtherDevIntClearTrap, unisDot11APRadioDownTrap ,
--        unisDot11APRadioDownRecovTrap, unisDot11APStaFullTrap,
--        unisDot11APStaFullRecoverTrap, unisDot11APMtDetectedIntfAP,
--        unisDot11DetcAdjChlIntfAP, unisDot11DetcAdjChlIntfAPClear,
--        unisDot11APMtDetectedIntfSTA
--   V2.6 2012-05-08 modified by Lihonghao
--        Add new table unisDot11APUserSecAuthTypeStatisTable
--        Add unisDot11APPortalOnlineUserNum, unisDot11APAuthFreeOnlineUserNum,
--        unisDot11APAssocAuthOnlineUserNum, unisDot11APMacAuthOnlineUserNum,
--        unisDot11APAllPortalUserOnlineTime, unisDot11APAllAuthFreeUserOnlineTime,
--        unisDot11APAllAssocAuthUserOnlineTime, unisDot11APAllMacAuthUserOnlineTime,
--        unisDot11APPortalUserLostCnntCnt, unisDot11APAuthFreeUserLostCnntCnt,
--        unisDot11APAssocAuthUserLostCnntCnt, unisDot11APMacAuthUserLostCnntCnt,
--        unisDot11APPortalAuthReqCnt, unisDot11APAssocAuthReqCnt,
--        unisDot11APMacAuthReqCnt, unisDot11APPortalAuthSucCnt,
--        unisDot11APAssocAuthSucCnt, unisDot11APMacAuthSucCnt,
--        unisDot11APPortalAuthReqFailCnt, unisDot11APAssocAuthReqFailCnt,
--        unisDot11APMacAuthReqFailCnt to unisDot11APUserSecAuthTypeStatisTable
--    2012-04-25 modified by Wang Shaojie
--        Add new table unisDot11RadioRxStatis64Table, unisDot11RadioTxStatis64Table,
--        unisDot11BSSRxStatis64Table, unisDot11BSSTxStatis64Table to
--        unisDot11APStatisGroup.
--    2012-08-12 modified by Zhang Congcong & Chen Zhao liang & Li Xin
--        Add new node   unisDot11APMtTrapAPMacAddress to unisDot11APMtTrapVarObjects
--        Add new object unisDot11APMtTrapAPMacAddress to unisDot11APMtWorkModeChgTrap
--        Add new object unisDot11APMtTrapAPMacAddress to unisDot11APFlashWriteFailure
--        Add new object unisDot11APMtTrapAPMacAddress to unisDot11APMtDetectedIntfAP
--        Add new object unisDot11APMtTrapAPMacAddress to unisDot11APInterfClearTrap
--        Add new object unisDot11APMtTrapAPMacAddress to unisDot11APMtDetectedIntfSTA
--        Add new object unisDot11APMtTrapAPMacAddress to unisDot11StaInterfClearTrap
--        Add new object unisDot11APMtTrapAPMacAddress to unisDot11APMtDetectedIntfOtherDev
--        Add new object unisDot11APMtTrapAPMacAddress to unisDot11OtherDevIntClearTrap
--        Add new object unisDot11APMtTrapAPMacAddress to unisDot11APModuleTroubleTrap
--        Add new object unisDot11APMtTrapAPMacAddress to unisDot11APModuleTroubleClearTrap
--        Add new object unisDot11APMtTrapAPMacAddress to unisDot11APRadioDownTrap
--        Add new object unisDot11APMtTrapAPMacAddress to unisDot11APRadioDownRecovTrap
--        Add new object unisDot11APMtTrapAPMacAddress to unisDot11APStaFullTrap
--        Add new object unisDot11APMtTrapAPMacAddress to unisDot11APStaFullRecoverTrap
--        Add new object unisDot11APMtTrapAPMacAddress to unisDot11APMtAvailChlTooLow
--        Add new object unisDot11APMtTrapAPMacAddress to unisDot11DFSFreeCntBelowThrRecov
--        Add new object unisDot11APMtTrapAPMacAddress to unisDot11APMtRdoChanlChgTrap
--   V2.7 2013-01-16 modified by Peng Nao
--        Add new object unisDot11APMtTrapAPMacAddress to unisDot11APCpuUsageHigh
--        Add new object unisDot11APMtTrapAPMacAddress to unisDot11APCpuUsageHighRecover
--        Add new object unisDot11APMtTrapAPMacAddress to unisDot11APMemUsageHigh
--        Add new object unisDot11APMtTrapAPMacAddress to unisDot11APMemUsageHighRecover
--   V2.8 2013-07-01 modified by LiuYanjie
--        Add new table unisDot11APPacketMCSRateStatis2Table to unisDot11APStatisGroup.
--        2013-07-08 modified by Chen Guoxi
--        Add new node  unisDot11ApStationReassocReqSum      to unisDot11APAssocStatisEntry
--        Add new node  unisDot11ApStationReassocFailSum     to unisDot11APAssocStatisEntry
--   V2.9 2013-09-02 Added unisDot11OperStatusCM to unisDot11APRadioTable by Zhang Siyu
--        2013-09-13 Added unisDot11APIfAdminStatus,unisDot11APIfOperStatusCM and
--        unisDot11APACAssociateStatusCM by duyanbing
--   V3.0 2014-02-10 modified by weixiangxiang
--        Add new object unisDot11APResetCM to unisDot11APObjectStatusTable
--        Add new object unisDot11CurrAPCPUTypeCM to unisDot11APObjectTable
--        Add new object unisDot11CurrAPMemoryTypeCM to unisDot11APObjectTable
--        Add new object unisDot11CurrAPBSSIDNumberCM to unisDot11APObjectTable
--        Add new object unisDot11APIfTypeCM to unisDot11APIfTable
--        Add new object unisDot11RxSignalStrengthPacketCntCM to unisDot11APRxStatisTable
--        Add new object unisDot11APAssocFailStatis3RSSILowCntCM to unisDot11APAssocFailStatis3Table
--        Add new object unisDot11APUserLoginNameCM to unisDot11APUserInfoStatisTable
--        Add new object unisDot11APUserAuthTypeCM to unisDot11APUserInfoStatisTable
--        Add new object unisDot11APUserTxPacketCntCM to unisDot11APUserInfoStatisTable
--        Add new object unisDot11APUserTxBytesCM to unisDot11APUserInfoStatisTable
--        Add new object unisDot11APUserRxPacketCntCM to unisDot11APUserInfoStatisTable
--        Add new object unisDot11APUserRxBytesCM to unisDot11APUserInfoStatisTable
--        Add new table unisDot11APUserSecAuthStatisCMTable to unisDot11APStatisGroup
--        Add new object unisDot11APAutoAuthOnlineUserNumCM to unisDot11APUserSecAuthTypeStatisTable
--        Add new object unisDot11APAllAutoAuthOnlineTimeCM to unisDot11APUserSecAuthTypeStatisTable
--        Add new object unisDot11APAutoAuthUserLostCnntCntCM to unisDot11APUserSecAuthTypeStatisTable
--        Add new object unisDot11APAutoAuthReqCntCM to unisDot11APUserSecAuthTypeStatisTable
--        Add new object unisDot11APAutoAuthSucCntCM to unisDot11APUserSecAuthTypeStatisTable
--        Add new object unisDot11APAutoAuthReqFailCntCM to unisDot11APUserSecAuthTypeStatisTable
--        Modify object unisDot11APPortalOnlineUserNum from unisDot11APUserSecAuthTypeStatisTable
--        Modify object unisDot11APAssocAuthOnlineUserNum from unisDot11APUserSecAuthTypeStatisTable
--        Add unisDot11RxDataFrameCntCM to unisDot11APRxStatisTable
--        Add unisDot11Rx64DataFrameBytesCM to unisDot11RadioRxStatis64Table
--   V3.1 2014-05-15 modified by yubo
--        Add new object unisDot11PrivateSrvRxFrameBytes  to unisDot11APLinkStatisTable
--        Add new object unisDot11PrivateSrvTxFrameBytes  to unisDot11APLinkStatisTable
--        Add new object unisDot11APInternetAllRxBytes    to unisDot11APLinkStatisTable
--        Add new object unisDot11APInternetAllTxBytes    to unisDot11APLinkStatisTable
--        Add new object unisDot11APLocalAllRxBytes       to unisDot11APLinkStatisTable
--        Add new object unisDot11APLocalAllTxBytes       to unisDot11APLinkStatisTable
--        Add new object unisDot11APPowerOffTrap          to unisDot11APMtTraps
--        Add new object unisDot11APPowerOnTrap           to unisDot11APMtTraps
--        Add new object unisDot11UpLinkSwitchTrap        to unisDot11APMtTraps
--        Add new object unisDot11APMtUpLinkSwitchInfo    to unisDot11APMtTrapVarObjects
--        Add new object unisDot11APMtUpLinkSwitchTime    to unisDot11APMtTrapVarObjects
--        Add new object unisDot11APMtOldCellId           to unisDot11APMtTrapVarObjects
--        Add new object unisDot11APMtCurCellId           to unisDot11APMtTrapVarObjects
--        Add new object unisDot11APMtOldBand             to unisDot11APMtTrapVarObjects
--        Add new object unisDot11APMtActiveBand          to unisDot11APMtTrapVarObjects
--        Add new table unisDot11APUserInfoStatis2CMTable to unisDot11APStatisGroup
--        Add new object unisDot11RxTotalFrameCnt         to unisDot11APRxStatisTable
--        Add new object unisDot11TxTotalFrameCnt         to unisDot11APTxStatisTable
--   V3.2 2014-11-19 modified by yubo
--        Add new object unisDot11AirPrimChnlBusy       to unisDot11APRadioTable
--        Add new object unisDot11AirPrimChnlTxBusy     to unisDot11APRadioTable
--        Add new object unisDot11AirPrimChnlRxBusy     to unisDot11APRadioTable
--        Add new object unisDot11AirExtChnlBusy        to unisDot11APRadioTable
--        Add new object unisDot11CurrAPIPv6PrefixLen   to unisDot11APObjectTable
--        Add new object unisDot11APIPv6PrefixLen       to unisDot11APObjectStatusTable
--        Add new object unisDot11APUserIPv6Addr2CM     to unisDot11APUserInfoStatis2CMTable
--        2014-12-12 modified by yubo
--        Add new object unisDot11APAssocStaNum   to unisDot11APSSIDObjectTable
--   V3.3 2015-6-20 modified by wangshaojie
--        Add new object unisDot11WTUAPInfoTable        to unisDot11APObjectGroup
--   V3.4 2016-3-11 modified by yubo 04460
--        Changed DESCRIPTION of unisDot11RadioModeSupport, unisDot11RadioModeSupport2,
--        unisDot11TxDiscardFrameBytes, unisDot11Tx64DiscardFrameBytes
--        Add unisDot11APUserInCirValueCM to unisDot11APUserInfoStatis2CMTable
--        Add unisDot11APUserOutCirValueCM to unisDot11APUserInfoStatis2CMTable
--        Add unisDot11APUserMac2CM to unisDot11APUserInfoStatis2CMTable
--        Add unisDot11BSSRxFrameErrCntCM to unisDot11BSSRxStatisTable
--        Add unisDot11BSSTxFrameErrCntCM to unisDot11BSSTxStatisTable
--        Add unisDot11APFactoryDataResetCM to unisDot11APObjectStatusTable
--        2016-6-15 modified by zhouwenshuai kf6157
--        Add new node  unisDot11WsmAPLicenseType      to unisDot11APModelTable
-- =============================================================================
UNIS-DOT11-APMT-MIB DEFINITIONS ::= BEGIN

IMPORTS
        MODULE-IDENTITY,
        OBJECT-TYPE,
        NOTIFICATION-TYPE,
        Integer32,
        Counter32,
        IpAddress,
        Unsigned32,
        TimeTicks,
        Counter64,
        Gauge32
    FROM SNMPv2-SMI
        MacAddress,
        TruthValue,
        DateAndTime,
        TimeStamp
    FROM SNMPv2-TC
        unisDot11,
        UnisDot11ObjectIDType,
        UnisDot11MACModeType,
        UnisDot11RadioScopeType,
        UnisDot11NotifyReasonType,
        UnisDot11ChannelScopeType,
        UnisDot11ServicePolicyIDType,
        UnisDot11RFModeType,
        UnisDot11TxPwrLevelScopeType,
        UnisDot11RadioElementIndex,
        unisDot11APElementIndex,
        UnisDot11SSIDStringType
    FROM UNIS-DOT11-REF-MIB;

unisDot11APMT MODULE-IDENTITY
    LAST-UPDATED "201603111800Z"        -- Mar 11, 2016 at 18:00 GMT
    ORGANIZATION
        "Unisyue Technologies Co., Ltd."
    CONTACT-INFO
        ""
    DESCRIPTION
        "This MIB provides AP information which includes AP current object
        information, AP statistic data.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable STA invocation
        of the distribution system services.
        (Wireless clients attempt to connect to
        access points.)

        Basic Rate
        A data rate that is mandatory for client
        devices to support in order for them to achieve
        successful association."
    REVISION "201603111800Z"        -- Mar 11, 2016 at 18:00 GMT
    DESCRIPTION
        "Modified to add new tables and new nodes."
    REVISION "201506201800Z"        -- June 20, 2015 at 18:00 GMT
    DESCRIPTION
        "Modified to add new tables and new nodes."

    REVISION "201205071800Z"        -- May 07, 2012 at 18:00 GMT
    DESCRIPTION
        "Modified to add new tables."

    REVISION "201010111800Z"        -- Oct 11, 2010 at 18:00 GMT
    DESCRIPTION
        "Modified to add new nodes."
    REVISION "201009151200Z"        -- Sep 15, 2010 at 12:00 GMT
    DESCRIPTION
        "Modified to add new table."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new tables and new nodes."
    REVISION "200811071000Z"        -- Nov 07, 2008 at 10:00 GMT
    DESCRIPTION
        "Modified to add new tables and new nodes."
    REVISION "200807091800Z"        -- July 09, 2008 at 18:00 GMT
    DESCRIPTION
        "Modified to add new nodes."
    REVISION "200802251800Z"        -- Feb 25, 2008 at 18:00 GMT
    DESCRIPTION
        "Modified to add new nodes."
    REVISION "200712211800Z"        -- Dec 21, 2007 at 18:00 GMT
    DESCRIPTION
        "Modified to add new tables and new nodes."
    REVISION "200706191800Z"        -- June 19, 2007 at 18:00 GMT
    DESCRIPTION
        "Modified for new requirements and fix some issue."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { unisDot11 2 }

-- *****************************************************************************
-- *  Major sections
-- *****************************************************************************
--  AP Object Group
--  DEFINED AS "The group to provide the basic information for APs.
--  In order to support fit and fat AP, it uses tables to keep
--  information.  For fat AP, if it is needful, it could add more
--  tables to keep information."
unisDot11APObjectGroup OBJECT IDENTIFIER   ::= { unisDot11APMT 1 }

--  AP Object Group has the following children:
--  unisDot11APObjectStatusTable           ::= { unisDot11APObjectGroup 1 }
--  unisDot11APObjectTable                 ::= { unisDot11APObjectGroup 2 }
--  unisDot11APRadioTable                  ::= { unisDot11APObjectGroup 3 }
--  unisDot11APBSSTable                    ::= { unisDot11APObjectGroup 4 }
--  unisDot11APModelTable                  ::= { unisDot11APObjectGroup 5 }
--  unisDot11APIfTable                     ::= { unisDot11APObjectGroup 6 }
--  unisDot11APSSIDObjectTable             ::= { unisDot11APObjectGroup 7 }
--  unisDot11APSysInfoTable                ::= { unisDot11APObjectGroup 8 }
--  unisDot11APIdleListTable               ::= { unisDot11APObjectGroup 9 }
--  unisDot11APSysInfoByAPIDTable          ::= { unisDot11APObjectGroup 10 }
--  unisDot11WTUAPInfoTable                ::= { unisDot11APObjectGroup 11 }

--  AP Statistic Group
--  DEFINED AS "The group to provide the statistic information of Rx
--  and Tx for AP."
unisDot11APStatisGroup OBJECT IDENTIFIER   ::= { unisDot11APMT 2 }

--  AP Statistic Group has the following children:
--  unisDot11APRxStatisTable               ::= { unisDot11APStatisGroup 1 }
--  unisDot11APTxStatisTable               ::= { unisDot11APStatisGroup 2 }
--  unisDot11APAssocStatisTable            ::= { unisDot11APStatisGroup 3 }
--  unisDot11BSSRxStatisTable              ::= { unisDot11APStatisGroup 4 }
--  unisDot11BSSTxStatisTable              ::= { unisDot11APStatisGroup 5 }
--  unisDot11BSSAssocStatisTable           ::= { unisDot11APStatisGroup 6 }
--  unisDot11APLinkStatisTable             ::= { unisDot11APStatisGroup 7 }
--  unisDot11RadioAssocStatisTable         ::= { unisDot11APStatisGroup 8 }
--  unisDot11RadioMngFrameStatisTable      ::= { unisDot11APStatisGroup 9 }
--  unisDot11APAuthFailStatisTable         ::= { unisDot11APStatisGroup 10 }
--  unisDot11APAssocFailStatisTable        ::= { unisDot11APStatisGroup 11 }
--  unisDot11APReassocStatisTable          ::= { unisDot11APStatisGroup 12 }
--  unisDot11APUserAuthStatisTable         ::= { unisDot11APStatisGroup 13 }
--  unisDot11APDeauthStatisTable           ::= { unisDot11APStatisGroup 14 }
--  unisDot11APDeassocStatisTable          ::= { unisDot11APStatisGroup 15 }
--  unisDot11APAssocFailStatis2Table       ::= { unisDot11APStatisGroup 16 }
--  unisDot11APIfStatisTable               ::= { unisDot11APStatisGroup 17 }
--  unisDot11RadioMngFrmStatisTable        ::= { unisDot11APStatisGroup 18 }
--  unisDot11APPacketSizeStatisTable       ::= { unisDot11APStatisGroup 19 }
--  unisDot11APPacketRateStatisTable       ::= { unisDot11APStatisGroup 20 }
--  unisDot11APPacketMCSRateStatisTable    ::= { unisDot11APStatisGroup 21 }
--  unisDot11APAssocFailStatis3Table       ::= { unisDot11APStatisGroup 22 }
--  unisDot11APIfStatisByAPIDTable         ::= { unisDot11APStatisGroup 23 }
--  unisDot11APUserSecAuthStatisTable      ::= { unisDot11APStatisGroup 24 }
--  unisDot11APUserInfoStatisTable         ::= { unisDot11APStatisGroup 25 }
--  unisDot11APReassocStatis2Table         ::= { unisDot11APStatisGroup 26 }
--  unisDot11TrafficTable                  ::= { unisDot11APStatisGroup 27 }
--  unisDot11APEchoStatisTable             ::= { unisDot11APStatisGroup 28 }
--  unisDot11APUserSecAuthTypeStatisTable  ::= { unisDot11APStatisGroup 29 }
--  unisDot11RadioRxStatis64Table          ::= { unisDot11APStatisGroup 30 }
--  unisDot11RadioTxStatis64Table          ::= { unisDot11APStatisGroup 31 }
--  unisDot11BSSRxStatis64Table            ::= { unisDot11APStatisGroup 32 }
--  unisDot11BSSTxStatis64Table            ::= { unisDot11APStatisGroup 33 }
--  unisDot11APPacketMCSRateStatis2Table   ::= { unisDot11APStatisGroup 34 }
--  unisDot11APUserSecAuthStatisCMTable    ::= { unisDot11APStatisGroup 35 }
--  unisDot11APUserInfoStatis2CMTable      ::= { unisDot11APStatisGroup 36 }

--  AP Event Notification
--  DEFINED AS " The group to provide AP management notification."
unisDot11APMtNotifyGroup OBJECT IDENTIFIER ::= { unisDot11APMT 3 }

-- *****************************************************************************
-- *  unisDot11APObjectStatusTable Definition
-- *****************************************************************************
unisDot11APObjectStatusTable OBJECT-TYPE
    SYNTAX      SEQUENCE OF UnisDot11APObjectStatusEntry
    MAX-ACCESS  not-accessible
    STATUS      current
    DESCRIPTION
        "The table will provide the general information about APs in
        different status."
    ::= { unisDot11APObjectGroup 1 }

unisDot11APObjectStatusEntry OBJECT-TYPE
    SYNTAX      UnisDot11APObjectStatusEntry
    MAX-ACCESS  not-accessible
    STATUS      current
    DESCRIPTION
        "Each entry contains the general information of an AP."
    INDEX
        {
            unisDot11APID
        }
    ::= { unisDot11APObjectStatusTable 1 }

UnisDot11APObjectStatusEntry ::= SEQUENCE
    {
        unisDot11APID                  UnisDot11ObjectIDType,
        unisDot11APIPAddress           IpAddress,
        unisDot11APMacAddress          MacAddress,
        unisDot11APOperationStatus     INTEGER,
        unisDot11APTemplateNameOfAP    OCTET STRING,
        unisDot11APReset               TruthValue,
        unisDot11APCpuUsage            Integer32,
        unisDot11APConnectionType      INTEGER,
        unisDot11APLastImgDownloadTime DateAndTime,
        unisDot11APIPv6Address         OCTET STRING,
        unisDot11APLastRegisterTime    DateAndTime,
        unisDot11APResetCM             INTEGER,
        unisDot11APIPv6PrefixLen       Integer32,
        unisDot11APFactoryDataResetCM  INTEGER
    }

unisDot11APID OBJECT-TYPE
    SYNTAX      UnisDot11ObjectIDType
    MAX-ACCESS  accessible-for-notify
    STATUS      current
    DESCRIPTION
        "To uniquely identify each AP, and relation-ship between unisDot11APID
        and AP device will be static."
    ::= { unisDot11APObjectStatusEntry 1 }

unisDot11APIPAddress OBJECT-TYPE
    SYNTAX      IpAddress
    MAX-ACCESS  read-only
    STATUS      current
    DESCRIPTION
        "Represents the IP address of an AP."
    ::= { unisDot11APObjectStatusEntry 2 }

unisDot11APMacAddress OBJECT-TYPE
    SYNTAX      MacAddress
    MAX-ACCESS  read-only
    STATUS      current
    DESCRIPTION
        "Represents the MAC address of an AP."
    ::= { unisDot11APObjectStatusEntry 3 }

unisDot11APOperationStatus OBJECT-TYPE
    SYNTAX      INTEGER
        {
            join(1),
            joinConfirm(2),
            download(3),
            config(4),
            run(5)
        }
    MAX-ACCESS  read-only
    STATUS      current
    DESCRIPTION
        "Represents operational status of AP.
        The following values are supported:
        join         - AP is joining to AC.
        joinConfirm  - AC confirm whether permit AP to join.
        download     - AP is downloading software from AC.
        config       - AP and AC exchange configuration before AP
        - provide WLAN service.
        run          - The WLAN service is ready."
    ::= { unisDot11APObjectStatusEntry 4 }

unisDot11APTemplateNameOfAP OBJECT-TYPE
    SYNTAX      OCTET STRING
    MAX-ACCESS  read-only
    STATUS      current
    DESCRIPTION
        "Represents the name of current AP template configured for AP."
    ::= { unisDot11APObjectStatusEntry 5 }

unisDot11APReset OBJECT-TYPE
    SYNTAX      TruthValue
    MAX-ACCESS  read-write
    STATUS      current
    DESCRIPTION
        "When read the value from the node
        2: Represents the AP cannot be reset.
        1: Represents the AP can be reset.
        When write the value to the node
        1: Represents resetting the AP.  Other values are not supported"
    ::= { unisDot11APObjectStatusEntry 6 }

unisDot11APCpuUsage OBJECT-TYPE
    SYNTAX      Integer32(0..100)
    UNITS       "onepercent"
    MAX-ACCESS  read-only
    STATUS      current
    DESCRIPTION
        "Represents the current CPU usage for AP."
    ::= { unisDot11APObjectStatusEntry 7 }

unisDot11APConnectionType OBJECT-TYPE
    SYNTAX      INTEGER
        {
            master(1),
            slave(2),
            notAvailable(3)
        }
    MAX-ACCESS  read-only
    STATUS      current
    DESCRIPTION
        "Represents the current connection type."
    ::= { unisDot11APObjectStatusEntry 8 }

unisDot11APLastImgDownloadTime OBJECT-TYPE
    SYNTAX      DateAndTime
    MAX-ACCESS  read-only
    STATUS      current
    DESCRIPTION
        "Represents the time at which the device last downloaded image."
    ::= { unisDot11APObjectStatusEntry 9 }

unisDot11APIPv6Address OBJECT-TYPE
    SYNTAX      OCTET STRING
    MAX-ACCESS  read-only
    STATUS      current
    DESCRIPTION
        "Represents the IPv6 address of AP."
    ::= { unisDot11APObjectStatusEntry 10 }

unisDot11APLastRegisterTime OBJECT-TYPE
    SYNTAX      DateAndTime
    MAX-ACCESS  read-only
    STATUS      current
    DESCRIPTION
        "Represents the time at which the device last registered with AC."
    ::= { unisDot11APObjectStatusEntry 11 }

unisDot11APResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { unisDot11APObjectStatusEntry 12 }

unisDot11APIPv6PrefixLen OBJECT-TYPE
    SYNTAX      Integer32
    MAX-ACCESS  read-only
    STATUS      current
    DESCRIPTION
        "Represents the prefix length of an AP IPv6 address."
    ::= { unisDot11APObjectStatusEntry 13 }

unisDot11APFactoryDataResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { unisDot11APObjectStatusEntry 14 }

-- *****************************************************************************
-- *  End of UnisDot11APObjectStatusTable Definition
-- *****************************************************************************

-- *****************************************************************************
-- *  unisDot11APObjectTable Definition
-- *****************************************************************************
unisDot11APObjectTable OBJECT-TYPE
    SYNTAX      SEQUENCE OF UnisDot11APObjectEntry
    MAX-ACCESS  not-accessible
    STATUS      current
    DESCRIPTION
        "The table will provide information for APs in the running status."
    ::= { unisDot11APObjectGroup 2 }

unisDot11APObjectEntry OBJECT-TYPE
    SYNTAX      UnisDot11APObjectEntry
    MAX-ACCESS  not-accessible
    STATUS      current
    DESCRIPTION
        "Each entry contains information of an AP in run status."
    INDEX
        {
            unisDot11APObjID
        }
    ::= { unisDot11APObjectTable 1 }

UnisDot11APObjectEntry ::= SEQUENCE
    {
        unisDot11APObjID                    UnisDot11ObjectIDType,
        unisDot11CurrAPIPAddress            IpAddress,
        unisDot11CurrAPMacAddress           MacAddress,
        unisDot11CurrACPortIndex            Integer32,
        unisDot11CurrAPMACMode              UnisDot11MACModeType,
        unisDot11CurrAPTemplateName         OCTET STRING,
        unisDot11CurrAPStationAssocCount    Integer32,
        unisDot11CurrAPName                 OCTET STRING,
        unisDot11CurrAPModelName            OCTET STRING,
        unisDot11CurrAPImageName            OCTET STRING,
        unisDot11CurrAPSoftwareVersion      OCTET STRING,
        unisDot11CurrAPIPNetMask            IpAddress,
        unisDot11CurrRadioModeSupport       Integer32,
        unisDot11CurrIfNumber               Integer32,
        unisDot11CurrAPElementID            Integer32,
        unisDot11CurrAPMode                 INTEGER,
        unisDot11CurrAPIPv6Address          OCTET STRING,
        unisDot11CurrAPSSIDNumber           Integer32,
        unisDot11CurrAPManufacturer         OCTET STRING,
        unisDot11CurrAPMemorySize           Integer32,
        unisDot11CurrAPMemSizeInBytes       Integer32,
        unisDot11CurrAPFlashSize            Integer32,
        unisDot11CurrAPFlashSizeInBytes     Integer32,
        unisDot11CurrAPReleasedVersion      OCTET STRING,
        unisDot11CurrRadioModeSupport2      Integer32,
        unisDot11CurrAPCPUTypeCM            OCTET STRING,
        unisDot11CurrAPMemoryTypeCM         OCTET STRING,
        unisDot11CurrAPBSSIDNumberCM        Integer32,
        unisDot11CurrAPIPv6PrefixLen        Integer32
    }

unisDot11APObjID OBJECT-TYPE
    SYNTAX      UnisDot11ObjectIDType
    MAX-ACCESS  not-accessible
    STATUS      current
    DESCRIPTION
        "To uniquely identify each AP, and relation-ship between unisDot11APObjID
        and AP device will be static."
    ::= { unisDot11APObjectEntry 1 }

unisDot11CurrAPIPAddress OBJECT-TYPE
    SYNTAX      IpAddress
    MAX-ACCESS  read-only
    STATUS      current
    DESCRIPTION
        "Represents the IP address of an AP."
    ::= { unisDot11APObjectEntry 2 }

unisDot11CurrAPMacAddress OBJECT-TYPE
    SYNTAX      MacAddress
    MAX-ACCESS  read-only
    STATUS      current
    DESCRIPTION
        "Represents the MAC address of an AP."
    ::= { unisDot11APObjectEntry 3 }

unisDot11CurrACPortIndex OBJECT-TYPE
    SYNTAX      Integer32
    MAX-ACCESS  read-only
    STATUS      current
    DESCRIPTION
        "Represents the port on the AC, by which the traffic of this AP comes
        through.  NMS could refer it to access information kept in the
        MIB-2."
    ::= { unisDot11APObjectEntry 4 }

unisDot11CurrAPMACMode OBJECT-TYPE
    SYNTAX      UnisDot11MACModeType
    MAX-ACCESS  read-only
    STATUS      current
    DESCRIPTION
        "Represents what MAC mode defined in the CAPWAP is applied.
        For fat AP, the value will be fatap."
    ::= { unisDot11APObjectEntry 5 }

unisDot11CurrAPTemplateName OBJECT-TYPE
    SYNTAX      OCTET STRING
    MAX-ACCESS  read-only
    STATUS      current
    DESCRIPTION
        "Represents the name of current AP template."
    ::= { unisDot11APObjectEntry 6 }

unisDot11CurrAPStationAssocCount OBJECT-TYPE
    SYNTAX      Integer32
    MAX-ACCESS  read-only
    STATUS      current
    DESCRIPTION
        "Represents the total number of stations which are associating
        to AP."
    ::= { unisDot11APObjectEntry 7 }

unisDot11CurrAPName OBJECT-TYPE
    SYNTAX      OCTET STRING
    MAX-ACCESS  read-only
    STATUS      current
    DESCRIPTION
        "Represents the name of AP."
    ::= { unisDot11APObjectEntry 8 }

unisDot11CurrAPModelName OBJECT-TYPE
    SYNTAX      OCTET STRING
    MAX-ACCESS  read-only
    STATUS      current
    DESCRIPTION
        "Represents index of WTP model,with it to get AP model information."
    ::= { unisDot11APObjectEntry 9 }

unisDot11CurrAPImageName OBJECT-TYPE
    SYNTAX      OCTET STRING
    MAX-ACCESS  read-only
    STATUS      current
    DESCRIPTION
        "Represents the image file name of AP."
    ::= { unisDot11APObjectEntry 10 }

unisDot11CurrAPSoftwareVersion OBJECT-TYPE
    SYNTAX      OCTET STRING
    MAX-ACCESS  read-only
    STATUS      current
    DESCRIPTION
        "Represents the software version of AP."
    ::= { unisDot11APObjectEntry 11 }

unisDot11CurrAPIPNetMask OBJECT-TYPE
    SYNTAX      IpAddress
    MAX-ACCESS  read-only
    STATUS      current
    DESCRIPTION
        "Represents the IP netmask of AP."
    ::= { unisDot11APObjectEntry 12 }

unisDot11CurrRadioModeSupport OBJECT-TYPE
    SYNTAX      Integer32
    MAX-ACCESS  read-only
    STATUS      current
    DESCRIPTION
        "Represents which radio type supported by the AP.
        The WLAN system support the following possible radio type.
        dot11a(1),
        dot11b(2),
        dot11g(4),
        dot11n(8),
        dot11an(16),
        dot11gn(32),
        dot11ac(64),
        dot11gac(128)
        For a AP,it could support multiple radio types at
        the same time.So the value of object could combine multiple value
        of radio type above.
        For example:
        For one AP which support both b and g mode radio, when getting the value
        from the node, the value is 6(2 + 4)."
    ::= { unisDot11APObjectEntry 13 }

unisDot11CurrIfNumber OBJECT-TYPE
    SYNTAX      Integer32
    MAX-ACCESS  read-only
    STATUS      current
    DESCRIPTION
        "Represents number of interface of the AP."
    ::= { unisDot11APObjectEntry 14 }

unisDot11CurrAPElementID OBJECT-TYPE
    SYNTAX      Integer32
    MAX-ACCESS  read-only
    STATUS      current
    DESCRIPTION
    "Represents the AP element ID."
    ::= { unisDot11APObjectEntry 15 }

unisDot11CurrAPMode OBJECT-TYPE
    SYNTAX      INTEGER
        {
            bridge(1),
            route(2)
        }
    MAX-ACCESS  read-only
    STATUS      current
    DESCRIPTION
        "Represents the forward mode of the AP."
    ::= { unisDot11APObjectEntry 16 }

unisDot11CurrAPIPv6Address OBJECT-TYPE
    SYNTAX      OCTET STRING
    MAX-ACCESS  read-only
    STATUS      current
    DESCRIPTION
        "Represents the IPv6 address of AP."
    ::= { unisDot11APObjectEntry 17 }

unisDot11CurrAPSSIDNumber OBJECT-TYPE
    SYNTAX      Integer32
    MAX-ACCESS  read-only
    STATUS      current
    DESCRIPTION
        "Represents the number of SSID configured on AP."
    ::= { unisDot11APObjectEntry 18 }

unisDot11CurrAPManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { unisDot11APObjectEntry 19 }

unisDot11CurrAPMemorySize OBJECT-TYPE
    SYNTAX      Integer32
    UNITS       "kbytes"
    MAX-ACCESS  read-only
    STATUS      current
    DESCRIPTION
        "Represents the size of AP memory."
    ::= { unisDot11APObjectEntry 20 }

unisDot11CurrAPMemSizeInBytes OBJECT-TYPE
    SYNTAX      Integer32
    UNITS       "bytes"
    MAX-ACCESS  read-only
    STATUS      current
    DESCRIPTION
        "Represents the size of AP memory."
    ::= { unisDot11APObjectEntry 21 }

unisDot11CurrAPFlashSize OBJECT-TYPE
    SYNTAX      Integer32
    UNITS       "Kbytes"
    MAX-ACCESS  read-only
    STATUS      current
    DESCRIPTION
        "Represents the size of AP flash."
    ::= { unisDot11APObjectEntry 22 }

unisDot11CurrAPFlashSizeInBytes OBJECT-TYPE
    SYNTAX      Integer32
    UNITS       "bytes"
    MAX-ACCESS  read-only
    STATUS      current
    DESCRIPTION
        "This object represents the size of AP flash."
    ::= { unisDot11APObjectEntry 23 }

unisDot11CurrAPReleasedVersion OBJECT-TYPE
    SYNTAX      OCTET STRING
    MAX-ACCESS  read-only
    STATUS      current
    DESCRIPTION
        "Represents the released version of AP."
    ::= { unisDot11APObjectEntry 24 }

unisDot11CurrRadioModeSupport2 OBJECT-TYPE
    SYNTAX      Integer32
    MAX-ACCESS  read-only
    STATUS      current
    DESCRIPTION
        "Represents which radio type supported by the AP.
        The WLAN system support the following possible radio type.
        dot11a(1),
        dot11b(2),
        dot11g(4),
        dot11an(8),
        dot11gn(16),
        dot11gac(32),
        dot11ac(64)
        For a AP,it could support multiple radio types at
        the same time.So the value of object could combine multiple value
        of radio type above.
        For example:
        For one AP which support both b and g mode radio, when getting the value
        from the node, the value is 6(2 + 4)."
    ::= { unisDot11APObjectEntry 25 }

unisDot11CurrAPCPUTypeCM OBJECT-TYPE
    SYNTAX      OCTET STRING
    MAX-ACCESS  read-only
    STATUS      current
    DESCRIPTION
        "Represents the CPU type of AP."
    ::= { unisDot11APObjectEntry 26 }

unisDot11CurrAPMemoryTypeCM OBJECT-TYPE
    SYNTAX      OCTET STRING
    MAX-ACCESS  read-only
    STATUS      current
    DESCRIPTION
        "Represents the memory card type of AP."
    ::= { unisDot11APObjectEntry 27 }

unisDot11CurrAPBSSIDNumberCM OBJECT-TYPE
    SYNTAX      Integer32
    MAX-ACCESS  read-only
    STATUS      current
    DESCRIPTION
        "Represents the number of BSSID configured on AP."
    ::= { unisDot11APObjectEntry 28 }

unisDot11CurrAPIPv6PrefixLen OBJECT-TYPE
    SYNTAX      Integer32
    MAX-ACCESS  read-only
    STATUS      current
    DESCRIPTION
        "Represents the prefix length of an AP IPv6 address."
    ::= { unisDot11APObjectEntry 29 }
-- *****************************************************************************
-- *  End of unisDot11APObjectTable Definition
-- *****************************************************************************

-- *****************************************************************************
-- *  unisDot11APRadioTable Definition
-- *****************************************************************************
unisDot11APRadioTable OBJECT-TYPE
    SYNTAX      SEQUENCE OF UnisDot11APRadioEntry
    MAX-ACCESS  not-accessible
    STATUS      current
    DESCRIPTION
        "The table will describe the radio information of AP.  The AP here will
        be in running status."
    ::= { unisDot11APObjectGroup 3 }

unisDot11APRadioEntry OBJECT-TYPE
    SYNTAX      UnisDot11APRadioEntry
    MAX-ACCESS  not-accessible
    STATUS      current
    DESCRIPTION
        "Each entry contains the information of each radio of a specific AP."
    INDEX
        {
            unisDot11CurAPID,
            unisDot11RadioID
        }
    ::= { unisDot11APRadioTable 1 }

UnisDot11APRadioEntry ::= SEQUENCE
    {
        unisDot11CurAPID            OCTET STRING,
        unisDot11RadioID            Integer32,
        unisDot11AdminStatus        TruthValue,
        unisDot11OperStatus         TruthValue,
        unisDot11Channel            UnisDot11ChannelScopeType,
        unisDot11TxPowerLevel       UnisDot11TxPwrLevelScopeType,
        unisDot11APRadioIfIndex     Integer32,
        unisDot11AntennaGain        Integer32,
        unisDot11MaxBandwidth       Integer32,
        unisDot11ResourceUseRatio   Integer32,
        unisDot11RadioModeSupport   Unsigned32,
        unisDot11TxPowerLevel2      Integer32,
        unisDot11PowerMgmtStatus    TruthValue,
        unisDot11ChannelSwitchTimes Counter32,
        unisDot11AntennaType        OCTET STRING,
        unisDot11DiversitySelectionRx     TruthValue,
        unisDot11MaxTxPwrLvl              OCTET STRING,
        unisDot11PwrAttRange              Integer32,
        unisDot11AvgRxSignalStrength      Integer32,
        unisDot11HighestRxSignalStrength  Integer32,
        unisDot11LowestRxSignalStrength   Integer32,
        unisDot11RadioIfUpdownTimes       Counter32,
        unisDot11RadioIfLastChange        TimeTicks,
        unisDot11RadioModeSupport2        Unsigned32,
        unisDot11OperStatusCM             INTEGER,
        unisDot11AirPrimChnlBusy          Integer32,
        unisDot11AirPrimChnlTxBusy        Integer32,
        unisDot11AirPrimChnlRxBusy        Integer32,
        unisDot11AirExtChnlBusy           Integer32
    }

unisDot11CurAPID OBJECT-TYPE
    SYNTAX      OCTET STRING(SIZE(0..64))
    MAX-ACCESS  not-accessible
    STATUS      current
    DESCRIPTION
        "To uniquely identify a AP in running status."
    ::= { unisDot11APRadioEntry 1 }

unisDot11RadioID OBJECT-TYPE
    SYNTAX      Integer32(0..2147483647)
    MAX-ACCESS  accessible-for-notify
    STATUS      current
    DESCRIPTION
        "Represents each radio."
    ::= { unisDot11APRadioEntry 2 }

unisDot11AdminStatus OBJECT-TYPE
    SYNTAX      TruthValue
    MAX-ACCESS  read-only
    STATUS      current
    DESCRIPTION
        "Represents the administrator status of radio."
    ::= { unisDot11APRadioEntry 3 }

unisDot11OperStatus OBJECT-TYPE
    SYNTAX      TruthValue
    MAX-ACCESS  read-only
    STATUS      current
    DESCRIPTION
        "Represents the operational status of radio."
    ::= { unisDot11APRadioEntry 4 }

unisDot11Channel OBJECT-TYPE
    SYNTAX      UnisDot11ChannelScopeType
    MAX-ACCESS  read-only
    STATUS      current
    DESCRIPTION
        "Represents the current channel allocation for radio."
    ::= { unisDot11APRadioEntry 5 }

unisDot11TxPowerLevel OBJECT-TYPE
    SYNTAX      UnisDot11TxPwrLevelScopeType
    UNITS       "dbm"
    MAX-ACCESS  read-only
    STATUS      current
    DESCRIPTION
        "Represents the current transmit power level for radio."
    ::= { unisDot11APRadioEntry 6 }

unisDot11APRadioIfIndex OBJECT-TYPE
    SYNTAX      Integer32
    MAX-ACCESS  read-only
    STATUS      current
    DESCRIPTION
        "Represents the interface index for the radio."
    ::= { unisDot11APRadioEntry 7 }

unisDot11AntennaGain OBJECT-TYPE
    SYNTAX      Integer32
    UNITS       "dBi"
    MAX-ACCESS  read-only
    STATUS      current
    DESCRIPTION
        "Represents the current gain for antenna."
    ::= { unisDot11APRadioEntry 8 }

unisDot11MaxBandwidth OBJECT-TYPE
    SYNTAX      Integer32
    UNITS       "Mbps"
    MAX-ACCESS  read-only
    STATUS      current
    DESCRIPTION
        "Represents the maximum bandwidth for the radio."
    ::= { unisDot11APRadioEntry 9 }

unisDot11ResourceUseRatio OBJECT-TYPE
    SYNTAX      Integer32
    UNITS       "onepercent"
    MAX-ACCESS  read-only
    STATUS      current
    DESCRIPTION
        "Represents the ratio of radio resource usage."
    ::= { unisDot11APRadioEntry 10 }

unisDot11RadioModeSupport OBJECT-TYPE
    SYNTAX      Unsigned32
    MAX-ACCESS  read-only
    STATUS      current
    DESCRIPTION
        "Represents radio type supported by the radio.
        The WLAN system supports the following possible radio type:
        dot11a(1),
        dot11b(2),
        dot11g(4),
        dot11gn(16),
        dot11an(32),
        dot11ac(64),
        dot11gac(128)
        For the radio, it could support multiple radio types at
        the same time.  So the value of this object could combine multiple
        values of radio type above.
        For example:
        For one radio which supports both dot11b and dot11g mode, when get
        value from the object, the value is 6(2 + 4)."
    ::= { unisDot11APRadioEntry 11 }

unisDot11TxPowerLevel2 OBJECT-TYPE
    SYNTAX      Integer32(1..8)
    MAX-ACCESS  read-only
    STATUS      current
    DESCRIPTION
        "The TxPowerLevel N currently being used to transmit data."
    ::= { unisDot11APRadioEntry 12 }

unisDot11PowerMgmtStatus OBJECT-TYPE
    SYNTAX      TruthValue
    MAX-ACCESS  read-only
    STATUS      current
    DESCRIPTION
        "Represents status of power management of the radio."
    ::= { unisDot11APRadioEntry 13 }

unisDot11ChannelSwitchTimes OBJECT-TYPE
    SYNTAX      Counter32
    MAX-ACCESS  read-only
    STATUS      current
    DESCRIPTION
        "Represents the channel switch times."
    ::= { unisDot11APRadioEntry 14 }

unisDot11AntennaType OBJECT-TYPE
    SYNTAX      OCTET STRING
    MAX-ACCESS  read-only
    STATUS      current
    DESCRIPTION
        "Represents type of the antenna which radio used."
    ::= { unisDot11APRadioEntry 15 }

unisDot11DiversitySelectionRx OBJECT-TYPE
    SYNTAX      TruthValue
    MAX-ACCESS  read-only
    STATUS      current
    DESCRIPTION
        "Represents the diversity selection received."
    ::= { unisDot11APRadioEntry 16 }

unisDot11MaxTxPwrLvl OBJECT-TYPE
    SYNTAX      OCTET STRING
    MAX-ACCESS  read-only
    STATUS      current
    DESCRIPTION
        "Represents the maximum transmit power."
    ::= { unisDot11APRadioEntry 17 }

unisDot11PwrAttRange OBJECT-TYPE
    SYNTAX      Integer32
    MAX-ACCESS  read-only
    STATUS      current
    DESCRIPTION
        "Represents the range of power attenuation."
    ::= { unisDot11APRadioEntry 18 }

unisDot11AvgRxSignalStrength OBJECT-TYPE
    SYNTAX      Integer32
    UNITS       "dBm"
    MAX-ACCESS  read-only
    STATUS      current
    DESCRIPTION
        "Represents the average received signal strength."
    ::= { unisDot11APRadioEntry 19 }

unisDot11HighestRxSignalStrength OBJECT-TYPE
    SYNTAX      Integer32
    UNITS       "dBm"
    MAX-ACCESS  read-only
    STATUS      current
    DESCRIPTION
        "Represents the highest received signal strength."
    ::= { unisDot11APRadioEntry 20 }

unisDot11LowestRxSignalStrength OBJECT-TYPE
    SYNTAX      Integer32
    UNITS       "dBm"
    MAX-ACCESS  read-only
    STATUS      current
    DESCRIPTION
        "Represents the lowest received signal strength."
    ::= { unisDot11APRadioEntry 21 }

unisDot11RadioIfUpdownTimes OBJECT-TYPE
    SYNTAX      Counter32
    MAX-ACCESS  read-only
    STATUS      current
    DESCRIPTION
        "Represents the up/down times on radio interface."
    ::= { unisDot11APRadioEntry 22 }

unisDot11RadioIfLastChange OBJECT-TYPE
    SYNTAX      TimeTicks
    MAX-ACCESS  read-only
    STATUS      current
    DESCRIPTION
        "Represents time at last change that occurred on radio interface."
    ::= { unisDot11APRadioEntry 23 }

unisDot11RadioModeSupport2 OBJECT-TYPE
    SYNTAX      Unsigned32
    MAX-ACCESS  read-only
    STATUS      current
    DESCRIPTION
        "Represents radio type supported by the radio.
        The WLAN system supports the following possible radio type:
        dot11a(1),
        dot11b(2),
        dot11g(4),
        dot11an(8),
        dot11gn(16),
        dot11gac(32),
        dot11ac(64)
        For the radio, it could support multiple radio types at
        the same time.  So the value of this object could combine multiple
        values of radio type above.
        For example:
        For one radio which supports both dot11b and dot11g mode, when get
        value from the object, the value is 6(2 + 4)."
    ::= { unisDot11APRadioEntry 24 }

unisDot11OperStatusCM OBJECT-TYPE
    SYNTAX      INTEGER
        {
            up(1),
            down(2),
            testing(3),
            admindown(4)
        }
    MAX-ACCESS  read-only
    STATUS      current
    DESCRIPTION
        "Represents the operational status of radio."
    ::= { unisDot11APRadioEntry 25 }

unisDot11AirPrimChnlBusy OBJECT-TYPE
    SYNTAX      Integer32(0..100 | 255)
    MAX-ACCESS  read-only
    STATUS      current
    DESCRIPTION
    "Represents air interface utilization on the primary channel.
    The value 255 represents an invalid value."
    ::= { unisDot11APRadioEntry 26 }

unisDot11AirPrimChnlTxBusy OBJECT-TYPE
    SYNTAX      Integer32(0..100 | 255)
    MAX-ACCESS  read-only
    STATUS      current
    DESCRIPTION
    "Represents air interface utilization for signal sending on the
    primary channel.
    The value 255 represents an invalid value."
    ::= { unisDot11APRadioEntry 27 }

unisDot11AirPrimChnlRxBusy OBJECT-TYPE
    SYNTAX      Integer32(0..100 | 255)
    MAX-ACCESS  read-only
    STATUS      current
    DESCRIPTION
    "Represents air interface utilization for signal receiving on the
    primary channel.
    The value 255 represents an invalid value."
    ::= { unisDot11APRadioEntry 28 }

unisDot11AirExtChnlBusy OBJECT-TYPE
    SYNTAX      Integer32(0..100 | 255)
    MAX-ACCESS  read-only
    STATUS      current
    DESCRIPTION
    "Represents air interface utilization on the secondary channel.
    The value 255 represents an invalid value."
    ::= { unisDot11APRadioEntry 29 }
-- *****************************************************************************
-- *  End of unisDot11APRadioTable Definition
-- *****************************************************************************

-- *****************************************************************************
-- *  unisDot11APBSSTable Definition
-- *****************************************************************************
unisDot11APBSSTable OBJECT-TYPE
    SYNTAX      SEQUENCE OF UnisDot11APBSSEntry
    MAX-ACCESS  not-accessible
    STATUS      current
    DESCRIPTION
        "After AP connect to AC and get AP template configuration,
        it will create BSS data structure for each radio.
        The table will describe BSS information of AP and service
        policy as per BSS."
    ::= { unisDot11APObjectGroup 4 }

unisDot11APBSSEntry OBJECT-TYPE
    SYNTAX      UnisDot11APBSSEntry
    MAX-ACCESS  not-accessible
    STATUS      current
    DESCRIPTION
        "Each entry contains information of each BSS for specific radio."
    INDEX
        {
            unisDot11CurAPID,
            unisDot11RadioID,
            unisDot11WlanID
        }
    ::= { unisDot11APBSSTable 1 }

UnisDot11APBSSEntry ::= SEQUENCE
    {
        unisDot11WlanID             Integer32,
        unisDot11BSSID              MacAddress,
        unisDot11CurrSvcPolicyID    UnisDot11ServicePolicyIDType,
        unisDot11SSID               OCTET STRING,
        unisDot11CurrSSIDResourceUseRatio             Integer32,
        unisDot11APEssVlanId                          Integer32
    }

unisDot11WlanID OBJECT-TYPE
    SYNTAX      Integer32(0..2147483647)
    MAX-ACCESS  not-accessible
    STATUS      current
    DESCRIPTION
        "Represents ID of a specific ESS."
    ::= { unisDot11APBSSEntry 1 }

unisDot11BSSID OBJECT-TYPE
    SYNTAX      MacAddress
    MAX-ACCESS  read-only
    STATUS      current
    DESCRIPTION
        "As MAC Address format, it is to identify BSS."
    ::= { unisDot11APBSSEntry 2 }

unisDot11CurrSvcPolicyID OBJECT-TYPE
    SYNTAX      UnisDot11ServicePolicyIDType
    MAX-ACCESS  read-only
    STATUS      current
    DESCRIPTION
        "Represents the ID of each service policy used by the AP."
    ::= { unisDot11APBSSEntry 3 }

unisDot11SSID OBJECT-TYPE
    SYNTAX      OCTET STRING
    MAX-ACCESS  read-only
    STATUS      current
    DESCRIPTION
        "This object represents the SSID corresponding to this BSS."
    ::= { unisDot11APBSSEntry 4 }

unisDot11CurrSSIDResourceUseRatio OBJECT-TYPE
    SYNTAX      Integer32
    MAX-ACCESS  read-only
    STATUS      current
    DESCRIPTION
        "Represents the ratio of resource usage of curr SSID"
    ::= { unisDot11APBSSEntry 5 }

unisDot11APEssVlanId OBJECT-TYPE
    SYNTAX      Integer32
    MAX-ACCESS  read-only
    STATUS      current
    DESCRIPTION
        "This object represents the VlanID of the interface ESS
        corresponding to this BSS."
    ::= { unisDot11APBSSEntry 6 }
-- *****************************************************************************
-- *  End of unisDot11APBSSTable Definition
-- *****************************************************************************

-- *****************************************************************************
-- *  unisDot11APModelTable Definition
-- *****************************************************************************
unisDot11APModelTable OBJECT-TYPE
    SYNTAX      SEQUENCE OF UnisDot11APModelEntry
    MAX-ACCESS  not-accessible
    STATUS      current
    DESCRIPTION
        "The table defines the capability information for a specific
        kind of AP."
    ::= { unisDot11APObjectGroup 5 }

unisDot11APModelEntry OBJECT-TYPE
    SYNTAX      UnisDot11APModelEntry
    MAX-ACCESS  not-accessible
    STATUS      current
    DESCRIPTION
        "Each entry contains capability information for a specific kind
        of AP."
    INDEX
        {
            IMPLIED unisDot11APModelAlias
        }
    ::= { unisDot11APModelTable 1 }

UnisDot11APModelEntry ::= SEQUENCE
    {
        unisDot11APModelAlias         OCTET STRING,
        unisDot11APModelName          OCTET STRING,
        unisDot11RadioNumSupport      UnisDot11RadioScopeType,
        unisDot11StationNumSupport    Integer32,
        unisDot11MACModeSupport       UnisDot11MACModeType,
        unisDot11APManufacturer       OCTET STRING,
        unisDot11APCPUType            OCTET STRING,
        unisDot11APCPUClockSpeed      Unsigned32,
        unisDot11APMemoryType         OCTET STRING,
        unisDot11APMemorySize         Unsigned32,
        unisDot11APFlashType          OCTET STRING,
        unisDot11APFlashSize          Unsigned32,
        unisDot11APMemSize            Gauge32,
        unisDot11APFlashSizeInBytes   Unsigned32,
        unisDot11WsmAPLicenseType     INTEGER
    }

unisDot11APModelAlias OBJECT-TYPE
    SYNTAX      OCTET STRING(SIZE(0..127))
    MAX-ACCESS  not-accessible
    STATUS      current
    DESCRIPTION
        "Represents alias of AP model name."
    ::= { unisDot11APModelEntry 1 }

unisDot11APModelName OBJECT-TYPE
    SYNTAX      OCTET STRING
    MAX-ACCESS  read-only
    STATUS      current
    DESCRIPTION
        "Represents AP model name(like WA2100)."
    ::= { unisDot11APModelEntry 2 }

unisDot11RadioNumSupport OBJECT-TYPE
    SYNTAX      UnisDot11RadioScopeType
    MAX-ACCESS  read-only
    STATUS      current
    DESCRIPTION
        "Represents how many radios the specific AP model
        could support."
    ::= { unisDot11APModelEntry 3 }

unisDot11StationNumSupport OBJECT-TYPE
    SYNTAX      Integer32
    MAX-ACCESS  read-only
    STATUS      current
    DESCRIPTION
        "Represents how many station could be supported by a specific
        AP model."
    ::= { unisDot11APModelEntry 4 }

unisDot11MACModeSupport OBJECT-TYPE
    SYNTAX      UnisDot11MACModeType
    MAX-ACCESS  read-only
    STATUS      current
    DESCRIPTION
        "Represents the MAC mode type could be supported by a specific
        AP model."
    DEFVAL      { split }
    ::= { unisDot11APModelEntry 5 }

unisDot11APManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { unisDot11APModelEntry 6 }

unisDot11APCPUType OBJECT-TYPE
    SYNTAX      OCTET STRING
    MAX-ACCESS  read-only
    STATUS      current
    DESCRIPTION
        "Represents the CPU type of AP"
    ::= { unisDot11APModelEntry 7 }

unisDot11APCPUClockSpeed OBJECT-TYPE
    SYNTAX      Unsigned32
    UNITS       "Hz"
    MAX-ACCESS  read-only
    STATUS      current
    DESCRIPTION
        "Represents the clock speed of CPU."
    ::= { unisDot11APModelEntry 8 }

unisDot11APMemoryType OBJECT-TYPE
    SYNTAX      OCTET STRING
    MAX-ACCESS  read-only
    STATUS      current
    DESCRIPTION
        "Represents the memory card type of AP"
    ::= { unisDot11APModelEntry 9 }

unisDot11APMemorySize OBJECT-TYPE
    SYNTAX      Unsigned32
    UNITS       "kbytes"
    MAX-ACCESS  read-only
    STATUS      current
    DESCRIPTION
        "Represents the size of AP memory card."
    ::= { unisDot11APModelEntry 20 }

unisDot11APFlashType OBJECT-TYPE
    SYNTAX      OCTET STRING
    MAX-ACCESS  read-only
    STATUS      current
    DESCRIPTION
        "Represents the flash card type of AP"
    ::= { unisDot11APModelEntry 11 }

unisDot11APFlashSize OBJECT-TYPE
    SYNTAX      Unsigned32
    UNITS       "kbytes"
    MAX-ACCESS  read-only
    STATUS      current
    DESCRIPTION
        "Represents the size of AP flash card."
    ::= { unisDot11APModelEntry 12 }

unisDot11APMemSize OBJECT-TYPE
    SYNTAX      Gauge32
    UNITS       "bytes"
    MAX-ACCESS  read-only
    STATUS      current
    DESCRIPTION
        "Represents the size of AP memory card."
    ::= { unisDot11APModelEntry 13 }

unisDot11APFlashSizeInBytes OBJECT-TYPE
    SYNTAX      Unsigned32
    UNITS       "bytes"
    MAX-ACCESS  read-only
    STATUS      current
    DESCRIPTION
        "This object represents the size of AP flash card in bytes."
    ::= { unisDot11APModelEntry 14 }

unisDot11WsmAPLicenseType OBJECT-TYPE
    SYNTAX      INTEGER
        {
            normal(1),
            wtu(2),
            wt(3),
            iot(4),
            other(5)
        }
    MAX-ACCESS  read-only
    STATUS      current
    DESCRIPTION
        "Represents AP license type for iMc WSM."
    ::= { unisDot11APModelEntry 15 }


-- *****************************************************************************
-- *  End of unisDot11APModelTable Definition
-- *****************************************************************************

-- *****************************************************************************
-- *  unisDot11APIfTable Definition
-- *****************************************************************************
unisDot11APIfTable OBJECT-TYPE
    SYNTAX      SEQUENCE OF UnisDot11APIfEntry
    MAX-ACCESS  not-accessible
    STATUS      current
    DESCRIPTION
        "This table represents the AP interface information."
    ::= { unisDot11APObjectGroup 6 }

unisDot11APIfEntry OBJECT-TYPE
    SYNTAX      UnisDot11APIfEntry
    MAX-ACCESS  not-accessible
    STATUS      current
    DESCRIPTION
        "Each entry of the table will provide data for the interface of AP."
    INDEX
        {
            unisDot11APObjID,
            unisDot11APIfIndex
        }
    ::= { unisDot11APIfTable 1 }

UnisDot11APIfEntry ::= SEQUENCE
    {
        unisDot11APIfIndex         Integer32,
        unisDot11APIfDescr         OCTET STRING,
        unisDot11APIfType          Integer32,
        unisDot11APIfMtu           Integer32,
        unisDot11APIfPHYAddress    OCTET STRING,
        unisDot11APIfSpeed         Integer32,
        unisDot11APIfInDataRate    Integer32,
        unisDot11APIfOutDataRate   Integer32,
        unisDot11APIfSpeedKbps     Gauge32,
        unisDot11APIfTypeCM        Integer32
    }

unisDot11APIfIndex OBJECT-TYPE
    SYNTAX      Integer32
    MAX-ACCESS  not-accessible
    STATUS      current
    DESCRIPTION
        "Represents the index for an interface."
    ::= { unisDot11APIfEntry 1 }

unisDot11APIfDescr OBJECT-TYPE
    SYNTAX      OCTET STRING
    MAX-ACCESS  read-only
    STATUS      current
    DESCRIPTION
        "Represents the interface description for an interface."
    ::= { unisDot11APIfEntry 2 }

unisDot11APIfType OBJECT-TYPE
    SYNTAX      Integer32
    MAX-ACCESS  read-only
    STATUS      current
    DESCRIPTION
        "Represents the interface type for an interface."
    ::= { unisDot11APIfEntry 3 }

unisDot11APIfMtu OBJECT-TYPE
    SYNTAX      Integer32
    MAX-ACCESS  read-write
    STATUS      current
    DESCRIPTION
        "Represents size of the largest datagram which can
        be sent/received on the interface, specified in octets."
    ::= { unisDot11APIfEntry 4 }

unisDot11APIfPHYAddress OBJECT-TYPE
    SYNTAX      OCTET STRING
    MAX-ACCESS  read-only
    STATUS      current
    DESCRIPTION
        "Represents the PHY address of interface."
    ::= { unisDot11APIfEntry 5 }

unisDot11APIfSpeed OBJECT-TYPE
    SYNTAX      Integer32
    UNITS       "Mbps"
    MAX-ACCESS  read-only
    STATUS      current
    DESCRIPTION
        "Represents maximum bandwidth of this interface."
    ::= { unisDot11APIfEntry 6 }

unisDot11APIfInDataRate OBJECT-TYPE
    SYNTAX      Integer32
    UNITS       "Kbps"
    MAX-ACCESS  read-only
    STATUS      current
    DESCRIPTION
        "Represents the average input data rate of this interface in
        latest 300 seconds."
    ::= { unisDot11APIfEntry 7 }

unisDot11APIfOutDataRate OBJECT-TYPE
    SYNTAX      Integer32
    UNITS       "Kbps"
    MAX-ACCESS  read-only
    STATUS      current
    DESCRIPTION
        "Represents the average output data rate of this interface in
        latest 300 seconds."
    ::= { unisDot11APIfEntry 8 }

unisDot11APIfSpeedKbps OBJECT-TYPE
    SYNTAX      Gauge32
    UNITS       "kbps"
    MAX-ACCESS  read-only
    STATUS      current
    DESCRIPTION
        "Represents maximum bandwidth of this interface."
    ::= { unisDot11APIfEntry 9 }

unisDot11APIfTypeCM OBJECT-TYPE
    SYNTAX      Integer32
    MAX-ACCESS  read-only
    STATUS      current
    DESCRIPTION
        "Represents the interface type."
    ::= { unisDot11APIfEntry 10 }

-- *****************************************************************************
-- *  End of unisDot11APIfTable Definition
-- *****************************************************************************

-- *****************************************************************************
-- *  unisDot11APSSIDObjectTable Definition
-- *****************************************************************************
unisDot11APSSIDObjectTable OBJECT-TYPE
    SYNTAX      SEQUENCE OF UnisDot11APSSIDObjectEntry
    MAX-ACCESS  not-accessible
    STATUS      current
    DESCRIPTION
        "This table provides BSSID number configuration information
         based on SSID."
    ::= { unisDot11APObjectGroup 7 }

unisDot11APSSIDObjectEntry OBJECT-TYPE
    SYNTAX      UnisDot11APSSIDObjectEntry
    MAX-ACCESS  not-accessible
    STATUS      current
    DESCRIPTION
        "Each entry provides BSSID number configuration information
         of a SSID."
    INDEX
        {
            unisDot11APConfigSPID
        }
    ::= { unisDot11APSSIDObjectTable 1 }

UnisDot11APSSIDObjectEntry ::= SEQUENCE
    {
        unisDot11APConfigSPID              UnisDot11ServicePolicyIDType,
        unisDot11APConfigSSIDName          UnisDot11SSIDStringType,
        unisDot11APConfigBSSIDNum          Integer32,
        unisDot11APConfigPortalStaNum      Integer32,
        unisDot11APAssocStaNum             Integer32
    }

unisDot11APConfigSPID OBJECT-TYPE
    SYNTAX      UnisDot11ServicePolicyIDType
    MAX-ACCESS  not-accessible
    STATUS      current
    DESCRIPTION
        "Represents the service policy ID."
    ::= { unisDot11APSSIDObjectEntry 1 }

unisDot11APConfigSSIDName OBJECT-TYPE
    SYNTAX      UnisDot11SSIDStringType
    MAX-ACCESS  read-only
    STATUS      current
    DESCRIPTION
        "Represents the SSID name of this service policy."
    ::= { unisDot11APSSIDObjectEntry 2 }

unisDot11APConfigBSSIDNum OBJECT-TYPE
    SYNTAX      Integer32
    MAX-ACCESS  read-only
    STATUS      current
    DESCRIPTION
        "Represents the number of BSSID that be configured
         with current SSID."
    ::= { unisDot11APSSIDObjectEntry 3 }

unisDot11APConfigPortalStaNum OBJECT-TYPE
    SYNTAX      Integer32
    MAX-ACCESS  read-only
    STATUS      current
    DESCRIPTION
        "Represents the total number of associated protal
        stations with current SSID."
    ::= { unisDot11APSSIDObjectEntry 4 }

unisDot11APAssocStaNum OBJECT-TYPE
    SYNTAX      Integer32
    MAX-ACCESS  read-only
    STATUS      current
    DESCRIPTION
        "Represents the total number of associated stations with current SSID."
    ::= { unisDot11APSSIDObjectEntry 5 }

-- *****************************************************************************
-- *  End of unisDot11APSSIDObjectTable Definition
-- *****************************************************************************

-- *****************************************************************************
-- *  unisDot11APSysInfoTable Definition
-- *****************************************************************************
unisDot11APSysInfoTable OBJECT-TYPE
    SYNTAX      SEQUENCE OF UnisDot11APSysInfoEntry
    MAX-ACCESS  not-accessible
    STATUS      current
    DESCRIPTION
        "The table provides the system information of the AP."
    ::= { unisDot11APObjectGroup 8 }

unisDot11APSysInfoEntry OBJECT-TYPE
    SYNTAX      UnisDot11APSysInfoEntry
    MAX-ACCESS  not-accessible
    STATUS      current
    DESCRIPTION
        "Each entry provides system information of an AP."
    INDEX
        {
            unisDot11APElementIndex
        }
    ::= { unisDot11APSysInfoTable 1 }

UnisDot11APSysInfoEntry ::= SEQUENCE
    {
        unisDot11APSysUpTime           TimeTicks,
        unisDot11APCPURTUsage          Integer32,
        unisDot11APCPUAvgUsage         Integer32,
        unisDot11APMemRTUsage          Integer32,
        unisDot11APMemAvgUsage         Integer32,
        unisDot11APIPAddressGateway    IpAddress,
        unisDot11APACAssociateStatus   INTEGER,
        unisDot11APManuBuildInfo       OCTET STRING,
        unisDot11APFlashFreeSize       Unsigned32,
        unisDot11APTemperature         Integer32
    }

unisDot11APSysUpTime OBJECT-TYPE
    SYNTAX      TimeTicks
    MAX-ACCESS  read-only
    STATUS      current
    DESCRIPTION
        "Represents how long AP has been powered on."
    ::= { unisDot11APSysInfoEntry 1 }

unisDot11APCPURTUsage OBJECT-TYPE
    SYNTAX      Integer32(0..100)
    UNITS       "onepercent"
    MAX-ACCESS  read-only
    STATUS      current
    DESCRIPTION
        "Represents the CPU real time usage for AP."
    ::= { unisDot11APSysInfoEntry 2 }

unisDot11APCPUAvgUsage OBJECT-TYPE
    SYNTAX      Integer32(0..100)
    UNITS       "onepercent"
    MAX-ACCESS  read-only
    STATUS      current
    DESCRIPTION
        "Represents the CPU average usage for AP."
    ::= { unisDot11APSysInfoEntry 3 }

unisDot11APMemRTUsage OBJECT-TYPE
    SYNTAX      Integer32(0..100)
    UNITS       "onepercent"
    MAX-ACCESS  read-only
    STATUS      current
    DESCRIPTION
        "Represents the memory real time usage for AP."
    ::= { unisDot11APSysInfoEntry 4 }

unisDot11APMemAvgUsage OBJECT-TYPE
    SYNTAX      Integer32(0..100)
    UNITS       "onepercent"
    MAX-ACCESS  read-only
    STATUS      current
    DESCRIPTION
        "Represents the average memory usage for AP."
    ::= { unisDot11APSysInfoEntry 5 }

unisDot11APIPAddressGateway OBJECT-TYPE
    SYNTAX      IpAddress
    MAX-ACCESS  read-only
    STATUS      current
    DESCRIPTION
        "Represents the IP address gateway for AP."
    ::= { unisDot11APSysInfoEntry 6 }

unisDot11APACAssociateStatus OBJECT-TYPE
    SYNTAX      INTEGER
        {
            associated(1),
            deassociated(2),
            downloadingImage(3)
        }
    MAX-ACCESS  read-only
    STATUS      current
    DESCRIPTION
        "Represents associate status of AP and AC."
    ::= { unisDot11APSysInfoEntry 7 }

unisDot11APManuBuildInfo OBJECT-TYPE
    SYNTAX      OCTET STRING(SIZE(0..255))
    MAX-ACCESS  read-only
    STATUS      current
    DESCRIPTION
        "Represents the device version information for AP."
    ::= { unisDot11APSysInfoEntry 8 }

unisDot11APFlashFreeSize OBJECT-TYPE
    SYNTAX      Unsigned32
    UNITS       "bytes"
    MAX-ACCESS  read-only
    STATUS      current
    DESCRIPTION
        "Represents the free size of AP flash card."
    ::= { unisDot11APSysInfoEntry 9 }

unisDot11APTemperature OBJECT-TYPE
    SYNTAX      Integer32
    MAX-ACCESS  read-only
    STATUS      current
    DESCRIPTION
        "Represents the device temperature information for AP."
    ::= { unisDot11APSysInfoEntry 10 }

-- *****************************************************************************
-- *  End of unisDot11APSysInfoTable Definition
-- *****************************************************************************

-- *****************************************************************************
-- *  unisDot11APIdleListTable Definition
-- *****************************************************************************
unisDot11APIdleListTable OBJECT-TYPE
    SYNTAX      SEQUENCE OF UnisDot11APIdleListEntry
    MAX-ACCESS  not-accessible
    STATUS      current
    DESCRIPTION
        "This table provides the list of idle AP."
    ::= { unisDot11APObjectGroup 9 }

unisDot11APIdleListEntry OBJECT-TYPE
    SYNTAX      UnisDot11APIdleListEntry
    MAX-ACCESS  not-accessible
    STATUS      current
    DESCRIPTION
        "Each entry provides information of a idle AP."
    INDEX
        {
            unisDot11APIdleTemplateName
        }
    ::= { unisDot11APIdleListTable 1 }

UnisDot11APIdleListEntry ::= SEQUENCE
    {
        unisDot11APIdleTemplateName OCTET STRING,
        unisDot11APIdleSerialID     OCTET STRING
    }

unisDot11APIdleTemplateName OBJECT-TYPE
    SYNTAX      OCTET STRING(SIZE(0..127))
    MAX-ACCESS  not-accessible
    STATUS      current
    DESCRIPTION
        "Represents the name of idle AP template."
    ::= { unisDot11APIdleListEntry 1 }

unisDot11APIdleSerialID    OBJECT-TYPE
    SYNTAX      OCTET STRING
    MAX-ACCESS  read-only
    STATUS      current
    DESCRIPTION
        "Represents AP serial ID."
    ::= { unisDot11APIdleListEntry 2 }

-- *****************************************************************************
-- *  End of unisDot11APIdleListTable Definition
-- *****************************************************************************

-- *****************************************************************************
-- *  unisDot11APSysInfoByAPIDTable Definition
-- *****************************************************************************
unisDot11APSysInfoByAPIDTable OBJECT-TYPE
    SYNTAX      SEQUENCE OF UnisDot11APSysInfoByAPIDEntry
    MAX-ACCESS  not-accessible
    STATUS      current
    DESCRIPTION
        "The table provides the system information of the AP."
    ::= { unisDot11APObjectGroup 10 }

unisDot11APSysInfoByAPIDEntry OBJECT-TYPE
    SYNTAX      UnisDot11APSysInfoByAPIDEntry
    MAX-ACCESS  not-accessible
    STATUS      current
    DESCRIPTION
        "Each entry provides system information of an AP."
    INDEX
        {
            unisDot11APObjID
        }
    ::= { unisDot11APSysInfoByAPIDTable 1 }

UnisDot11APSysInfoByAPIDEntry ::= SEQUENCE
    {
        unisDot11APSysUpTime2           TimeTicks,
        unisDot11APCPURTUsage2          Integer32,
        unisDot11APCPUAvgUsage2         Integer32,
        unisDot11APMemRTUsage2          Integer32,
        unisDot11APMemAvgUsage2         Integer32,
        unisDot11APIPAddressGateway2    IpAddress,
        unisDot11APACAssociateStatus2   INTEGER,
        unisDot11APManuBuildInfo2       OCTET STRING,
        unisDot11APFlashFreeSize2       Unsigned32,
        unisDot11APTemperature2         Integer32,
        unisDot11APMacAddress2          MacAddress,
        unisDot11APACAssociateStatusCM  INTEGER
    }

unisDot11APSysUpTime2 OBJECT-TYPE
    SYNTAX      TimeTicks
    MAX-ACCESS  read-only
    STATUS      current
    DESCRIPTION
        "Represents how long AP has been powered on."
    ::= { unisDot11APSysInfoByAPIDEntry 1 }

unisDot11APCPURTUsage2 OBJECT-TYPE
    SYNTAX      Integer32(0..100)
    UNITS       "onepercent"
    MAX-ACCESS  read-only
    STATUS      current
    DESCRIPTION
        "Represents the CPU real time usage for AP."
    ::= { unisDot11APSysInfoByAPIDEntry 2 }

unisDot11APCPUAvgUsage2 OBJECT-TYPE
    SYNTAX      Integer32(0..100)
    UNITS       "onepercent"
    MAX-ACCESS  read-only
    STATUS      current
    DESCRIPTION
        "Represents the CPU average usage for AP."
    ::= { unisDot11APSysInfoByAPIDEntry 3 }

unisDot11APMemRTUsage2 OBJECT-TYPE
    SYNTAX      Integer32(0..100)
    UNITS       "onepercent"
    MAX-ACCESS  read-only
    STATUS      current
    DESCRIPTION
        "Represents the memory real time usage for AP."
    ::= { unisDot11APSysInfoByAPIDEntry 4 }

unisDot11APMemAvgUsage2 OBJECT-TYPE
    SYNTAX      Integer32(0..100)
    UNITS       "onepercent"
    MAX-ACCESS  read-only
    STATUS      current
    DESCRIPTION
        "Represents the average memory usage for AP."
    ::= { unisDot11APSysInfoByAPIDEntry 5 }

unisDot11APIPAddressGateway2 OBJECT-TYPE
    SYNTAX      IpAddress
    MAX-ACCESS  read-only
    STATUS      current
    DESCRIPTION
        "Represents the IP address gateway for AP."
    ::= { unisDot11APSysInfoByAPIDEntry 6 }

unisDot11APACAssociateStatus2 OBJECT-TYPE
    SYNTAX      INTEGER
        {
            associated(1),
            deassociated(2),
            downloadingImage(3)
        }
    MAX-ACCESS  read-only
    STATUS      current
    DESCRIPTION
        "Represents associate status of AP and AC."
    ::= { unisDot11APSysInfoByAPIDEntry 7 }

unisDot11APManuBuildInfo2 OBJECT-TYPE
    SYNTAX      OCTET STRING(SIZE(0..255))
    MAX-ACCESS  read-only
    STATUS      current
    DESCRIPTION
        "Represents the device version information for AP."
    ::= { unisDot11APSysInfoByAPIDEntry 8 }

unisDot11APFlashFreeSize2 OBJECT-TYPE
    SYNTAX      Unsigned32
    UNITS       "bytes"
    MAX-ACCESS  read-only
    STATUS      current
    DESCRIPTION
        "Represents the free size of AP flash card."
    ::= { unisDot11APSysInfoByAPIDEntry 9 }

unisDot11APTemperature2 OBJECT-TYPE
    SYNTAX      Integer32
    MAX-ACCESS  read-only
    STATUS      current
    DESCRIPTION
        "Represents the device temperature information for AP."
    ::= { unisDot11APSysInfoByAPIDEntry 10 }

unisDot11APMacAddress2 OBJECT-TYPE
    SYNTAX      MacAddress
    MAX-ACCESS  read-only
    STATUS      current
    DESCRIPTION
        "Represents the MAC address of AP."
    ::= { unisDot11APSysInfoByAPIDEntry 11 }

unisDot11APACAssociateStatusCM OBJECT-TYPE
    SYNTAX      INTEGER
        {
            deassociated(0),
            associated(1)
        }
    MAX-ACCESS  read-only
    STATUS      current
    DESCRIPTION
        "Represents associate status of AP and AC."
    ::= { unisDot11APSysInfoByAPIDEntry 12 }

-- *****************************************************************************
-- *  End of unisDot11APSysInfoByAPIDTable Definition
-- *****************************************************************************

-- *****************************************************************************
-- *  unisDot11WTUAPInfoTable Definition
-- *****************************************************************************
unisDot11WTUAPInfoTable OBJECT-TYPE
    SYNTAX      SEQUENCE OF UnisDot11WTUAPInfoEntry
    MAX-ACCESS  not-accessible
    STATUS      current
    DESCRIPTION
        "The table provides relationship information between wireless terminator units (WTUs) and WTs."
    ::= { unisDot11APObjectGroup 11 }

unisDot11WTUAPInfoEntry OBJECT-TYPE
    SYNTAX      UnisDot11WTUAPInfoEntry
    MAX-ACCESS  not-accessible
    STATUS      current
    DESCRIPTION
        "Each entry provides relationship information between a WTU and a WT."
    INDEX
        {
            unisDot11ContainerSerialID,
            unisDot11WTUAPSerialID
        }
    ::= { unisDot11WTUAPInfoTable 1 }

UnisDot11WTUAPInfoEntry ::= SEQUENCE
    {
        unisDot11ContainerSerialID    UnisDot11ObjectIDType,
        unisDot11WTUAPSerialID        UnisDot11ObjectIDType,
        unisDot11WTUAPSubSlotID       Unsigned32
    }

unisDot11ContainerSerialID OBJECT-TYPE
    SYNTAX      UnisDot11ObjectIDType
    MAX-ACCESS  not-accessible
    STATUS      current
    DESCRIPTION
        "Serial ID that uniquely identifies a WT."
    ::= { unisDot11WTUAPInfoEntry 1 }

unisDot11WTUAPSerialID OBJECT-TYPE
    SYNTAX      UnisDot11ObjectIDType
    MAX-ACCESS  not-accessible
    STATUS      current
    DESCRIPTION
        "Serial ID that uniquely identifies a WTU."
    ::= { unisDot11WTUAPInfoEntry 2 }

unisDot11WTUAPSubSlotID OBJECT-TYPE
    SYNTAX      Unsigned32
    MAX-ACCESS  read-only
    STATUS      current
    DESCRIPTION
        "Represents the sub-slot ID of a WTU."
    ::= { unisDot11WTUAPInfoEntry 3 }

-- *****************************************************************************
-- *  End of unisDot11WTUAPInfoTable Definition
-- *****************************************************************************

-- *****************************************************************************
-- *  unisDot11APRxStatisTable Definition
-- *****************************************************************************
unisDot11APRxStatisTable OBJECT-TYPE
    SYNTAX      SEQUENCE OF UnisDot11APRxStatisEntry
    MAX-ACCESS  not-accessible
    STATUS      current
    DESCRIPTION
        "The table will provide the receiving statistic for a specific
        radio of AP."
    ::= { unisDot11APStatisGroup 1 }

unisDot11APRxStatisEntry OBJECT-TYPE
    SYNTAX      UnisDot11APRxStatisEntry
    MAX-ACCESS  not-accessible
    STATUS      current
    DESCRIPTION
        "Each entry of the table will provide the statistic data for
        each radio of a specific AP."
    INDEX
        {
            unisDot11CurAPID,
            unisDot11RadioID
        }
    ::= { unisDot11APRxStatisTable 1 }

UnisDot11APRxStatisEntry ::= SEQUENCE
    {
        unisDot11RxFrameDupCnt          Counter32,
        unisDot11RxFrameCnt             Counter32,
        unisDot11RxUcastFrameCnt        Counter32,
        unisDot11RxBcastFrameCnt        Counter32,
        unisDot11RxMcastFrameCnt        Counter32,
        unisDot11RxDiscardFrameCnt      Counter32,
        unisDot11RxFragCnt              Counter32,
        unisDot11RxFcsErrCnt            Counter32,
        unisDot11RxFrameBytes           Counter32,
        unisDot11RxUcastFrameBytes      Counter32,
        unisDot11RxBcastFrameBytes      Counter32,
        unisDot11RxMcastFrameBytes      Counter32,
        unisDot11RxDiscardFrameBytes    Counter32,
        unisDot11RxMgmtFrameCnt         Counter32,
        unisDot11RxCtrlFrameCnt         Counter32,
        unisDot11RxDataFrameCnt         Counter32,
        unisDot11RxDecryptErrorCnt      Counter32,
        unisDot11RxAuthenFrameCnt       Counter32,
        unisDot11RxAssociateFrameCnt    Counter32,
        unisDot11RxFrameErrorRatio      Integer32,
        unisDot11RxPhyErrorCnt          Counter32,
        unisDot11RxMICErrorCnt          Counter32,
        unisDot11RxDataFrameBytes       Counter32,
        unisDot11RadioRxAverSnr         Integer32,
        unisDot11RxPayloadBytes         Counter32,
        unisDot11RxTrafficSpeed         Integer32,
        unisDot11RxUcastDataFrameCnt    Counter64,
        unisDot11RxNUcastDataFrameCnt   Counter64,
        unisDot11RxTotalDiscardFrameCnt Counter64,
        unisDot11RxTotalIPCheckErrPacketCnt    Counter64,
        unisDot11RxSignalStrengthPacketCntCM   OCTET STRING,
        unisDot11RxDataFrameCntCM              Counter32,
        unisDot11RxTotalFrameCnt               Counter64
    }

unisDot11RxFrameDupCnt OBJECT-TYPE
    SYNTAX      Counter32
    MAX-ACCESS  read-only
    STATUS      current
    DESCRIPTION
        "Represents the number of duplicate frames reception."
    ::= { unisDot11APRxStatisEntry 1 }

unisDot11RxFrameCnt OBJECT-TYPE
    SYNTAX      Counter32
    MAX-ACCESS  read-only
    STATUS      current
    DESCRIPTION
        "Represents the number of frames reception."
    ::= { unisDot11APRxStatisEntry 2 }

unisDot11RxUcastFrameCnt OBJECT-TYPE
    SYNTAX      Counter32
    MAX-ACCESS  read-only
    STATUS      current
    DESCRIPTION
        "Represents the number of unicast frames reception."
    ::= { unisDot11APRxStatisEntry 3 }

unisDot11RxBcastFrameCnt OBJECT-TYPE
    SYNTAX      Counter32
    MAX-ACCESS  read-only
    STATUS      current
    DESCRIPTION
        "Represents the number of broadcast frames reception."
    ::= { unisDot11APRxStatisEntry 4 }

unisDot11RxMcastFrameCnt OBJECT-TYPE
    SYNTAX      Counter32
    MAX-ACCESS  read-only
    STATUS      current
    DESCRIPTION
        "Represents the number of multicast frames reception."
    ::= { unisDot11APRxStatisEntry 5 }

unisDot11RxDiscardFrameCnt OBJECT-TYPE
    SYNTAX      Counter32
    MAX-ACCESS  read-only
    STATUS      current
    DESCRIPTION
        "Represents the number of frames discarded by AP."
    ::= { unisDot11APRxStatisEntry 6 }

unisDot11RxFragCnt OBJECT-TYPE
    SYNTAX      Counter32
    MAX-ACCESS  read-only
    STATUS      current
    DESCRIPTION
        "Represents the number of frame fragments reception."
    ::= { unisDot11APRxStatisEntry 7 }

unisDot11RxFcsErrCnt OBJECT-TYPE
    SYNTAX      Counter32
    MAX-ACCESS  read-only
    STATUS      current
    DESCRIPTION
        "Represents the number of FCS error frames reception."
    ::= { unisDot11APRxStatisEntry 8 }

unisDot11RxFrameBytes OBJECT-TYPE
    SYNTAX      Counter32
    MAX-ACCESS  read-only
    STATUS      current
    DESCRIPTION
        "Represents the bytes of frames reception."
    ::= { unisDot11APRxStatisEntry 9 }

unisDot11RxUcastFrameBytes OBJECT-TYPE
    SYNTAX      Counter32
    MAX-ACCESS  read-only
    STATUS      current
    DESCRIPTION
        "Represents the bytes of unicast frames reception."
    ::= { unisDot11APRxStatisEntry 10 }

unisDot11RxBcastFrameBytes OBJECT-TYPE
    SYNTAX      Counter32
    MAX-ACCESS  read-only
    STATUS      current
    DESCRIPTION
        "Represents the bytes of broadcast frames reception."
    ::= { unisDot11APRxStatisEntry 11 }

unisDot11RxMcastFrameBytes OBJECT-TYPE
    SYNTAX      Counter32
    MAX-ACCESS  read-only
    STATUS      current
    DESCRIPTION
        "Represents the bytes of multicast frames reception."
    ::= { unisDot11APRxStatisEntry 12 }

unisDot11RxDiscardFrameBytes OBJECT-TYPE
    SYNTAX      Counter32
    MAX-ACCESS  read-only
    STATUS      current
    DESCRIPTION
        "Represents the bytes of frames discarded by AP."
    ::= { unisDot11APRxStatisEntry 13 }

unisDot11RxMgmtFrameCnt OBJECT-TYPE
    SYNTAX      Counter32
    MAX-ACCESS  read-only
    STATUS      current
    DESCRIPTION
        "Represents the number of management frames reception."
    ::= { unisDot11APRxStatisEntry 14 }

unisDot11RxCtrlFrameCnt OBJECT-TYPE
    SYNTAX      Counter32
    MAX-ACCESS  read-only
    STATUS      current
    DESCRIPTION
        "Represents the number of control frames reception."
    ::= { unisDot11APRxStatisEntry 15 }

unisDot11RxDataFrameCnt OBJECT-TYPE
    SYNTAX      Counter32
    MAX-ACCESS  read-only
    STATUS      current
    DESCRIPTION
        "Represents the number of data frames reception."
    ::= { unisDot11APRxStatisEntry 16 }

unisDot11RxDecryptErrorCnt OBJECT-TYPE
    SYNTAX      Counter32
    MAX-ACCESS  read-only
    STATUS      current
    DESCRIPTION
        "Represents the number of decryption error."
    ::= { unisDot11APRxStatisEntry 17 }

unisDot11RxAuthenFrameCnt OBJECT-TYPE
    SYNTAX      Counter32
    MAX-ACCESS  read-only
    STATUS      current
    DESCRIPTION
        "Represents the number of authentication frame reception."
    ::= { unisDot11APRxStatisEntry 18 }

unisDot11RxAssociateFrameCnt OBJECT-TYPE
    SYNTAX      Counter32
    MAX-ACCESS  read-only
    STATUS      current
    DESCRIPTION
        "Represents the number of associate frame reception."
    ::= { unisDot11APRxStatisEntry 19 }

unisDot11RxFrameErrorRatio OBJECT-TYPE
    SYNTAX      Integer32
    UNITS       "onepercent"
    MAX-ACCESS  read-only
    STATUS      current
    DESCRIPTION
        "Represents the ratio of error frame."
    ::= { unisDot11APRxStatisEntry 20 }

unisDot11RxPhyErrorCnt OBJECT-TYPE
    SYNTAX      Counter32
    MAX-ACCESS  read-only
    STATUS      current
    DESCRIPTION
        "Represents the number of physical reception error."
    ::= { unisDot11APRxStatisEntry 21 }

unisDot11RxMICErrorCnt OBJECT-TYPE
    SYNTAX      Counter32
    MAX-ACCESS  read-only
    STATUS      current
    DESCRIPTION
        "Represents the number of MIC verification error."
    ::= { unisDot11APRxStatisEntry 22 }

unisDot11RxDataFrameBytes OBJECT-TYPE
    SYNTAX      Counter32
    MAX-ACCESS  read-only
    STATUS      current
    DESCRIPTION
        "Represents the bytes of data frames reception."
    ::= { unisDot11APRxStatisEntry 23 }

unisDot11RadioRxAverSnr OBJECT-TYPE
    SYNTAX      Integer32
    MAX-ACCESS  read-only
    STATUS      current
    DESCRIPTION
        "Represents the average signal noise rate of this radio."
    ::= { unisDot11APRxStatisEntry 24 }

unisDot11RxPayloadBytes OBJECT-TYPE
    SYNTAX      Counter32
    MAX-ACCESS  read-only
    STATUS      current
    DESCRIPTION
        "Represents the payload bytes of data frames reception."
    ::= { unisDot11APRxStatisEntry 25 }

unisDot11RxTrafficSpeed OBJECT-TYPE
    SYNTAX      Integer32
    UNITS       "byte/s"
    MAX-ACCESS  read-only
    STATUS      current
    DESCRIPTION
        "Represents the bytes of frames reception per second."
    ::= { unisDot11APRxStatisEntry 26 }

unisDot11RxUcastDataFrameCnt OBJECT-TYPE
    SYNTAX      Counter64
    MAX-ACCESS  read-only
    STATUS      current
    DESCRIPTION
        "Represents the number of unicast data frames reception."
    ::= { unisDot11APRxStatisEntry 27 }

unisDot11RxNUcastDataFrameCnt OBJECT-TYPE
    SYNTAX      Counter64
    MAX-ACCESS  read-only
    STATUS      current
    DESCRIPTION
        "Represents the number of non-unicast data frames reception."
    ::= { unisDot11APRxStatisEntry 28 }

unisDot11RxTotalDiscardFrameCnt OBJECT-TYPE
    SYNTAX      Counter64
    MAX-ACCESS  read-only
    STATUS      current
    DESCRIPTION
        "Represents the number of total frames discarded by radio."
    ::= { unisDot11APRxStatisEntry 29 }

unisDot11RxTotalIPCheckErrPacketCnt OBJECT-TYPE
    SYNTAX      Counter64
    MAX-ACCESS  read-only
    STATUS      current
    DESCRIPTION
        "Represents the total number of IP checksum error packets
        received through the current radio."
    ::= { unisDot11APRxStatisEntry 30 }

unisDot11RxSignalStrengthPacketCntCM OBJECT-TYPE
    SYNTAX      OCTET STRING
    MAX-ACCESS  read-only
    STATUS      current
    DESCRIPTION
        "Represents the count of received packets according to signal strength."
    ::= { unisDot11APRxStatisEntry 31 }

unisDot11RxDataFrameCntCM OBJECT-TYPE
    SYNTAX      Counter32
    MAX-ACCESS  read-only
    STATUS      current
    DESCRIPTION
        "Represents the number of received data frames, excluding retransmitted
        frames."
    ::= { unisDot11APRxStatisEntry 32 }

unisDot11RxTotalFrameCnt OBJECT-TYPE
    SYNTAX      Counter64
    MAX-ACCESS  read-only
    STATUS      current
    DESCRIPTION
        "Represents the total number of packets
        received through the current radio."
    ::= { unisDot11APRxStatisEntry 33 }

-- *****************************************************************************
-- *  End of unisDot11APRxStatisTable Definition
-- *****************************************************************************

-- *****************************************************************************
-- *  unisDot11APTxStatisTable Definition
-- *****************************************************************************
unisDot11APTxStatisTable OBJECT-TYPE
    SYNTAX      SEQUENCE OF UnisDot11APTxStatisEntry
    MAX-ACCESS  not-accessible
    STATUS      current
    DESCRIPTION
        "The table will provide the transmission statistic for a
        specific radio of AP."
    ::= { unisDot11APStatisGroup 2 }

unisDot11APTxStatisEntry OBJECT-TYPE
    SYNTAX      UnisDot11APTxStatisEntry
    MAX-ACCESS  not-accessible
    STATUS      current
    DESCRIPTION
        "Each entry of the table will provide the statistic data for
        each radio of a specific AP."
    INDEX
        {
            unisDot11CurAPID,
            unisDot11RadioID
        }
    ::= { unisDot11APTxStatisTable 1 }

UnisDot11APTxStatisEntry ::= SEQUENCE
    {
        unisDot11TxFragCnt              Counter32,
        unisDot11FailedCnt              Counter32,
        unisDot11RetryCnt               Counter32,
        unisDot11MultiRetryCnt          Counter32,
        unisDot11RtsSuccessCnt          Counter32,
        unisDot11RtsFailCnt             Counter32,
        unisDot11AckFailCnt             Counter32,
        unisDot11TxFrameCnt             Counter32,
        unisDot11TxUcastFrameCnt        Counter32,
        unisDot11TxBcastFrameCnt        Counter32,
        unisDot11TxMcastFrameCnt        Counter32,
        unisDot11TxDiscardFrameCnt      Counter32,
        unisDot11TxFrameBytes           Counter32,
        unisDot11TxUcastFrameBytes      Counter32,
        unisDot11TxBcastFrameBytes      Counter32,
        unisDot11TxMcastFrameBytes      Counter32,
        unisDot11TxDiscardFrameBytes    Counter32,
        unisDot11TxAuthenFrameCnt       Counter32,
        unisDot11TxAssociateFrameCnt    Counter32,
        unisDot11TxFrameRetryRatio      Integer32,
        unisDot11TxDataFrameCnt         Counter32,
        unisDot11TxDataFrameBytes       Counter32,
        unisDot11TxMSDUCnt              Counter32,
        unisDot11TxDiscardMSDUCnt       Counter32,
        unisDot11RetryMSDUCnt           Counter32,
        unisDot11TxPayloadBytes         Counter32,
        unisDot11TxTrafficSpeed         Integer32,
        unisDot11TxErrFrameRatio        Integer32,
        unisDot11TxFrameRate            Integer32,
        unisDot11TxMgtFrameCnt          Counter32,
        unisDot11TxCtrlFrameCnt         Counter32,
        unisDot11TxMACErrCnt            Counter32,
        unisDot11TxErrFrameCnt          Counter32,
        unisDot11TxUcastDataFrameCnt    Counter64,
        unisDot11TxNUcastDataFrameCnt   Counter64,
        unisDot11TxTotalFrameCnt        Counter64
    }

unisDot11TxFragCnt OBJECT-TYPE
    SYNTAX      Counter32
    MAX-ACCESS  read-only
    STATUS      current
    DESCRIPTION
        "Represents the number of fragmented frames transmission."
    ::= { unisDot11APTxStatisEntry 1 }

unisDot11FailedCnt OBJECT-TYPE
    SYNTAX      Counter32
    MAX-ACCESS  read-only
    STATUS      current
    DESCRIPTION
        "Represents the number of transmission failures."
    ::= { unisDot11APTxStatisEntry 2 }

unisDot11RetryCnt OBJECT-TYPE
    SYNTAX      Counter32
    MAX-ACCESS  read-only
    STATUS      current
    DESCRIPTION
        "Represents the number of transmit retries."
    ::= { unisDot11APTxStatisEntry 3 }

unisDot11MultiRetryCnt OBJECT-TYPE
    SYNTAX      Counter32
    MAX-ACCESS  read-only
    STATUS      current
    DESCRIPTION
        "Represents the number of transmits that required more than
        one retry."
    ::= { unisDot11APTxStatisEntry 4 }

unisDot11RtsSuccessCnt OBJECT-TYPE
    SYNTAX      Counter32
    MAX-ACCESS  read-only
    STATUS      current
    DESCRIPTION
        "Represents the number of successful RTS (Request to send)
        transmission."
    ::= { unisDot11APTxStatisEntry 5 }

unisDot11RtsFailCnt OBJECT-TYPE
    SYNTAX      Counter32
    MAX-ACCESS  read-only
    STATUS      current
    DESCRIPTION
        "Represents the number of RTS transmission failures."
    ::= { unisDot11APTxStatisEntry 6 }

unisDot11AckFailCnt OBJECT-TYPE
    SYNTAX      Counter32
    MAX-ACCESS  read-only
    STATUS      current
    DESCRIPTION
        "Represents the number of acknowledgement failures."
    ::= { unisDot11APTxStatisEntry 7 }

unisDot11TxFrameCnt OBJECT-TYPE
    SYNTAX      Counter32
    MAX-ACCESS  read-only
    STATUS      current
    DESCRIPTION
        "Represents the total number of frames transmission."
    ::= { unisDot11APTxStatisEntry 8 }

unisDot11TxUcastFrameCnt OBJECT-TYPE
    SYNTAX      Counter32
    MAX-ACCESS  read-only
    STATUS      current
    DESCRIPTION
        "Represents the number of unicast frames transmission."
    ::= { unisDot11APTxStatisEntry 9 }

unisDot11TxBcastFrameCnt OBJECT-TYPE
    SYNTAX      Counter32
    MAX-ACCESS  read-only
    STATUS      current
    DESCRIPTION
        "Represents the number of broadcast frames transmission."
    ::= { unisDot11APTxStatisEntry 10 }

unisDot11TxMcastFrameCnt OBJECT-TYPE
    SYNTAX      Counter32
    MAX-ACCESS  read-only
    STATUS      current
    DESCRIPTION
        "Represents the number of multicast frames transmission."
    ::= { unisDot11APTxStatisEntry 11 }

unisDot11TxDiscardFrameCnt OBJECT-TYPE
    SYNTAX      Counter32
    MAX-ACCESS  read-only
    STATUS      current
    DESCRIPTION
        "Represents the number of frames discarded by AP."
    ::= { unisDot11APTxStatisEntry 12 }

unisDot11TxFrameBytes OBJECT-TYPE
    SYNTAX      Counter32
    MAX-ACCESS  read-only
    STATUS      current
    DESCRIPTION
        "Represents the total bytes of frames transmission."
    ::= { unisDot11APTxStatisEntry 13 }

unisDot11TxUcastFrameBytes OBJECT-TYPE
    SYNTAX      Counter32
    MAX-ACCESS  read-only
    STATUS      current
    DESCRIPTION
        "Represents the bytes of unicast frames transmission."
    ::= { unisDot11APTxStatisEntry 14 }

unisDot11TxBcastFrameBytes OBJECT-TYPE
    SYNTAX      Counter32
    MAX-ACCESS  read-only
    STATUS      current
    DESCRIPTION
        "Represents the bytes of broadcast frames transmission."
    ::= { unisDot11APTxStatisEntry 15 }

unisDot11TxMcastFrameBytes OBJECT-TYPE
    SYNTAX      Counter32
    MAX-ACCESS  read-only
    STATUS      current
    DESCRIPTION
        "Represents the bytes of multicast frames transmission."
    ::= { unisDot11APTxStatisEntry 16 }

unisDot11TxDiscardFrameBytes OBJECT-TYPE
    SYNTAX      Counter32
    MAX-ACCESS  read-only
    STATUS      current
    DESCRIPTION
        "Represents the bytes of discarded frames transmission."
    ::= { unisDot11APTxStatisEntry 17 }

unisDot11TxAuthenFrameCnt OBJECT-TYPE
    SYNTAX      Counter32
    MAX-ACCESS  read-only
    STATUS      current
    DESCRIPTION
        "Represents the number of authentication frame transmission."
    ::= { unisDot11APTxStatisEntry 18 }

unisDot11TxAssociateFrameCnt OBJECT-TYPE
    SYNTAX      Counter32
    MAX-ACCESS  read-only
    STATUS      current
    DESCRIPTION
        "Represents the number of associate frame transmission."
    ::= { unisDot11APTxStatisEntry 19 }

unisDot11TxFrameRetryRatio OBJECT-TYPE
    SYNTAX      Integer32
    UNITS       "onepercent"
    MAX-ACCESS  read-only
    STATUS      current
    DESCRIPTION
        "Represents the ratio of retry frame."
    ::= { unisDot11APTxStatisEntry 20 }

unisDot11TxDataFrameCnt OBJECT-TYPE
    SYNTAX      Counter32
    MAX-ACCESS  read-only
    STATUS      current
    DESCRIPTION
        "Represents the number of data frame transmission."
    ::= { unisDot11APTxStatisEntry 21 }

unisDot11TxDataFrameBytes OBJECT-TYPE
    SYNTAX      Counter32
    MAX-ACCESS  read-only
    STATUS      current
    DESCRIPTION
        "Represents the bytes of data frame transmission."
    ::= { unisDot11APTxStatisEntry 22 }

unisDot11TxMSDUCnt OBJECT-TYPE
    SYNTAX      Counter32
    MAX-ACCESS  read-only
    STATUS      current
    DESCRIPTION
        "Represents the total number of MSDU transmission."
    ::= { unisDot11APTxStatisEntry 23 }

unisDot11TxDiscardMSDUCnt OBJECT-TYPE
    SYNTAX      Counter32
    MAX-ACCESS  read-only
    STATUS      current
    DESCRIPTION
        "Represents the number of discarded MSDU transmission."
    ::= { unisDot11APTxStatisEntry 24 }

unisDot11RetryMSDUCnt OBJECT-TYPE
    SYNTAX      Counter32
    MAX-ACCESS  read-only
    STATUS      current
    DESCRIPTION
        "Represents the number of retransfer MSDU."
    ::= { unisDot11APTxStatisEntry 25 }

unisDot11TxPayloadBytes OBJECT-TYPE
    SYNTAX      Counter32
    MAX-ACCESS  read-only
    STATUS      current
    DESCRIPTION
        "Represents the payload bytes of data frames transmission."
    ::= { unisDot11APTxStatisEntry 26 }

unisDot11TxTrafficSpeed OBJECT-TYPE
    SYNTAX      Integer32
    UNITS       "byte/s"
    MAX-ACCESS  read-only
    STATUS      current
    DESCRIPTION
        "Represents the bytes of frames transmission per second."
    ::= { unisDot11APTxStatisEntry 27 }

unisDot11TxErrFrameRatio OBJECT-TYPE
    SYNTAX      Integer32
    UNITS       "onepercent"
    MAX-ACCESS  read-only
    STATUS      current
    DESCRIPTION
        "Represents the ratio of error frame."
    ::= { unisDot11APTxStatisEntry 28 }

unisDot11TxFrameRate OBJECT-TYPE
    SYNTAX      Integer32
    MAX-ACCESS  read-only
    STATUS      current
    DESCRIPTION
        "Represents the count of frames transmission per second."
    ::= { unisDot11APTxStatisEntry 29 }

unisDot11TxMgtFrameCnt OBJECT-TYPE
    SYNTAX      Counter32
    MAX-ACCESS  read-only
    STATUS      current
    DESCRIPTION
        "Represents the number of transmitted management frames."
    ::= { unisDot11APTxStatisEntry 30 }

unisDot11TxCtrlFrameCnt OBJECT-TYPE
    SYNTAX      Counter32
    MAX-ACCESS  read-only
    STATUS      current
    DESCRIPTION
        "Represents the number of transmission control frames."
    ::= { unisDot11APTxStatisEntry 31 }
unisDot11TxMACErrCnt OBJECT-TYPE
    SYNTAX      Counter32
    MAX-ACCESS  read-only
    STATUS      current
    DESCRIPTION
        "Represents the count of MAC error frame."
    ::= { unisDot11APTxStatisEntry 32 }

unisDot11TxErrFrameCnt OBJECT-TYPE
    SYNTAX      Counter32
    MAX-ACCESS  read-only
    STATUS      current
    DESCRIPTION
        "Represents the count of error frame."
    ::= { unisDot11APTxStatisEntry 33 }

unisDot11TxUcastDataFrameCnt OBJECT-TYPE
    SYNTAX      Counter64
    MAX-ACCESS  read-only
    STATUS      current
    DESCRIPTION
        "Represents the number of unicast data frames transmission."
    ::= { unisDot11APTxStatisEntry 34 }

unisDot11TxNUcastDataFrameCnt OBJECT-TYPE
    SYNTAX      Counter64
    MAX-ACCESS  read-only
    STATUS      current
    DESCRIPTION
        "Represents the number of non-unicast data frames transmission."
    ::= { unisDot11APTxStatisEntry 35 }

unisDot11TxTotalFrameCnt OBJECT-TYPE
    SYNTAX      Counter64
    MAX-ACCESS  read-only
    STATUS      current
    DESCRIPTION
        "Represents the number of total frames transmission."
    ::= { unisDot11APTxStatisEntry 36 }

-- *****************************************************************************
-- *  End of unisDot11APTxStatisTable Definition
-- *****************************************************************************

-- *****************************************************************************
-- *  unisDot11APAssocStatisTable Definition
-- *****************************************************************************
unisDot11APAssocStatisTable OBJECT-TYPE
    SYNTAX      SEQUENCE OF UnisDot11APAssocStatisEntry
    MAX-ACCESS  not-accessible
    STATUS      current
    DESCRIPTION
        "The table will provide the station association statistic for AP."
    ::= { unisDot11APStatisGroup 3 }

unisDot11APAssocStatisEntry OBJECT-TYPE
    SYNTAX      UnisDot11APAssocStatisEntry
    MAX-ACCESS  not-accessible
    STATUS      current
    DESCRIPTION
        "Each entry of the table will provide the statistic data of station
        association for AP."
    INDEX
        {
            unisDot11CurAPID
        }
    ::= { unisDot11APAssocStatisTable 1 }

UnisDot11APAssocStatisEntry ::= SEQUENCE
    {
        unisDot11ApStationAssocSum          Counter32,
        unisDot11ApStationAssocFailSum      Counter32,
        unisDot11ApStationReassocSum        Counter32,
        unisDot11ApStationAssocRejectSum    Counter32,
        unisDot11ApStationExDeAuthenSum     Counter32,
        unisDot11ApStationCurAssocSum       Integer32,
        unisDot11ApStaCurAuthSuccSum        Integer32,
        unisDot11AllStationUpSumTime        Counter32,
        unisDot11ApStationAssocReqSum       Counter32,
        unisDot11AllStationUpSumTimeTicks   TimeTicks,
        unisDot11ApStationReassocReqSum     Counter32,
        unisDot11ApStationReassocFailSum    Counter32,
        unisDot11ApStationAssocRespSum       Counter32
    }

unisDot11ApStationAssocSum OBJECT-TYPE
    SYNTAX      Counter32
    MAX-ACCESS  read-only
    STATUS      current
    DESCRIPTION
        "Represents the total number of station association
        with this AP."
    ::= { unisDot11APAssocStatisEntry 1 }

unisDot11ApStationAssocFailSum OBJECT-TYPE
    SYNTAX      Counter32
    MAX-ACCESS  read-only
    STATUS      current
    DESCRIPTION
        "Represents the total number of station
        association failure with this AP."
    ::= { unisDot11APAssocStatisEntry 2 }

unisDot11ApStationReassocSum OBJECT-TYPE
    SYNTAX      Counter32
    MAX-ACCESS  read-only
    STATUS      current
    DESCRIPTION
        "Represents the total number of station reassociation with this AP."
    ::= { unisDot11APAssocStatisEntry 3 }

unisDot11ApStationAssocRejectSum OBJECT-TYPE
    SYNTAX      Counter32
    MAX-ACCESS  read-only
    STATUS      current
    DESCRIPTION
        "Represents the total number of station association rejected
        on account of resource limit with this AP."
    ::= { unisDot11APAssocStatisEntry 4 }

unisDot11ApStationExDeAuthenSum OBJECT-TYPE
    SYNTAX      Counter32
    MAX-ACCESS  read-only
    STATUS      current
    DESCRIPTION
        "Represents the total number of exceptional station deauthentication
        (Without sending a deauthentication to AP) with this AP."
    ::= { unisDot11APAssocStatisEntry 5 }

unisDot11ApStationCurAssocSum OBJECT-TYPE
    SYNTAX      Integer32
    MAX-ACCESS  read-only
    STATUS      current
    DESCRIPTION
        "Represents the total number of current associated stations
        with this AP."
    ::= { unisDot11APAssocStatisEntry 6 }

unisDot11ApStaCurAuthSuccSum OBJECT-TYPE
    SYNTAX      Integer32
    MAX-ACCESS  read-only
    STATUS      current
    DESCRIPTION
        "Represents the successful number of station authentication
        with this AP."
    ::= { unisDot11APAssocStatisEntry 7 }

unisDot11AllStationUpSumTime OBJECT-TYPE
    SYNTAX      Counter32
    UNITS       "minute"
    MAX-ACCESS  read-only
    STATUS      current
    DESCRIPTION
        "Represents the sum of duration of all stations which associate with
         this AP."
    ::= { unisDot11APAssocStatisEntry 8 }

unisDot11ApStationAssocReqSum OBJECT-TYPE
    SYNTAX      Counter32
    MAX-ACCESS  read-only
    STATUS      current
    DESCRIPTION
        "Represents the number of station association request with this AP."
    ::= { unisDot11APAssocStatisEntry 9 }

unisDot11AllStationUpSumTimeTicks OBJECT-TYPE
    SYNTAX      TimeTicks
    MAX-ACCESS  read-only
    STATUS      current
    DESCRIPTION
        "Represents the sum of duration of all stations which associate with
         this AP."
    ::= { unisDot11APAssocStatisEntry 10 }

unisDot11ApStationReassocReqSum OBJECT-TYPE
    SYNTAX      Counter32
    MAX-ACCESS  read-only
    STATUS      current
    DESCRIPTION
        "Represents the total number of station reassociation request
        with this AP."
    ::= { unisDot11APAssocStatisEntry 11 }

unisDot11ApStationReassocFailSum OBJECT-TYPE
    SYNTAX      Counter32
    MAX-ACCESS  read-only
    STATUS      current
    DESCRIPTION
        "Represents the total number of station reassociation failure
        with this AP."
    ::= { unisDot11APAssocStatisEntry 12 }

unisDot11ApStationAssocRespSum OBJECT-TYPE
    SYNTAX      Counter32
    MAX-ACCESS  read-only
    STATUS      current
    DESCRIPTION
        "Represents the number of this AP response with station association."
    ::= { unisDot11APAssocStatisEntry 13 }

-- *****************************************************************************
-- *  End of unisDot11APAssocStatisTable Definition
-- *****************************************************************************

-- *****************************************************************************
-- *  unisDot11BSSRxStatisTable Definition
-- *****************************************************************************
unisDot11BSSRxStatisTable OBJECT-TYPE
    SYNTAX      SEQUENCE OF UnisDot11BSSRxStatisEntry
    MAX-ACCESS  not-accessible
    STATUS      current
    DESCRIPTION
        "The table will provide the reception statistic for a
        specific BSS on a radio."
    ::= { unisDot11APStatisGroup 4 }

unisDot11BSSRxStatisEntry OBJECT-TYPE
    SYNTAX      UnisDot11BSSRxStatisEntry
    MAX-ACCESS  not-accessible
    STATUS      current
    DESCRIPTION
        "Each entry of the table will provide the statistic data for
        each BSS on a specific radio."
    INDEX
        {
            unisDot11CurAPID,
            unisDot11RadioID,
            unisDot11WlanID
        }
    ::= { unisDot11BSSRxStatisTable 1 }

UnisDot11BSSRxStatisEntry ::= SEQUENCE
    {
        unisDot11BSSRxFrameCnt             Counter32,
        unisDot11BSSRxFrameBytes           Counter32,
        unisDot11BSSRxDataFrameCnt         Counter32,
        unisDot11BSSRxDataFrameBytes       Counter32,
        unisDot11BSSRxAssociateFrameCnt    Counter32,
        unisDot11BSSRxFrameErrorRatio      Integer32,
        unisDot11BSSRxPayloadBytes         Counter32,
        unisDot11BSSRxUniFrameCnt          Counter32,
        unisDot11BSSRxNonUniFrameCnt       Integer32,
        unisDot11BSSRxAuthenFrameCnt       Counter32,
        unisDot11BSSRxFrameErrCntCM        Counter32
    }

unisDot11BSSRxFrameCnt OBJECT-TYPE
    SYNTAX      Counter32
    MAX-ACCESS  read-only
    STATUS      current
    DESCRIPTION
        "Represents the number of frames reception with this BSS."
    ::= { unisDot11BSSRxStatisEntry 1 }

unisDot11BSSRxFrameBytes OBJECT-TYPE
    SYNTAX      Counter32
    MAX-ACCESS  read-only
    STATUS      current
    DESCRIPTION
        "Represents the bytes of frames reception with this BSS."
    ::= { unisDot11BSSRxStatisEntry 2 }

unisDot11BSSRxDataFrameCnt OBJECT-TYPE
    SYNTAX      Counter32
    MAX-ACCESS  read-only
    STATUS      current
    DESCRIPTION
        "Represents the number of data frames reception with this BSS."
    ::= { unisDot11BSSRxStatisEntry 3 }

unisDot11BSSRxDataFrameBytes OBJECT-TYPE
    SYNTAX      Counter32
    MAX-ACCESS  read-only
    STATUS      current
    DESCRIPTION
        "Represents the bytes of data frames reception with this BSS."
    ::= { unisDot11BSSRxStatisEntry 4 }

unisDot11BSSRxAssociateFrameCnt OBJECT-TYPE
    SYNTAX      Counter32
    MAX-ACCESS  read-only
    STATUS      current
    DESCRIPTION
        "Represents the number of associate frames reception with this BSS."
    ::= { unisDot11BSSRxStatisEntry 5 }

unisDot11BSSRxFrameErrorRatio OBJECT-TYPE
    SYNTAX      Integer32
    UNITS       "percent"
    MAX-ACCESS  read-only
    STATUS      current
    DESCRIPTION
        "Represents the ratio of error frames reception with this BSS."
    ::= { unisDot11BSSRxStatisEntry 6 }

unisDot11BSSRxPayloadBytes OBJECT-TYPE
    SYNTAX      Counter32
    MAX-ACCESS  read-only
    STATUS      current
    DESCRIPTION
        "Represents the payload bytes of data frames reception with this BSS."
    ::= { unisDot11BSSRxStatisEntry 7 }

unisDot11BSSRxUniFrameCnt OBJECT-TYPE
    SYNTAX      Counter32
    MAX-ACCESS  read-only
    STATUS      current
    DESCRIPTION
        "Represents the count of unicast frames received."
    ::= { unisDot11BSSRxStatisEntry 8 }

unisDot11BSSRxNonUniFrameCnt  OBJECT-TYPE
    SYNTAX      Integer32
    MAX-ACCESS  read-only
    STATUS      current
    DESCRIPTION
        "Represents the count of non-unicast frames received."
    ::= { unisDot11BSSRxStatisEntry 9 }

unisDot11BSSRxAuthenFrameCnt OBJECT-TYPE
    SYNTAX      Counter32
    MAX-ACCESS  read-only
    STATUS      current
    DESCRIPTION
        "Represents the count of authentication frames received."
    ::= { unisDot11BSSRxStatisEntry 10 }

unisDot11BSSRxFrameErrCntCM OBJECT-TYPE
    SYNTAX      Counter32
    MAX-ACCESS  read-only
    STATUS      current
    DESCRIPTION
        "Represents the count of error authentication frames received."
    ::= { unisDot11BSSRxStatisEntry 11 }

-- *****************************************************************************
-- *  End of unisDot11BSSRxStatisTable Definition
-- *****************************************************************************

-- *****************************************************************************
-- *  unisDot11BSSTxStatisTable Definition
-- *****************************************************************************
unisDot11BSSTxStatisTable OBJECT-TYPE
    SYNTAX      SEQUENCE OF UnisDot11BSSTxStatisEntry
    MAX-ACCESS  not-accessible
    STATUS      current
    DESCRIPTION
        "The table will provide the transmission statistic for a
        specific BSS on a radio."
    ::= { unisDot11APStatisGroup 5 }

unisDot11BSSTxStatisEntry OBJECT-TYPE
    SYNTAX      UnisDot11BSSTxStatisEntry
    MAX-ACCESS  not-accessible
    STATUS      current
    DESCRIPTION
        "Each entry of the table will provide the statistic data for
        each BSS on a specific radio."
    INDEX
        {
            unisDot11CurAPID,
            unisDot11RadioID,
            unisDot11WlanID
        }
    ::= { unisDot11BSSTxStatisTable 1 }

UnisDot11BSSTxStatisEntry ::= SEQUENCE
    {
        unisDot11BSSTxFrameCnt             Counter32,
        unisDot11BSSTxFrameBytes           Counter32,
        unisDot11BSSTxDataFrameCnt         Counter32,
        unisDot11BSSTxDataFrameBytes       Counter32,
        unisDot11BSSTxAssociateFrameCnt    Counter32,
        unisDot11BSSTxPayloadBytes         Counter32,
        unisDot11BSSTxRetryCnt             Counter32,
        unisDot11BSSTxUniFrameCnt          Counter32,
        unisDot11BSSTxNonUniFrameCnt       Integer32,
        unisDot11BSSTxAuthenFrameCnt       Counter32,
        unisDot11BSSTxFrameErrCntCM        Counter32
    }

unisDot11BSSTxFrameCnt OBJECT-TYPE
    SYNTAX      Counter32
    MAX-ACCESS  read-only
    STATUS      current
    DESCRIPTION
        "Represents the total number of frames transmission with this BSS."
    ::= { unisDot11BSSTxStatisEntry 1 }

unisDot11BSSTxFrameBytes OBJECT-TYPE
    SYNTAX      Counter32
    MAX-ACCESS  read-only
    STATUS      current
    DESCRIPTION
        "Represents the total number of bytes transmission with this BSS."
    ::= { unisDot11BSSTxStatisEntry 2 }

unisDot11BSSTxDataFrameCnt OBJECT-TYPE
    SYNTAX      Counter32
    MAX-ACCESS  read-only
    STATUS      current
    DESCRIPTION
        "Represents the number of data frame transmission with this BSS."
    ::= { unisDot11BSSTxStatisEntry 3 }

unisDot11BSSTxDataFrameBytes OBJECT-TYPE
    SYNTAX      Counter32
    MAX-ACCESS  read-only
    STATUS      current
    DESCRIPTION
        "Represents the bytes of data frame transmission with this BSS."
    ::= { unisDot11BSSTxStatisEntry 4 }

unisDot11BSSTxAssociateFrameCnt OBJECT-TYPE
    SYNTAX      Counter32
    MAX-ACCESS  read-only
    STATUS      current
    DESCRIPTION
        "Represents the number of associate frame transmission with this BSS."
    ::= { unisDot11BSSTxStatisEntry 5 }

unisDot11BSSTxPayloadBytes OBJECT-TYPE
    SYNTAX      Counter32
    MAX-ACCESS  read-only
    STATUS      current
    DESCRIPTION
        "Represents the payload bytes of data frame transmission with this BSS."
    ::= { unisDot11BSSTxStatisEntry 6 }

unisDot11BSSTxRetryCnt   OBJECT-TYPE
    SYNTAX      Counter32
    MAX-ACCESS  read-only
    STATUS      current
    DESCRIPTION
        "Represents the count of bytes retransmitted with this BSS."
    ::= { unisDot11BSSTxStatisEntry 7 }

unisDot11BSSTxUniFrameCnt OBJECT-TYPE
    SYNTAX      Counter32
    MAX-ACCESS  read-only
    STATUS      current
    DESCRIPTION
        "Represents the count of unicast frames transmission with this BSS."
    ::= { unisDot11BSSTxStatisEntry 8 }

unisDot11BSSTxNonUniFrameCnt OBJECT-TYPE
    SYNTAX      Integer32
    MAX-ACCESS  read-only
    STATUS      current
    DESCRIPTION
        "Represents the number of non-unicast frames transmission with this BSS."
    ::= { unisDot11BSSTxStatisEntry 9 }

unisDot11BSSTxAuthenFrameCnt OBJECT-TYPE
    SYNTAX      Counter32
    MAX-ACCESS  read-only
    STATUS      current
    DESCRIPTION
        "Represents the count of authentication frames transmission with this BSS."
    ::= { unisDot11BSSTxStatisEntry 10 }

unisDot11BSSTxFrameErrCntCM OBJECT-TYPE
    SYNTAX      Counter32
    MAX-ACCESS  read-only
    STATUS      current
    DESCRIPTION
        "Represents the count of error authentication frames transmission with this BSS."
    ::= { unisDot11BSSTxStatisEntry 11 }

-- *****************************************************************************
-- *  End of unisDot11BSSTxStatisTable Definition
-- *****************************************************************************

-- *****************************************************************************
-- *  unisDot11BSSAssocStatisTable Definition
-- *****************************************************************************
unisDot11BSSAssocStatisTable OBJECT-TYPE
    SYNTAX      SEQUENCE OF UnisDot11BSSAssocStatisEntry
    MAX-ACCESS  not-accessible
    STATUS      current
    DESCRIPTION
        "The table will provide the station association statistic for BSS."
    ::= { unisDot11APStatisGroup 6 }

unisDot11BSSAssocStatisEntry OBJECT-TYPE
    SYNTAX      UnisDot11BSSAssocStatisEntry
    MAX-ACCESS  not-accessible
    STATUS      current
    DESCRIPTION
        "Each entry of the table will provide the statistic data of station
        association for BSS."
    INDEX
        {
            unisDot11CurAPID,
            unisDot11RadioID,
            unisDot11WlanID
        }
    ::= { unisDot11BSSAssocStatisTable 1 }

UnisDot11BSSAssocStatisEntry ::= SEQUENCE
    {
        unisDot11BSSStationAssocSum          Counter32,
        unisDot11BSSStationAssocFailSum      Counter32,
        unisDot11BSSStationReassocSum        Counter32,
        unisDot11BSSStationAssocRejectSum    Counter32,
        unisDot11BSSStationExDeAssocSum      Counter32,
        unisDot11BSSStationCurAssocSum       Integer32,
        unisDot11BSSStationAssocReqSum       Counter32,
        unisDot11BSSStationCurAuthSum        Integer32
    }

unisDot11BSSStationAssocSum OBJECT-TYPE
    SYNTAX      Counter32
    MAX-ACCESS  read-only
    STATUS      current
    DESCRIPTION
        "Represents the total number of station association
        with this BSS."
    ::= { unisDot11BSSAssocStatisEntry 1 }

unisDot11BSSStationAssocFailSum OBJECT-TYPE
    SYNTAX      Counter32
    MAX-ACCESS  read-only
    STATUS      current
    DESCRIPTION
        "Represents the total number of station
        association failure with this BSS."
    ::= { unisDot11BSSAssocStatisEntry 2 }

unisDot11BSSStationReassocSum OBJECT-TYPE
    SYNTAX      Counter32
    MAX-ACCESS  read-only
    STATUS      current
    DESCRIPTION
        "Represents the total number of station reassociation
        with this BSS."
    ::= { unisDot11BSSAssocStatisEntry 3 }

unisDot11BSSStationAssocRejectSum OBJECT-TYPE
    SYNTAX      Counter32
    MAX-ACCESS  read-only
    STATUS      current
    DESCRIPTION
        "Represents the total number of station association rejected
        on account of resource limit with this BSS."
    ::= { unisDot11BSSAssocStatisEntry 4 }

unisDot11BSSStationExDeAssocSum OBJECT-TYPE
    SYNTAX      Counter32
    MAX-ACCESS  read-only
    STATUS      current
    DESCRIPTION
        "Represents the total number of exceptional station deauthentication
        (Without sending a deauthentication to AP) with this BSS."
    ::= { unisDot11BSSAssocStatisEntry 5 }

unisDot11BSSStationCurAssocSum OBJECT-TYPE
    SYNTAX      Integer32
    MAX-ACCESS  read-only
    STATUS      current
    DESCRIPTION
        "Represents the total number of current associated stations
        with this BSS."
    ::= { unisDot11BSSAssocStatisEntry 6 }

unisDot11BSSStationAssocReqSum OBJECT-TYPE
    SYNTAX      Counter32
    MAX-ACCESS  read-only
    STATUS      current
    DESCRIPTION
        "Represents the total number of station association request with
         this BSS."
    ::= { unisDot11BSSAssocStatisEntry 7 }

unisDot11BSSStationCurAuthSum OBJECT-TYPE
    SYNTAX      Integer32
    MAX-ACCESS  read-only
    STATUS      current
    DESCRIPTION
        "Represents the total number of current associated stations which have
        passed portal or 1x authentication with this BSS."
    ::= { unisDot11BSSAssocStatisEntry 8 }

-- *****************************************************************************
-- *  End of unisDot11BSSAssocStatisTable Definition
-- *****************************************************************************

-- *****************************************************************************
-- *  unisDot11APLinkStatisTable Definition
-- *****************************************************************************
unisDot11APLinkStatisTable OBJECT-TYPE
    SYNTAX      SEQUENCE OF UnisDot11APLinkStatisEntry
    MAX-ACCESS  not-accessible
    STATUS      current
    DESCRIPTION
        "The table will provide the link statistic for AP."
    ::= { unisDot11APStatisGroup 7 }

unisDot11APLinkStatisEntry OBJECT-TYPE
    SYNTAX      UnisDot11APLinkStatisEntry
    MAX-ACCESS  not-accessible
    STATUS      current
    DESCRIPTION
        "Each entry provides the link statistic of the AP."
    INDEX
        {
            unisDot11CurAPID
        }
    ::= { unisDot11APLinkStatisTable 1 }

UnisDot11APLinkStatisEntry ::= SEQUENCE
    {
        unisDot11UpLinkUpDownTimes          Counter32,
        unisDot11DownLinkUpDownTimes        Counter32,
        unisDot11PrivateSrvRxFrameBytes     Counter64,
        unisDot11PrivateSrvTxFrameBytes     Counter64,
        unisDot11APInternetAllRxBytes       Counter64,
        unisDot11APInternetAllTxBytes       Counter64,
        unisDot11APLocalAllRxBytes          Counter64,
        unisDot11APLocalAllTxBytes          Counter64
    }

unisDot11UpLinkUpDownTimes OBJECT-TYPE
    SYNTAX      Counter32
    MAX-ACCESS  read-only
    STATUS      current
    DESCRIPTION
        "Represents up/down times of uplink interface of the AP."
    ::= { unisDot11APLinkStatisEntry 1 }

unisDot11DownLinkUpDownTimes OBJECT-TYPE
    SYNTAX      Counter32
    MAX-ACCESS  read-only
    STATUS      current
    DESCRIPTION
        "Represents up/down times of downlink interface of the AP."
    ::= { unisDot11APLinkStatisEntry 2 }

unisDot11PrivateSrvRxFrameBytes OBJECT-TYPE
    SYNTAX      Counter64
    MAX-ACCESS  read-only
    STATUS      current
    DESCRIPTION
        "Traffic bytes received from private services."
    ::= { unisDot11APLinkStatisEntry 3 }

unisDot11PrivateSrvTxFrameBytes OBJECT-TYPE
    SYNTAX      Counter64
    MAX-ACCESS  read-only
    STATUS      current
    DESCRIPTION
        "Traffic bytes sent to private services."
    ::= { unisDot11APLinkStatisEntry 4 }

unisDot11APInternetAllRxBytes OBJECT-TYPE
    SYNTAX      Counter64
    MAX-ACCESS  read-only
    STATUS      current
    DESCRIPTION
        "Internet traffic bytes received from stations."
    ::= { unisDot11APLinkStatisEntry 5 }

unisDot11APInternetAllTxBytes OBJECT-TYPE
    SYNTAX      Counter64
    MAX-ACCESS  read-only
    STATUS      current
    DESCRIPTION
        "Internet traffic bytes sent to stations."
    ::= { unisDot11APLinkStatisEntry 6 }

unisDot11APLocalAllRxBytes OBJECT-TYPE
    SYNTAX      Counter64
    MAX-ACCESS  read-only
    STATUS      current
    DESCRIPTION
        "Local traffic bytes received from stations."
    ::= { unisDot11APLinkStatisEntry 7 }

unisDot11APLocalAllTxBytes OBJECT-TYPE
    SYNTAX      Counter64
    MAX-ACCESS  read-only
    STATUS      current
    DESCRIPTION
        "Local traffic bytes sent to stations."
    ::= { unisDot11APLinkStatisEntry 8 }
-- *****************************************************************************
-- *  End of unisDot11APLinkStatisTable Definition
-- *****************************************************************************

-- *****************************************************************************
-- *  unisDot11RadioAssocStatisTable Definition
-- *****************************************************************************
unisDot11RadioAssocStatisTable OBJECT-TYPE
    SYNTAX      SEQUENCE OF UnisDot11RadioAssocStatisEntry
    MAX-ACCESS  not-accessible
    STATUS      current
    DESCRIPTION
        "The table will provide the station association statistic for radio."
    ::= { unisDot11APStatisGroup 8 }

unisDot11RadioAssocStatisEntry OBJECT-TYPE
    SYNTAX      UnisDot11RadioAssocStatisEntry
    MAX-ACCESS  not-accessible
    STATUS      current
    DESCRIPTION
        "Each entry of the table will provide the statistic data of station
        association for radio."
    INDEX
        {
            unisDot11CurAPID,
            unisDot11RadioID
        }
    ::= { unisDot11RadioAssocStatisTable 1 }

UnisDot11RadioAssocStatisEntry ::= SEQUENCE
    {
        unisDot11RadioStaAssocSum          Counter32,
        unisDot11RadioStaAssocFailSum      Counter32,
        unisDot11RadioStaReassocSum        Counter32,
        unisDot11RadioStaAssocRejectSum    Counter32,
        unisDot11RadioStaExDeAssocSum      Counter32,
        unisDot11RadioStaCurAssocSum       Integer32
    }

unisDot11RadioStaAssocSum OBJECT-TYPE
    SYNTAX      Counter32
    MAX-ACCESS  read-only
    STATUS      current
    DESCRIPTION
        "Represents the total number of station association
        with this radio."
    ::= { unisDot11RadioAssocStatisEntry 1 }

unisDot11RadioStaAssocFailSum OBJECT-TYPE
    SYNTAX      Counter32
    MAX-ACCESS  read-only
    STATUS      current
    DESCRIPTION
        "Represents the total number of station
        association failure with this radio."
    ::= { unisDot11RadioAssocStatisEntry 2 }

unisDot11RadioStaReassocSum OBJECT-TYPE
    SYNTAX      Counter32
    MAX-ACCESS  read-only
    STATUS      current
    DESCRIPTION
        "Represents the total number of station re-association
        with this radio."
    ::= { unisDot11RadioAssocStatisEntry 3 }

unisDot11RadioStaAssocRejectSum OBJECT-TYPE
    SYNTAX      Counter32
    MAX-ACCESS  read-only
    STATUS      current
    DESCRIPTION
        "Represents the total number of station association rejected
        on account of resource limit with this radio."
    ::= { unisDot11RadioAssocStatisEntry 4 }

unisDot11RadioStaExDeAssocSum OBJECT-TYPE
    SYNTAX      Counter32
    MAX-ACCESS  read-only
    STATUS      current
    DESCRIPTION
        "Represents the total number of exceptional station de-authentication
        (Without sending a de-authentication to AP) with this radio."
    ::= { unisDot11RadioAssocStatisEntry 5 }

unisDot11RadioStaCurAssocSum OBJECT-TYPE
    SYNTAX      Integer32
    MAX-ACCESS  read-only
    STATUS      current
    DESCRIPTION
        "Represents the total number of current associated stations
        with this radio."
    ::= { unisDot11RadioAssocStatisEntry 6 }
-- *****************************************************************************
-- *  End of unisDot11RadioAssocStatisTable Definition
-- *****************************************************************************

-- *****************************************************************************
-- *  unisDot11RadioMngFrameStatisTable Definition
-- *****************************************************************************
unisDot11RadioMngFrameStatisTable OBJECT-TYPE
    SYNTAX      SEQUENCE OF UnisDot11RadioMngFrameStatisEntry
    MAX-ACCESS  not-accessible
    STATUS      current
    DESCRIPTION
        "The table will provide the management frame statistic for this radio."
    ::= { unisDot11APStatisGroup 9 }

unisDot11RadioMngFrameStatisEntry OBJECT-TYPE
    SYNTAX      UnisDot11RadioMngFrameStatisEntry
    MAX-ACCESS  not-accessible
    STATUS      current
    DESCRIPTION
        "Each entry of the table will provide the management
        frame statistic for this radio."
    INDEX
        {
            unisDot11RadioStatisIndex,
            unisDot11MngFrameType
        }
    ::= { unisDot11RadioMngFrameStatisTable 1 }

UnisDot11RadioMngFrameStatisEntry ::= SEQUENCE
    {
        unisDot11RadioStatisIndex            UnisDot11RadioElementIndex,
        unisDot11MngFrameType                INTEGER,
        unisDot11MngFrameCnt                 Counter32
    }

unisDot11RadioStatisIndex OBJECT-TYPE
    SYNTAX      UnisDot11RadioElementIndex
    MAX-ACCESS  not-accessible
    STATUS      current
    DESCRIPTION
        "Represents index of radio."
    ::= { unisDot11RadioMngFrameStatisEntry 1 }

unisDot11MngFrameType   OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { unisDot11RadioMngFrameStatisEntry 2 }

unisDot11MngFrameCnt OBJECT-TYPE
    SYNTAX      Counter32
    MAX-ACCESS  read-only
    STATUS      current
    DESCRIPTION
        "Represents the total number of each type for management frame on this
        radio."
    ::= { unisDot11RadioMngFrameStatisEntry 3 }

-- *****************************************************************************
-- *  End of unisDot11RadioMngFrameStatisTable Definition
-- *****************************************************************************

-- *****************************************************************************
-- *  unisDot11APAuthFailStatisTable Definition
-- *****************************************************************************
unisDot11APAuthFailStatisTable OBJECT-TYPE
    SYNTAX      SEQUENCE OF UnisDot11APAuthFailStatisEntry
    MAX-ACCESS  not-accessible
    STATUS      current
    DESCRIPTION
        "The table will provide the authentication failure statistic for this
         AP."
    ::= { unisDot11APStatisGroup 10 }

unisDot11APAuthFailStatisEntry OBJECT-TYPE
    SYNTAX      UnisDot11APAuthFailStatisEntry
    MAX-ACCESS  not-accessible
    STATUS      current
    DESCRIPTION
        "Each entry of the table will provide the authentication failure
         statistic for this AP."
    INDEX
        {
            unisDot11CurAPID,
            unisDot11APAuthFailStatisType
        }
    ::= { unisDot11APAuthFailStatisTable 1 }

UnisDot11APAuthFailStatisEntry ::= SEQUENCE
    {
        unisDot11APAuthFailStatisType                 INTEGER,
        unisDot11APAuthFailStatisCnt                  Counter32
    }

unisDot11APAuthFailStatisType OBJECT-TYPE
    SYNTAX      INTEGER
        {
            invalidation(1),
            overtime(2),
            rejected(3),
            other(4)
        }
    MAX-ACCESS  not-accessible
    STATUS      current
    DESCRIPTION
        "Represents the type of authentication
        failure with this AP."
    ::= { unisDot11APAuthFailStatisEntry 1 }

unisDot11APAuthFailStatisCnt   OBJECT-TYPE
    SYNTAX      Counter32
    MAX-ACCESS  read-only
    STATUS      current
    DESCRIPTION
        "Represents the total number of each type for authentication
        failure on this AP."
    ::= { unisDot11APAuthFailStatisEntry 2 }

-- *****************************************************************************
-- *  End of unisDot11APAuthFailStatisTable Definition
-- *****************************************************************************

-- *****************************************************************************
-- *  unisDot11APAssocFailStatisTable Definition
-- *****************************************************************************
unisDot11APAssocFailStatisTable OBJECT-TYPE
    SYNTAX      SEQUENCE OF UnisDot11APAssocFailStatisEntry
    MAX-ACCESS  not-accessible
    STATUS      current
    DESCRIPTION
        "The table will provide the association failure statistic for
        this AP."
    ::= { unisDot11APStatisGroup 11 }

unisDot11APAssocFailStatisEntry OBJECT-TYPE
    SYNTAX      UnisDot11APAssocFailStatisEntry
    MAX-ACCESS  not-accessible
    STATUS      current
    DESCRIPTION
        "Each entry of the table will provide the association failure statistic
         for this AP."
    INDEX
        {
            unisDot11CurAPID,
            unisDot11APAssocFailStatisType
        }
    ::= { unisDot11APAssocFailStatisTable 1 }

UnisDot11APAssocFailStatisEntry ::= SEQUENCE
    {
        unisDot11APAssocFailStatisType                 INTEGER,
        unisDot11APAssocFailStatisCnt                  Counter32
    }

unisDot11APAssocFailStatisType OBJECT-TYPE
    SYNTAX      INTEGER
        {
            invalidation(1),
            overtime(2),
            rejected(3),
            other(4)
        }
    MAX-ACCESS  not-accessible
    STATUS      current
    DESCRIPTION
        "Represents the type of association failure
        with this AP."
    ::= { unisDot11APAssocFailStatisEntry 1 }

unisDot11APAssocFailStatisCnt   OBJECT-TYPE
    SYNTAX      Counter32
    MAX-ACCESS  read-only
    STATUS      current
    DESCRIPTION
        "Represents the total number of each type for
        association failure on this AP."
    ::= { unisDot11APAssocFailStatisEntry 2 }

-- *****************************************************************************
-- *  End of unisDot11APAssocFailStatisTable Definition
-- *****************************************************************************

-- *****************************************************************************
-- *  unisDot11APReassocStatisTable Definition
-- *****************************************************************************
unisDot11APReassocStatisTable OBJECT-TYPE
    SYNTAX      SEQUENCE OF UnisDot11APReassocStatisEntry
    MAX-ACCESS  not-accessible
    STATUS      current
    DESCRIPTION
        "The table will provide the re-association statistic for this AP."
    ::= { unisDot11APStatisGroup 12 }

unisDot11APReassocStatisEntry OBJECT-TYPE
    SYNTAX      UnisDot11APReassocStatisEntry
    MAX-ACCESS  not-accessible
    STATUS      current
    DESCRIPTION
        "Each entry of the table will provide the re-association statistic
        for this AP."
    INDEX
        {
            unisDot11CurAPID,
            unisDot11APReassocStatisType
        }
    ::= { unisDot11APReassocStatisTable 1 }

UnisDot11APReassocStatisEntry ::= SEQUENCE
    {
        unisDot11APReassocStatisType                 INTEGER,
        unisDot11APReassocStatisCnt                  Counter32
    }

unisDot11APReassocStatisType OBJECT-TYPE
    SYNTAX      INTEGER
        {
            total(1),
            success(2),
            invalidation(3),
            overtime(4),
            rejected(5),
            other(6)
        }
    MAX-ACCESS  not-accessible
    STATUS      current
    DESCRIPTION
        "Represents the type of re-association with this AP."
    ::= { unisDot11APReassocStatisEntry 1 }

unisDot11APReassocStatisCnt   OBJECT-TYPE
    SYNTAX      Counter32
    MAX-ACCESS  read-only
    STATUS      current
    DESCRIPTION
        "Represents the total number of each type for re-association with
        this AP."
    ::= { unisDot11APReassocStatisEntry 2 }

-- *****************************************************************************
-- *  End of unisDot11APReassocStatisTable Definition
-- *****************************************************************************

-- *****************************************************************************
-- *  unisDot11APUserAuthStatisTable Definition
-- *****************************************************************************
unisDot11APUserAuthStatisTable OBJECT-TYPE
    SYNTAX      SEQUENCE OF UnisDot11APUserAuthStatisEntry
    MAX-ACCESS  not-accessible
    STATUS      current
    DESCRIPTION
        "The table will provide the user authentication statistic for this AP."
    ::= { unisDot11APStatisGroup 13 }

unisDot11APUserAuthStatisEntry OBJECT-TYPE
    SYNTAX      UnisDot11APUserAuthStatisEntry
    MAX-ACCESS  not-accessible
    STATUS      current
    DESCRIPTION
        "Each entry of the table will provide the user authentication statistic
        for this AP."
    INDEX
        {
            unisDot11CurAPID,
            unisDot11UserAuthStatisType
        }
    ::= { unisDot11APUserAuthStatisTable 1 }

UnisDot11APUserAuthStatisEntry ::= SEQUENCE
    {
        unisDot11UserAuthStatisType                 INTEGER,
        unisDot11UserAuthStatisCnt                  Counter32
    }

unisDot11UserAuthStatisType OBJECT-TYPE
    SYNTAX      INTEGER
        {
            total(1),
            success(2),
            keyError(3),
            invalidation(4),
            overtime(5),
            rejected(6),
            other(7)
        }
    MAX-ACCESS  not-accessible
    STATUS      current
    DESCRIPTION
        "Represents the type of user authentication with this AP."
    ::= { unisDot11APUserAuthStatisEntry 1 }

unisDot11UserAuthStatisCnt   OBJECT-TYPE
    SYNTAX      Counter32
    MAX-ACCESS  read-only
    STATUS      current
    DESCRIPTION
        "Represents the total number of each type for user authentication with
        this AP."
    ::= { unisDot11APUserAuthStatisEntry 2 }

-- *****************************************************************************
-- *  End of unisDot11APUserAuthStatisTable Definition
-- *****************************************************************************

-- *****************************************************************************
-- *  unisDot11APDeauthStatisTable Definition
-- *****************************************************************************
unisDot11APDeauthStatisTable OBJECT-TYPE
    SYNTAX      SEQUENCE OF UnisDot11APDeauthStatisEntry
    MAX-ACCESS  not-accessible
    STATUS      current
    DESCRIPTION
        "The table will provide the de-authentication statistic for this AP."
    ::= { unisDot11APStatisGroup 14 }

unisDot11APDeauthStatisEntry OBJECT-TYPE
    SYNTAX      UnisDot11APDeauthStatisEntry
    MAX-ACCESS  not-accessible
    STATUS      current
    DESCRIPTION
        "Each entry of the table will provide the de-authentication statistic
         for this AP."
    INDEX
        {
            unisDot11CurAPID,
            unisDot11APDeauthStatisType
        }
    ::= { unisDot11APDeauthStatisTable 1 }

UnisDot11APDeauthStatisEntry ::= SEQUENCE
    {
        unisDot11APDeauthStatisType                 INTEGER,
        unisDot11APDeauthStatisCnt                  Counter32
    }

unisDot11APDeauthStatisType OBJECT-TYPE
    SYNTAX      INTEGER
        {
            total(1),
            stationLeaving(2),
            shortResource(3),
            exception(4),
            other(5)
        }
    MAX-ACCESS  not-accessible
    STATUS      current
    DESCRIPTION
        "Represents the type of de-authentication for this AP."
    ::= { unisDot11APDeauthStatisEntry 1 }

unisDot11APDeauthStatisCnt   OBJECT-TYPE
    SYNTAX      Counter32
    MAX-ACCESS  read-only
    STATUS      current
    DESCRIPTION
        "Represents the total number of each type for de-authentication
         with this AP."
    ::= { unisDot11APDeauthStatisEntry 2 }

-- *****************************************************************************
-- *  End of unisDot11APDeauthStatisTable Definition
-- *****************************************************************************

-- *****************************************************************************
-- *  unisDot11APDeassocStatisTable Definition
-- *****************************************************************************
unisDot11APDeassocStatisTable OBJECT-TYPE
    SYNTAX      SEQUENCE OF UnisDot11APDeassocStatisEntry
    MAX-ACCESS  not-accessible
    STATUS      current
    DESCRIPTION
        "The table will provide the de-association statistic for this AP."
    ::= { unisDot11APStatisGroup 15 }

unisDot11APDeassocStatisEntry OBJECT-TYPE
    SYNTAX      UnisDot11APDeassocStatisEntry
    MAX-ACCESS  not-accessible
    STATUS      current
    DESCRIPTION
        "Each entry of the table will provide the de-association statistic
         for this AP."
    INDEX
        {
            unisDot11CurAPID,
            unisDot11APDeassocStatisType
        }
    ::= { unisDot11APDeassocStatisTable 1 }

UnisDot11APDeassocStatisEntry ::= SEQUENCE
    {
        unisDot11APDeassocStatisType                 INTEGER,
        unisDot11APDeassocStatisCnt                  Counter32
    }

unisDot11APDeassocStatisType OBJECT-TYPE
    SYNTAX      INTEGER
        {
            total(1),
            stationLeaving(2),
            shortResource(3),
            exception(4),
            other(5)
        }
    MAX-ACCESS  not-accessible
    STATUS      current
    DESCRIPTION
        "Represents the type of de-association with this AP."
    ::= { unisDot11APDeassocStatisEntry 1 }

unisDot11APDeassocStatisCnt   OBJECT-TYPE
    SYNTAX      Counter32
    MAX-ACCESS  read-only
    STATUS      current
    DESCRIPTION
        "Represents the total number of each type for de-association
         with this AP."
    ::= { unisDot11APDeassocStatisEntry 2 }

-- *****************************************************************************
-- *  End of unisDot11APDeassocStatisTable Definition
-- *****************************************************************************
-- *****************************************************************************
-- *  unisDot11APAssocFailStatis2Table Definition
-- *****************************************************************************
unisDot11APAssocFailStatis2Table OBJECT-TYPE
    SYNTAX      SEQUENCE OF UnisDot11APAssocFailStatis2Entry
    MAX-ACCESS  not-accessible
    STATUS      current
    DESCRIPTION
        "This table will provide statistic of association fails for each ap."
    ::= { unisDot11APStatisGroup 16 }

unisDot11APAssocFailStatis2Entry OBJECT-TYPE
    SYNTAX      UnisDot11APAssocFailStatis2Entry
    MAX-ACCESS  not-accessible
    STATUS      current
    DESCRIPTION
        "Each entry will provide statistic of association fails for this ap."
    INDEX
        {
            unisDot11CurAPID,
            unisDot11APAssocFailStatis2Type
        }
    ::= { unisDot11APAssocFailStatis2Table 1 }

UnisDot11APAssocFailStatis2Entry ::= SEQUENCE
    {
        unisDot11APAssocFailStatis2Type                 INTEGER,
        unisDot11APAssocFailStatis2Cnt                  Counter32
    }

unisDot11APAssocFailStatis2Type OBJECT-TYPE
    SYNTAX      INTEGER
        {
            shortResource(1),
            notSupportRateSet(2),
            unknownReasonCode(3),
            other(4),
            rssiLowness(5)
        }
    MAX-ACCESS  not-accessible
    STATUS      current
    DESCRIPTION
        "Represents the type of association fails for this AP"
    ::= { unisDot11APAssocFailStatis2Entry 1 }

unisDot11APAssocFailStatis2Cnt   OBJECT-TYPE
    SYNTAX      Counter32
    MAX-ACCESS  read-only
    STATUS      current
    DESCRIPTION
        "Represents the total count of association fails for this AP."
    ::= { unisDot11APAssocFailStatis2Entry 2 }

-- *****************************************************************************
-- *  End of unisDot11APAssocFailStatis2Table Definition
-- *****************************************************************************
-- *****************************************************************************
-- *  unisDot11APIfStatisTable Definition
-- *****************************************************************************
unisDot11APIfStatisTable OBJECT-TYPE
    SYNTAX      SEQUENCE OF UnisDot11APIfStatisEntry
    MAX-ACCESS  not-accessible
    STATUS      current
    DESCRIPTION
        "The table will provide the statistics on the interface of the AP."
    ::= { unisDot11APStatisGroup 17 }

unisDot11APIfStatisEntry OBJECT-TYPE
    SYNTAX      UnisDot11APIfStatisEntry
    MAX-ACCESS  not-accessible
    STATUS      current
    DESCRIPTION
        "Each entry of the table will provide statistics on the interface of the AP."
    INDEX
        {
            unisDot11APElementIndex,
            unisDot11APIfIndex
        }
    ::= { unisDot11APIfStatisTable 1 }

UnisDot11APIfStatisEntry ::= SEQUENCE
    {
        unisDot11APIfInPkts              Counter32,
        unisDot11APIfInNormalPkts        Counter32,
        unisDot11APIfInErrorPkts         Counter32,
        unisDot11APIfOutPkts             Counter32,
        unisDot11APIfInOctets            Counter32,
        unisDot11APIfOutOctets           Counter32,
        unisDot11APIfFlowOut             Unsigned32,
        unisDot11APIfFlowIN              Unsigned32,
        unisDot11APIfInUcastPkts         Counter32,
        unisDot11APIfInNUcastPkts        Counter32,
        unisDot11APIfInDiscardPkts       Counter32,
        unisDot11APIfOutUcastPkts        Counter32,
        unisDot11APIfOutNUcastPkts       Counter32,
        unisDot11APIfOutDiscardPkts      Counter32,
        unisDot11APIfOutErrorPkts        Counter32,
        unisDot11APIfUpdownTimes         Counter32,
        unisDot11APIfStatusKeepTime      TimeTicks,
        unisDot11APIfOperStatus          INTEGER,
        unisDot11APIfInBrdcastPkts       Counter64,
        unisDot11APIfOutBrdcastPkts      Counter64,
        unisDot11APIfInMulcastPkts       Counter64,
        unisDot11APIfOutMulcastPkts      Counter64,
        unisDot11APIfInPayloadOctets     Counter64,
        unisDot11APIfOutPayloadOctets    Counter64
    }

unisDot11APIfInPkts OBJECT-TYPE
    SYNTAX      Counter32
    MAX-ACCESS  read-only
    STATUS      current
    DESCRIPTION
        "Represents the total number of packets received
         on the interface."
    ::= { unisDot11APIfStatisEntry 1 }

unisDot11APIfInNormalPkts OBJECT-TYPE
    SYNTAX      Counter32
    MAX-ACCESS  read-only
    STATUS      current
    DESCRIPTION
        "Represents the total number of correct
         packets received on the interface."
    ::= { unisDot11APIfStatisEntry 2 }

unisDot11APIfInErrorPkts OBJECT-TYPE
    SYNTAX      Counter32
    MAX-ACCESS  read-only
    STATUS      current
    DESCRIPTION
        "Represents the total number of error
         packets received on the interface."
    ::= { unisDot11APIfStatisEntry 3 }

unisDot11APIfOutPkts OBJECT-TYPE
    SYNTAX      Counter32
    MAX-ACCESS  read-only
    STATUS      current
    DESCRIPTION
        "Represents the total number of packets
         sent from the interface."
    ::= { unisDot11APIfStatisEntry 4 }

unisDot11APIfInOctets OBJECT-TYPE
    SYNTAX      Counter32
    MAX-ACCESS  read-only
    STATUS      current
    DESCRIPTION
        "Represents the total number of octets
         received on the interface."
    ::= { unisDot11APIfStatisEntry 5 }

unisDot11APIfOutOctets OBJECT-TYPE
    SYNTAX      Counter32
    MAX-ACCESS  read-only
    STATUS      current
    DESCRIPTION
        "Represents the total number of octets
         sent from the interface."
    ::= { unisDot11APIfStatisEntry 6 }

unisDot11APIfFlowOut OBJECT-TYPE
    SYNTAX      Unsigned32
    MAX-ACCESS  read-only
    STATUS      current
    DESCRIPTION
        "Represents the traffic rate (byte/s) on the uplink interface
         during a sampling period."
    ::= { unisDot11APIfStatisEntry 7 }

unisDot11APIfFlowIN OBJECT-TYPE
    SYNTAX      Unsigned32
    MAX-ACCESS  read-only
    STATUS      current
    DESCRIPTION
        "Represents the traffic rate (byte/s) on the downlink interface
         during a sampling period."
    ::= { unisDot11APIfStatisEntry 8 }

unisDot11APIfInUcastPkts OBJECT-TYPE
    SYNTAX      Counter32
    MAX-ACCESS  read-only
    STATUS      current
    DESCRIPTION
        "Represents the number of unicast packets received on the interface."
    ::= { unisDot11APIfStatisEntry 9 }

unisDot11APIfInNUcastPkts OBJECT-TYPE
    SYNTAX      Counter32
    MAX-ACCESS  read-only
    STATUS      current
    DESCRIPTION
        "Represents the number of non-unicast packets received on the wired
         interface."
    ::= { unisDot11APIfStatisEntry 10 }

unisDot11APIfInDiscardPkts OBJECT-TYPE
    SYNTAX      Counter32
    MAX-ACCESS  read-only
    STATUS      current
    DESCRIPTION
        "Represents the number of unicast packets discarded on the interface."
    ::= { unisDot11APIfStatisEntry 11 }

unisDot11APIfOutUcastPkts OBJECT-TYPE
    SYNTAX      Counter32
    MAX-ACCESS  read-only
    STATUS      current
    DESCRIPTION
        "Represents the number of unicast packets send on the interface."
    ::= { unisDot11APIfStatisEntry 12 }

unisDot11APIfOutNUcastPkts OBJECT-TYPE
    SYNTAX      Counter32
    MAX-ACCESS  read-only
    STATUS      current
    DESCRIPTION
        "Represents the number of non-unicast packets send on the interface."
    ::= { unisDot11APIfStatisEntry 13 }

unisDot11APIfOutDiscardPkts OBJECT-TYPE
    SYNTAX      Counter32
    MAX-ACCESS  read-only
    STATUS      current
    DESCRIPTION
        "Represents the number of discarded packets send on the interface."
    ::= { unisDot11APIfStatisEntry 14 }

unisDot11APIfOutErrorPkts OBJECT-TYPE
    SYNTAX      Counter32
    MAX-ACCESS  read-only
    STATUS      current
    DESCRIPTION
        "Represents the number of error packets send on the interface."
    ::= { unisDot11APIfStatisEntry 15 }

unisDot11APIfUpdownTimes OBJECT-TYPE
    SYNTAX      Counter32
    MAX-ACCESS  read-only
    STATUS      current
    DESCRIPTION
        "Represents the up/down times on the interface."
    ::= { unisDot11APIfStatisEntry 16 }

unisDot11APIfStatusKeepTime OBJECT-TYPE
    SYNTAX      TimeTicks
    MAX-ACCESS  read-only
    STATUS      current
    DESCRIPTION
        "Represents the last change time on the interface."
    ::= { unisDot11APIfStatisEntry 17 }

unisDot11APIfOperStatus OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { unisDot11APIfStatisEntry 18 }

unisDot11APIfInBrdcastPkts OBJECT-TYPE
    SYNTAX      Counter64
    MAX-ACCESS  read-only
    STATUS      current
    DESCRIPTION
        "Represents the number of broadcast packets received on the interface."
    ::= { unisDot11APIfStatisEntry 19 }

unisDot11APIfOutBrdcastPkts OBJECT-TYPE
    SYNTAX      Counter64
    MAX-ACCESS  read-only
    STATUS      current
    DESCRIPTION
        "Represents the number of broadcast packets sent on the interface."
    ::= { unisDot11APIfStatisEntry 20 }

unisDot11APIfInMulcastPkts OBJECT-TYPE
    SYNTAX      Counter64
    MAX-ACCESS  read-only
    STATUS      current
    DESCRIPTION
        "Represents the number of multicast packets received on the interface."
    ::= { unisDot11APIfStatisEntry 21 }

unisDot11APIfOutMulcastPkts OBJECT-TYPE
    SYNTAX      Counter64
    MAX-ACCESS  read-only
    STATUS      current
    DESCRIPTION
        "Represents the number of multicast packets sent on the interface."
    ::= { unisDot11APIfStatisEntry 22 }

unisDot11APIfInPayloadOctets OBJECT-TYPE
    SYNTAX      Counter64
    MAX-ACCESS  read-only
    STATUS      current
    DESCRIPTION
        "Represents the number of actual octets received on the interface."
    ::= { unisDot11APIfStatisEntry 23 }

unisDot11APIfOutPayloadOctets OBJECT-TYPE
    SYNTAX      Counter64
    MAX-ACCESS  read-only
    STATUS      current
    DESCRIPTION
        "Represents the number of actual octets sent on the interface."
    ::= { unisDot11APIfStatisEntry 24 }

-- *****************************************************************************
-- *  End of unisDot11APIfStatisTable Definition
-- *****************************************************************************

-- *****************************************************************************
-- *  unisDot11RadioMngFrmStatisTable Definition
-- *****************************************************************************
unisDot11RadioMngFrmStatisTable OBJECT-TYPE
    SYNTAX      SEQUENCE OF UnisDot11RadioMngFrmStatisEntry
    MAX-ACCESS  not-accessible
    STATUS      current
    DESCRIPTION
        "The table will provide the management frame statistic of this radio."
    ::= { unisDot11APStatisGroup 18 }

unisDot11RadioMngFrmStatisEntry OBJECT-TYPE
    SYNTAX      UnisDot11RadioMngFrmStatisEntry
    MAX-ACCESS  not-accessible
    STATUS      current
    DESCRIPTION
        "Each entry of the table will provide the management
         frame statistic of this radio."
    INDEX
        {
            unisDot11CurAPID,
            unisDot11RadioID,
            unisDot11MngFrmType
        }
    ::= { unisDot11RadioMngFrmStatisTable 1 }

UnisDot11RadioMngFrmStatisEntry ::= SEQUENCE
    {
        unisDot11MngFrmType                 INTEGER,
        unisDot11MngFrmCnt                  Counter32
    }

unisDot11MngFrmType  OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { unisDot11RadioMngFrmStatisEntry 1 }

unisDot11MngFrmCnt  OBJECT-TYPE
    SYNTAX      Counter32
    MAX-ACCESS  read-only
    STATUS      current
    DESCRIPTION
        "Represents the total number of each type of management frame on this
         radio."
    ::= { unisDot11RadioMngFrmStatisEntry 2 }
-- *****************************************************************************
-- *  End of unisDot11RadioMngFrmStatisTable Definition
-- *****************************************************************************


-- *****************************************************************************
-- *  unisDot11APPacketSizeStatisTable Definition
-- *****************************************************************************
unisDot11APPacketSizeStatisTable  OBJECT-TYPE
        SYNTAX        SEQUENCE OF UnisDot11APPacketSizeStatisEntry
        MAX-ACCESS    not-accessible
        STATUS        current
        DESCRIPTION
                "This table provides packets statistic base on size."
        ::= { unisDot11APStatisGroup 19 }

unisDot11APPacketSizeStatisEntry  OBJECT-TYPE
        SYNTAX        UnisDot11APPacketSizeStatisEntry
        MAX-ACCESS    not-accessible
        STATUS        current
        DESCRIPTION
                "Each entry provides packets statistic base on size for each radio
                 of a specific AP."
        INDEX
            {
                unisDot11CurAPID,
                unisDot11RadioID,
                unisDot11APPacketSize
            }
        ::= { unisDot11APPacketSizeStatisTable 1 }

UnisDot11APPacketSizeStatisEntry    ::=SEQUENCE
        {
            unisDot11APPacketSize          INTEGER,
            unisDot11APRXPacketSizeCount   Counter64,
            unisDot11APTXPacketSizeCount   Counter64
        }

unisDot11APPacketSize    OBJECT-TYPE
        SYNTAX    INTEGER
            {
                sizeLevel1(1),
                sizeLevel2(2),
                sizeLevel3(3),
                sizeLevel4(4)
            }
        MAX-ACCESS    not-accessible
        STATUS        current
        DESCRIPTION
            "This node represents packet size:
                    sizeLevel1 : size <= 128
                    sizeLevel2 : 128 < size <= 512
                    sizeLevel3 : 512 < size <= 1024
                    sizeLevel4 : size > 1024"
    ::= { unisDot11APPacketSizeStatisEntry 1 }

unisDot11APRXPacketSizeCount    OBJECT-TYPE
        SYNTAX        Counter64
        MAX-ACCESS    read-only
        STATUS        current
        DESCRIPTION
                "Represents the count of packets reception base on frame size."
    ::= { unisDot11APPacketSizeStatisEntry 2 }

unisDot11APTXPacketSizeCount    OBJECT-TYPE
        SYNTAX        Counter64
        MAX-ACCESS    read-only
        STATUS        current
        DESCRIPTION
                "Represents the count of packets transmission base on frame size."
    ::= { unisDot11APPacketSizeStatisEntry 3 }
-- *****************************************************************************
-- *  End of unisDot11APPacketSizeStatisTable Definition
-- *****************************************************************************

-- *****************************************************************************
-- *  unisDot11APPacketRateStatisTable Definition
-- *****************************************************************************
unisDot11APPacketRateStatisTable  OBJECT-TYPE
        SYNTAX        SEQUENCE OF UnisDot11APPacketRateStatisEntry
        MAX-ACCESS    not-accessible
        STATUS        current
        DESCRIPTION
                "This table provides packets statistic base on rate."
        ::= { unisDot11APStatisGroup 20 }

unisDot11APPacketRateStatisEntry  OBJECT-TYPE
        SYNTAX        UnisDot11APPacketRateStatisEntry
        MAX-ACCESS    not-accessible
        STATUS        current
        DESCRIPTION
                "Each entry provides packets statistic base on rate for each radio
                 of a specific AP."
        INDEX
            {
                unisDot11CurAPID,
                unisDot11RadioID,
                unisDot11APPacketRate
            }
        ::= { unisDot11APPacketRateStatisTable 1 }

UnisDot11APPacketRateStatisEntry    ::=SEQUENCE
        {
                unisDot11APPacketRate          Integer32,
                unisDot11APRXPacketRateCount   Counter64,
                unisDot11APTXPacketRateCount   Counter64
        }

unisDot11APPacketRate    OBJECT-TYPE
        SYNTAX        Integer32
        MAX-ACCESS    not-accessible
        STATUS        current
        DESCRIPTION
                "Represents transmit data rate(twice as actual rate)."
    ::= { unisDot11APPacketRateStatisEntry 1 }

unisDot11APRXPacketRateCount    OBJECT-TYPE
        SYNTAX        Counter64
        MAX-ACCESS    read-only
        STATUS        current
        DESCRIPTION
                "Represents the count of packets reception base on transmit data rate."
    ::= { unisDot11APPacketRateStatisEntry 2 }

unisDot11APTXPacketRateCount    OBJECT-TYPE
        SYNTAX        Counter64
        MAX-ACCESS    read-only
        STATUS        current
        DESCRIPTION
                "Represents the count of packets transmission base on transmit data rate."
    ::= { unisDot11APPacketRateStatisEntry 3 }

-- *****************************************************************************
-- *  End of unisDot11APPacketRateStatisTable Definition
-- *****************************************************************************

-- *****************************************************************************
-- *  unisDot11APPacketMCSRateStatisTable Definition
-- *****************************************************************************
unisDot11APPacketMCSRateStatisTable  OBJECT-TYPE
        SYNTAX        SEQUENCE OF UnisDot11APPacketMCSRateStatisEntry
        MAX-ACCESS    not-accessible
        STATUS        current
        DESCRIPTION
                "This table provides packets statistic base on MCS rate."
        ::= { unisDot11APStatisGroup 21 }

unisDot11APPacketMCSRateStatisEntry  OBJECT-TYPE
        SYNTAX        UnisDot11APPacketMCSRateStatisEntry
        MAX-ACCESS    not-accessible
        STATUS        current
        DESCRIPTION
                "Each entry provides packets statistic base on MCS rate for each radio
                 of a specific AP."
        INDEX
            {
                unisDot11CurAPID,
                unisDot11RadioID,
                unisDot11APPacketMCSRate
            }
        ::= { unisDot11APPacketMCSRateStatisTable 1 }

UnisDot11APPacketMCSRateStatisEntry  ::=SEQUENCE
        {
            unisDot11APPacketMCSRate          Integer32,
            unisDot11APRXPacketMCSRateCount   Counter64,
            unisDot11APTXPacketMCSRateCount   Counter64
        }

unisDot11APPacketMCSRate    OBJECT-TYPE
        SYNTAX        Integer32
        MAX-ACCESS    not-accessible
        STATUS        current
        DESCRIPTION
            "Represents transmit data rate(twice as actual rate)."
    ::= { unisDot11APPacketMCSRateStatisEntry 1 }

unisDot11APRXPacketMCSRateCount    OBJECT-TYPE
        SYNTAX        Counter64
        MAX-ACCESS    read-only
        STATUS        current
        DESCRIPTION
            "Represents the count of packets reception base on transmit data rate."
    ::= { unisDot11APPacketMCSRateStatisEntry 2 }

unisDot11APTXPacketMCSRateCount    OBJECT-TYPE
        SYNTAX        Counter64
        MAX-ACCESS    read-only
        STATUS        current
        DESCRIPTION
            "Represents the count of packets transmission base on transmit
             data rate."
    ::= { unisDot11APPacketMCSRateStatisEntry 3 }

-- *****************************************************************************
-- *  End of unisDot11APPacketMcsRateStatisTable Definition
-- *****************************************************************************

-- *****************************************************************************
-- *  unisDot11APAssocFailStatis3Table Definition
-- *****************************************************************************
unisDot11APAssocFailStatis3Table OBJECT-TYPE
    SYNTAX      SEQUENCE OF UnisDot11APAssocFailStatis3Entry
    MAX-ACCESS  not-accessible
    STATUS      current
    DESCRIPTION
        "This table will provide statistic of association fails for each AP."
    ::= { unisDot11APStatisGroup 22 }

unisDot11APAssocFailStatis3Entry OBJECT-TYPE
    SYNTAX      UnisDot11APAssocFailStatis3Entry
    MAX-ACCESS  not-accessible
    STATUS      current
    DESCRIPTION
        "Each entry will provide statistic of association failure with this AP
         because of different reasons."
    INDEX
        {
            unisDot11CurAPID
       }
    ::= { unisDot11APAssocFailStatis3Table 1 }

UnisDot11APAssocFailStatis3Entry ::= SEQUENCE
    {
        unisDot11APAssocFailStatis3SRCnt                 Counter32,
        unisDot11APAssocFailStatis3NSRCnt                Counter32,
        unisDot11APAssocFailStatis3URCCnt                Counter32,
        unisDot11APAssocFailStatis3RFCnt                 Counter32,
        unisDot11APAssocFailStatis3OtherCnt              Counter32,
        unisDot11APAssocFailStatis3RSSILowCntCM          Counter32
    }

unisDot11APAssocFailStatis3SRCnt OBJECT-TYPE
    SYNTAX      Counter32
    MAX-ACCESS  read-only
    STATUS      current
    DESCRIPTION
        "This object represents the count of association failure because of
         lack of resource."
    ::= { unisDot11APAssocFailStatis3Entry 1 }

unisDot11APAssocFailStatis3NSRCnt OBJECT-TYPE
    SYNTAX      Counter32
    MAX-ACCESS  read-only
    STATUS      current
    DESCRIPTION
        "This object represents the count of association failure because of
         not support rate set."
    ::= { unisDot11APAssocFailStatis3Entry 2 }

unisDot11APAssocFailStatis3URCCnt OBJECT-TYPE
    SYNTAX      Counter32
    MAX-ACCESS  read-only
    STATUS      current
    DESCRIPTION
        "This object represents the count of association failure because of
         unknown reason code."
    ::= { unisDot11APAssocFailStatis3Entry 3 }

unisDot11APAssocFailStatis3RFCnt OBJECT-TYPE
    SYNTAX      Counter32
    MAX-ACCESS  read-only
    STATUS      current
    DESCRIPTION
        "This object represents the count of association failure because of
         re-associate failed."
    ::= { unisDot11APAssocFailStatis3Entry 4 }

unisDot11APAssocFailStatis3OtherCnt OBJECT-TYPE
    SYNTAX      Counter32
    MAX-ACCESS  read-only
    STATUS      current
    DESCRIPTION
        "This object represents the count of association fails because of
         reason not in 802.11 the protocol."
    ::= { unisDot11APAssocFailStatis3Entry 5 }

unisDot11APAssocFailStatis3RSSILowCntCM OBJECT-TYPE
    SYNTAX      Counter32
    MAX-ACCESS  read-only
    STATUS      current
    DESCRIPTION
        "Represents the count of failed associations due to low RSSI."
    ::= { unisDot11APAssocFailStatis3Entry 6 }

-- *****************************************************************************
-- *  End of unisDot11APAssocFailStatis3Table Definition
-- *****************************************************************************

-- *****************************************************************************
-- *  unisDot11APIfStatisByAPIDTable Definition
-- *****************************************************************************
unisDot11APIfStatisByAPIDTable OBJECT-TYPE
    SYNTAX      SEQUENCE OF UnisDot11APIfStatisByAPIDEntry
    MAX-ACCESS  not-accessible
    STATUS      current
    DESCRIPTION
        "The table will provide the statistics on the interface of the AP."
    ::= { unisDot11APStatisGroup 23 }

unisDot11APIfStatisByAPIDEntry OBJECT-TYPE
    SYNTAX      UnisDot11APIfStatisByAPIDEntry
    MAX-ACCESS  not-accessible
    STATUS      current
    DESCRIPTION
        "Each entry of the table will provide statistics on the interface of the AP."
    INDEX
        {
            unisDot11CurAPID,
            unisDot11APIfIndex
        }
    ::= { unisDot11APIfStatisByAPIDTable 1 }

UnisDot11APIfStatisByAPIDEntry ::= SEQUENCE
    {
        unisDot11APIfInPkts2              Counter64,
        unisDot11APIfInNormalPkts2        Counter64,
        unisDot11APIfInErrorPkts2         Counter64,
        unisDot11APIfOutPkts2             Counter64,
        unisDot11APIfInOctets2            Counter64,
        unisDot11APIfOutOctets2           Counter64,
        unisDot11APIfFlowOut2             Unsigned32,
        unisDot11APIfFlowIN2              Unsigned32,
        unisDot11APIfInUcastPkts2         Counter64,
        unisDot11APIfInNUcastPkts2        Counter64,
        unisDot11APIfInDiscardPkts2       Counter64,
        unisDot11APIfOutUcastPkts2        Counter64,
        unisDot11APIfOutNUcastPkts2       Counter64,
        unisDot11APIfOutDiscardPkts2      Counter64,
        unisDot11APIfOutErrorPkts2        Counter64,
        unisDot11APIfUpdownTimes2         Counter32,
        unisDot11APIfStatusKeepTime2      TimeTicks,
        unisDot11APIfOperStatus2          INTEGER,
        unisDot11APIfInBrdcastPkts2       Counter64,
        unisDot11APIfOutBrdcastPkts2      Counter64,
        unisDot11APIfInMulcastPkts2       Counter64,
        unisDot11APIfOutMulcastPkts2      Counter64,
        unisDot11APIfInPayloadOctets2     Counter64,
        unisDot11APIfOutPayloadOctets2    Counter64,
        unisDot11APIfInDataOctets2        Counter64,
        unisDot11APIfOutDataOctets2       Counter64,
        unisDot11APIfAdminStatus          INTEGER,
        unisDot11APIfOperStatusCM         INTEGER
    }

unisDot11APIfInPkts2 OBJECT-TYPE
    SYNTAX      Counter64
    MAX-ACCESS  read-only
    STATUS      current
    DESCRIPTION
        "Represents the total number of packets received
         on the interface."
    ::= { unisDot11APIfStatisByAPIDEntry 1 }

unisDot11APIfInNormalPkts2 OBJECT-TYPE
    SYNTAX      Counter64
    MAX-ACCESS  read-only
    STATUS      current
    DESCRIPTION
        "Represents the total number of correct
         packets received on the interface."
    ::= { unisDot11APIfStatisByAPIDEntry 2 }

unisDot11APIfInErrorPkts2 OBJECT-TYPE
    SYNTAX      Counter64
    MAX-ACCESS  read-only
    STATUS      current
    DESCRIPTION
        "Represents the total number of error
         packets received on the interface."
    ::= { unisDot11APIfStatisByAPIDEntry 3 }

unisDot11APIfOutPkts2 OBJECT-TYPE
    SYNTAX      Counter64
    MAX-ACCESS  read-only
    STATUS      current
    DESCRIPTION
        "Represents the total number of packets
         sent from the interface."
    ::= { unisDot11APIfStatisByAPIDEntry 4 }

unisDot11APIfInOctets2 OBJECT-TYPE
    SYNTAX      Counter64
    MAX-ACCESS  read-only
    STATUS      current
    DESCRIPTION
        "Represents the total number of octets
         received on the interface."
    ::= { unisDot11APIfStatisByAPIDEntry 5 }

unisDot11APIfOutOctets2 OBJECT-TYPE
    SYNTAX      Counter64
    MAX-ACCESS  read-only
    STATUS      current
    DESCRIPTION
        "Represents the total number of octets
         sent from the interface."
    ::= { unisDot11APIfStatisByAPIDEntry 6 }

unisDot11APIfFlowOut2 OBJECT-TYPE
    SYNTAX      Unsigned32
    MAX-ACCESS  read-only
    STATUS      current
    DESCRIPTION
        "Represents the traffic rate (byte/s) on the uplink interface
         during a sampling period."
    ::= { unisDot11APIfStatisByAPIDEntry 7 }

unisDot11APIfFlowIN2 OBJECT-TYPE
    SYNTAX      Unsigned32
    MAX-ACCESS  read-only
    STATUS      current
    DESCRIPTION
        "Represents the traffic rate (byte/s) on the downlink interface
         during a sampling period."
    ::= { unisDot11APIfStatisByAPIDEntry 8 }

unisDot11APIfInUcastPkts2 OBJECT-TYPE
    SYNTAX      Counter64
    MAX-ACCESS  read-only
    STATUS      current
    DESCRIPTION
        "Represents the number of unicast packets received on the interface."
    ::= { unisDot11APIfStatisByAPIDEntry 9 }

unisDot11APIfInNUcastPkts2 OBJECT-TYPE
    SYNTAX      Counter64
    MAX-ACCESS  read-only
    STATUS      current
    DESCRIPTION
        "Represents the number of non-unicast packets received on the wired
         interface."
    ::= { unisDot11APIfStatisByAPIDEntry 10 }

unisDot11APIfInDiscardPkts2 OBJECT-TYPE
    SYNTAX      Counter64
    MAX-ACCESS  read-only
    STATUS      current
    DESCRIPTION
        "Represents the number of unicast packets discarded on the interface."
    ::= { unisDot11APIfStatisByAPIDEntry 11 }

unisDot11APIfOutUcastPkts2 OBJECT-TYPE
    SYNTAX      Counter64
    MAX-ACCESS  read-only
    STATUS      current
    DESCRIPTION
        "Represents the number of unicast packets send on the interface."
    ::= { unisDot11APIfStatisByAPIDEntry 12 }

unisDot11APIfOutNUcastPkts2 OBJECT-TYPE
    SYNTAX      Counter64
    MAX-ACCESS  read-only
    STATUS      current
    DESCRIPTION
        "Represents the number of non-unicast packets send on the interface."
    ::= { unisDot11APIfStatisByAPIDEntry 13 }

unisDot11APIfOutDiscardPkts2 OBJECT-TYPE
    SYNTAX      Counter64
    MAX-ACCESS  read-only
    STATUS      current
    DESCRIPTION
        "Represents the number of discarded packets send on the interface."
    ::= { unisDot11APIfStatisByAPIDEntry 14 }

unisDot11APIfOutErrorPkts2 OBJECT-TYPE
    SYNTAX      Counter64
    MAX-ACCESS  read-only
    STATUS      current
    DESCRIPTION
        "Represents the number of error packets send on the interface."
    ::= { unisDot11APIfStatisByAPIDEntry 15 }

unisDot11APIfUpdownTimes2 OBJECT-TYPE
    SYNTAX      Counter32
    MAX-ACCESS  read-only
    STATUS      current
    DESCRIPTION
        "Represents the up/down times on the interface."
    ::= { unisDot11APIfStatisByAPIDEntry 16 }

unisDot11APIfStatusKeepTime2 OBJECT-TYPE
    SYNTAX      TimeTicks
    MAX-ACCESS  read-only
    STATUS      current
    DESCRIPTION
        "Represents the last change time on the interface."
    ::= { unisDot11APIfStatisByAPIDEntry 17 }

unisDot11APIfOperStatus2 OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { unisDot11APIfStatisByAPIDEntry 18 }

unisDot11APIfInBrdcastPkts2 OBJECT-TYPE
    SYNTAX      Counter64
    MAX-ACCESS  read-only
    STATUS      current
    DESCRIPTION
        "Represents the number of broadcast packets received on the interface."
    ::= { unisDot11APIfStatisByAPIDEntry 19 }

unisDot11APIfOutBrdcastPkts2 OBJECT-TYPE
    SYNTAX      Counter64
    MAX-ACCESS  read-only
    STATUS      current
    DESCRIPTION
        "Represents the number of broadcast packets sent on the interface."
    ::= { unisDot11APIfStatisByAPIDEntry 20 }

unisDot11APIfInMulcastPkts2 OBJECT-TYPE
    SYNTAX      Counter64
    MAX-ACCESS  read-only
    STATUS      current
    DESCRIPTION
        "Represents the number of multicast packets received on the interface."
    ::= { unisDot11APIfStatisByAPIDEntry 21 }

unisDot11APIfOutMulcastPkts2 OBJECT-TYPE
    SYNTAX      Counter64
    MAX-ACCESS  read-only
    STATUS      current
    DESCRIPTION
        "Represents the number of multicast packets sent on the interface."
    ::= { unisDot11APIfStatisByAPIDEntry 22 }

unisDot11APIfInPayloadOctets2 OBJECT-TYPE
    SYNTAX      Counter64
    MAX-ACCESS  read-only
    STATUS      current
    DESCRIPTION
        "Represents the number of actual octets received on the interface."
    ::= { unisDot11APIfStatisByAPIDEntry 23 }

unisDot11APIfOutPayloadOctets2 OBJECT-TYPE
    SYNTAX      Counter64
    MAX-ACCESS  read-only
    STATUS      current
    DESCRIPTION
        "Represents the number of actual octets sent on the interface."
    ::= { unisDot11APIfStatisByAPIDEntry 24 }

unisDot11APIfInDataOctets2 OBJECT-TYPE
    SYNTAX      Counter64
    MAX-ACCESS  read-only
    STATUS      current
    DESCRIPTION
        "Represents the number of actual data octets received on the interface."
    ::= { unisDot11APIfStatisByAPIDEntry 25 }

unisDot11APIfOutDataOctets2 OBJECT-TYPE
    SYNTAX      Counter64
    MAX-ACCESS  read-only
    STATUS      current
    DESCRIPTION
        "Represents the number of actual data octets sent on the interface."
    ::= { unisDot11APIfStatisByAPIDEntry 26 }

unisDot11APIfAdminStatus OBJECT-TYPE
    SYNTAX  INTEGER {
                up(1),       -- ready to forward packets
                down(2),
                testing(3)   -- in a test mode
            }
    MAX-ACCESS  read-write
    STATUS      current
    DESCRIPTION
            "Expected state of the interface.  In testing state the
            interface does not forward any operational packets.  When
             a managed system is initialized, all interfaces start with
            unisDot11APIfAdminStatus in the down state.  As a result
            of either explicit management action or per configuration
            information retained by the managed system,
            unisDot11APIfAdminStatus is then changed to either the up
             or testing state or remains in the down state."
    ::= { unisDot11APIfStatisByAPIDEntry 27 }

unisDot11APIfOperStatusCM OBJECT-TYPE
    SYNTAX  INTEGER {
                       up(1),        -- ready to forward packets
                       down(2),
                       testing(3),   -- in a test mode
                       admindown(4)  -- shutdown by administrator
                    }
    MAX-ACCESS  read-only
    STATUS      current
    DESCRIPTION
        "Operational status of the interface."
    ::= { unisDot11APIfStatisByAPIDEntry 28 }

-- *****************************************************************************
-- *  End of unisDot11APIfStatisTable1 Definition
-- *****************************************************************************

-- *****************************************************************************
-- *  unisDot11APUserSecAuthStatisTable Definition
-- *****************************************************************************
unisDot11APUserSecAuthStatisTable OBJECT-TYPE
    SYNTAX      SEQUENCE OF UnisDot11APUserSecAuthStatisEntry
    MAX-ACCESS  not-accessible
    STATUS      current
    DESCRIPTION
        "The table will provide the user authentication statistic for this AP."
    ::= { unisDot11APStatisGroup 24 }

unisDot11APUserSecAuthStatisEntry OBJECT-TYPE
    SYNTAX      UnisDot11APUserSecAuthStatisEntry
    MAX-ACCESS  not-accessible
    STATUS      current
    DESCRIPTION
        "Each entry of the table will provide the user authentication statistic
        for this AP."
    INDEX
        {
            unisDot11CurAPID
       }
    ::= { unisDot11APUserSecAuthStatisTable 1 }

UnisDot11APUserSecAuthStatisEntry ::= SEQUENCE
    {
        unisDot11APUserAuthCurNumber             Integer32,
        unisDot11APUserConnFailCnt               Counter32,
        unisDot11APUserAuthReqCnt                Counter32,
        unisDot11APUserAuthSuccCnt               Counter32,
        unisDot11APUserAuthFailCnt               Counter32,
        unisDot11AllUserOnlineTime               TimeTicks
    }

unisDot11APUserAuthCurNumber OBJECT-TYPE
    SYNTAX      Integer32
    MAX-ACCESS  read-only
    STATUS      current
    DESCRIPTION
        "Represents the current number of user authenticated with this AP."
    ::= { unisDot11APUserSecAuthStatisEntry 1 }

unisDot11APUserConnFailCnt OBJECT-TYPE
    SYNTAX      Counter32
    MAX-ACCESS  read-only
    STATUS      current
    DESCRIPTION
        "Represents the total number of user disconnected with this AP."
    ::= { unisDot11APUserSecAuthStatisEntry 2 }

unisDot11APUserAuthReqCnt OBJECT-TYPE
    SYNTAX      Counter32
    MAX-ACCESS  read-only
    STATUS      current
    DESCRIPTION
        "Represents the total number of user authentication request with this AP."
    ::= { unisDot11APUserSecAuthStatisEntry 3 }

unisDot11APUserAuthSuccCnt OBJECT-TYPE
    SYNTAX      Counter32
    MAX-ACCESS  read-only
    STATUS      current
    DESCRIPTION
        "Represents the total number of successful authenticated users with this AP."
    ::= { unisDot11APUserSecAuthStatisEntry 4 }

unisDot11APUserAuthFailCnt OBJECT-TYPE
    SYNTAX      Counter32
    MAX-ACCESS  read-only
    STATUS      current
    DESCRIPTION
        "Represents the total number of user authentication failures with this AP."
    ::= { unisDot11APUserSecAuthStatisEntry 5 }

unisDot11AllUserOnlineTime OBJECT-TYPE
    SYNTAX      TimeTicks
    MAX-ACCESS  read-only
    STATUS      current
    DESCRIPTION
        "Represents the online time of all successful authenticated users with this AP."
    ::= { unisDot11APUserSecAuthStatisEntry 6 }

-- *****************************************************************************
-- *  End of unisDot11APUserSecAuthStatisEntry Definition
-- *****************************************************************************

-- *****************************************************************************
-- *  unisDot11APUserInfoStatisTable Definition
-- *****************************************************************************
unisDot11APUserInfoStatisTable OBJECT-TYPE
    SYNTAX      SEQUENCE OF UnisDot11APUserInfoStatisEntry
    MAX-ACCESS  not-accessible
    STATUS      current
    DESCRIPTION
        "The table will provide the user information statistic of this AP."
    ::= { unisDot11APStatisGroup 25 }

unisDot11APUserInfoStatisEntry OBJECT-TYPE
    SYNTAX      UnisDot11APUserInfoStatisEntry
    MAX-ACCESS  not-accessible
    STATUS      current
    DESCRIPTION
        "Each entry of the table will provide the user information statistic
        of this AP."
    INDEX
        {
            unisDot11CurAPID,
            unisDot11APUserMacAddr
        }
    ::= { unisDot11APUserInfoStatisTable 1 }

UnisDot11APUserInfoStatisEntry ::= SEQUENCE
    {
        unisDot11APUserMacAddr                  MacAddress,
        unisDot11APUserIpAddr                   IpAddress,
        unisDot11APUserLoginName                OCTET STRING,
        unisDot11APUserLoginTime                OCTET STRING,
        unisDot11APUserOnlineTime               TimeTicks,
        unisDot11APUserLoginNameCM              OCTET STRING,
        unisDot11APUserAuthTypeCM               INTEGER,
        unisDot11APUserTxPacketCntCM            Counter32,
        unisDot11APUserTxBytesCM                Counter64,
        unisDot11APUserRxPacketCntCM            Counter32,
        unisDot11APUserRxBytesCM                Counter64
    }

unisDot11APUserMacAddr OBJECT-TYPE
    SYNTAX      MacAddress
    MAX-ACCESS  not-accessible
    STATUS      current
    DESCRIPTION
        "Represents the mac address of user logging to this AP."
    ::= { unisDot11APUserInfoStatisEntry 1 }

unisDot11APUserIpAddr OBJECT-TYPE
    SYNTAX      IpAddress
    MAX-ACCESS  read-only
    STATUS      current
    DESCRIPTION
        "Represents the ip address of user logging to this AP."
    ::= { unisDot11APUserInfoStatisEntry 2 }

unisDot11APUserLoginName OBJECT-TYPE
    SYNTAX      OCTET STRING
    MAX-ACCESS  read-only
    STATUS      current
    DESCRIPTION
        "Represents the login name of user logging to this AP."
    ::= { unisDot11APUserInfoStatisEntry 3 }

unisDot11APUserLoginTime OBJECT-TYPE
    SYNTAX      OCTET STRING
    MAX-ACCESS  read-only
    STATUS      current
    DESCRIPTION
        "Represents the login time of user with this AP."
    ::= { unisDot11APUserInfoStatisEntry 4 }

unisDot11APUserOnlineTime OBJECT-TYPE
    SYNTAX      TimeTicks
    MAX-ACCESS  read-only
    STATUS      current
    DESCRIPTION
        "Represents the online time of user with this AP."
    ::= { unisDot11APUserInfoStatisEntry 5 }

unisDot11APUserLoginNameCM OBJECT-TYPE
    SYNTAX      OCTET STRING
    MAX-ACCESS  read-only
    STATUS      current
    DESCRIPTION
        "Represents the login name of user logging to this AP."
    ::= { unisDot11APUserInfoStatisEntry 6 }

unisDot11APUserAuthTypeCM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { unisDot11APUserInfoStatisEntry 7 }

unisDot11APUserTxPacketCntCM OBJECT-TYPE
    SYNTAX      Counter32
    MAX-ACCESS  read-only
    STATUS      current
    DESCRIPTION
        "Represents the total count of packets sent to online users."
    ::= { unisDot11APUserInfoStatisEntry 8 }

unisDot11APUserTxBytesCM OBJECT-TYPE
    SYNTAX      Counter64
    MAX-ACCESS  read-only
    STATUS      current
    DESCRIPTION
        "Represents the total bytes sent to online users."
    ::= { unisDot11APUserInfoStatisEntry 9 }

unisDot11APUserRxPacketCntCM OBJECT-TYPE
    SYNTAX      Counter32
    MAX-ACCESS  read-only
    STATUS      current
    DESCRIPTION
        "Represents the total count of packets received from online users."
    ::= { unisDot11APUserInfoStatisEntry 10 }

unisDot11APUserRxBytesCM OBJECT-TYPE
    SYNTAX      Counter64
    MAX-ACCESS  read-only
    STATUS      current
    DESCRIPTION
        "Represents the total bytes received from online users."
    ::= { unisDot11APUserInfoStatisEntry 11 }

-- *****************************************************************************
-- *  End of unisDot11APUserInfoStatisTable Definition
-- *****************************************************************************

-- *****************************************************************************
-- *  unisDot11APReassocStatis2Table Definition
-- *****************************************************************************
unisDot11APReassocStatis2Table OBJECT-TYPE
    SYNTAX      SEQUENCE OF UnisDot11APReassocStatis2Entry
    MAX-ACCESS  not-accessible
    STATUS      current
    DESCRIPTION
        "This table will provide statistic of reassociation for each AP."
    ::= { unisDot11APStatisGroup 26 }

unisDot11APReassocStatis2Entry OBJECT-TYPE
    SYNTAX      UnisDot11APReassocStatis2Entry
    MAX-ACCESS  not-accessible
    STATUS      current
    DESCRIPTION
        "Each entry will provide statistic of reassociation with this AP
         because of different reasons."
    INDEX
        {
            unisDot11CurAPID
        }
    ::= { unisDot11APReassocStatis2Table 1 }

UnisDot11APReassocStatis2Entry ::= SEQUENCE
    {
        unisDot11APReassocFailStatis2Cnt                 Counter32
    }

unisDot11APReassocFailStatis2Cnt OBJECT-TYPE
    SYNTAX      Counter32
    MAX-ACCESS  read-only
    STATUS      current
    DESCRIPTION
        "This object represents the count of reassociation failure because of
         lack of resource."
    ::= { unisDot11APReassocStatis2Entry 1 }

-- *****************************************************************************
-- *  End of unisDot11APReassocStatis2Table Definition
-- *****************************************************************************

-- *****************************************************************************
-- *  unisDot11TrafficTable Definition
-- *****************************************************************************
unisDot11TrafficTable OBJECT-TYPE
    SYNTAX      SEQUENCE OF UnisDot11TrafficEntry
    MAX-ACCESS  not-accessible
    STATUS      current
    DESCRIPTION
        "The table describes user's traffic based on ssid"
    ::= { unisDot11APStatisGroup 27 }

unisDot11TrafficEntry OBJECT-TYPE
    SYNTAX      UnisDot11TrafficEntry
    MAX-ACCESS  not-accessible
    STATUS      current
    DESCRIPTION
        "Each entry contains the traffc information of a ssid."
    INDEX
        {
            unisDot11SSIDIndex
        }
    ::= { unisDot11TrafficTable 1 }

UnisDot11TrafficEntry ::= SEQUENCE
    {
        unisDot11SSIDIndex             OCTET STRING,
        unisDot11UpPacketNumber        Counter64,
        unisDot11UpByteNumber          Counter64,
        unisDot11DownPacketNumber      Counter64,
        unisDot11DownByteNumber        Counter64
    }

unisDot11SSIDIndex OBJECT-TYPE
    SYNTAX      OCTET STRING
    MAX-ACCESS  not-accessible
    STATUS      current
    DESCRIPTION
        "Represents the SSID."
    ::= { unisDot11TrafficEntry 1 }

unisDot11UpPacketNumber OBJECT-TYPE
    SYNTAX      Counter64
    MAX-ACCESS  read-only
    STATUS      current
    DESCRIPTION
        "Represents the packet count of up link."
    ::= { unisDot11TrafficEntry 2 }

unisDot11UpByteNumber OBJECT-TYPE
    SYNTAX      Counter64
    MAX-ACCESS  read-only
    STATUS      current
    DESCRIPTION
        "Represents the byte count of up link."
    ::= { unisDot11TrafficEntry 3 }

unisDot11DownPacketNumber OBJECT-TYPE
    SYNTAX      Counter64
    MAX-ACCESS  read-only
    STATUS      current
    DESCRIPTION
        "Represents the packet count of down link."
    ::= { unisDot11TrafficEntry 4 }

unisDot11DownByteNumber OBJECT-TYPE
    SYNTAX      Counter64
    MAX-ACCESS  read-only
    STATUS      current
    DESCRIPTION
        "Represents the byte count of down link."
    ::= { unisDot11TrafficEntry 5 }

-- *****************************************************************************
-- *  End of unisDot11TrafficTable Definition
-- *****************************************************************************

-- *****************************************************************************
-- *  unisDot11APEchoStatisTable Definition
-- *****************************************************************************
unisDot11APEchoStatisTable OBJECT-TYPE
    SYNTAX      SEQUENCE OF UnisDot11APEchoInfoStatisEntry
    MAX-ACCESS  not-accessible
    STATUS      current
    DESCRIPTION
        "The table will provide the Echo statistic of this AP."
    ::= { unisDot11APStatisGroup 28 }

unisDot11APEchoInfoStatisEntry OBJECT-TYPE
    SYNTAX      UnisDot11APEchoInfoStatisEntry
    MAX-ACCESS  not-accessible
    STATUS      current
    DESCRIPTION
        "Each entry of the table will provide the Echo statistic
        of this AP."
    INDEX
        {
            unisDot11CurAPID
        }
    ::= { unisDot11APEchoStatisTable 1 }

UnisDot11APEchoInfoStatisEntry ::= SEQUENCE
    {
        unisDot11APEchoAvgDelay                 Integer32,
        unisDot11APEchoRequestCnt               Counter64,
        unisDot11APEchoRespLossCnt              Counter64
    }

unisDot11APEchoAvgDelay OBJECT-TYPE
    SYNTAX      Integer32
    UNITS       "millisecond"
    MAX-ACCESS  read-only
    STATUS      current
    DESCRIPTION
        "This object represents the average time delay of heart beat in this AP."
    ::= { unisDot11APEchoInfoStatisEntry 1 }

unisDot11APEchoRequestCnt OBJECT-TYPE
    SYNTAX      Counter64
    MAX-ACCESS  read-only
    STATUS      current
    DESCRIPTION
        "This object represents the count of echo request in this AP."
    ::= { unisDot11APEchoInfoStatisEntry 2 }

unisDot11APEchoRespLossCnt OBJECT-TYPE
    SYNTAX      Counter64
    MAX-ACCESS  read-only
    STATUS      current
    DESCRIPTION
        "This object represents the loss count of echo response in this AP."
    ::= { unisDot11APEchoInfoStatisEntry 3 }

-- *****************************************************************************
-- *  End of unisDot11APEchoStatisTable Definition
-- *****************************************************************************

-- *****************************************************************************
-- *  unisDot11APUserSecAuthTypeStatisTable Definition
-- *****************************************************************************
unisDot11APUserSecAuthTypeStatisTable OBJECT-TYPE
    SYNTAX      SEQUENCE OF UnisDot11APUserSecAuthTypeStatisEntry
    MAX-ACCESS  not-accessible
    STATUS      current
    DESCRIPTION
        "The table will provide the user authentication type statistic for this AP."
    ::= { unisDot11APStatisGroup 29 }

unisDot11APUserSecAuthTypeStatisEntry OBJECT-TYPE
    SYNTAX      UnisDot11APUserSecAuthTypeStatisEntry
    MAX-ACCESS  not-accessible
    STATUS      current
    DESCRIPTION
        "Each entry of the table will provide the user authentication type statistic
        for this AP."
    INDEX
        {
            unisDot11CurAPID
        }
    ::= { unisDot11APUserSecAuthTypeStatisTable 1 }

UnisDot11APUserSecAuthTypeStatisEntry ::= SEQUENCE
    {
        unisDot11APPortalOnlineUserNum          Integer32,
        unisDot11APAuthFreeOnlineUserNum        Integer32,
        unisDot11APAssocAuthOnlineUserNum       Integer32,
        unisDot11APMacAuthOnlineUserNum         Integer32,
        unisDot11APAllPortalUserOnlineTime      TimeTicks,
        unisDot11APAllAuthFreeUserOnlineTime    TimeTicks,
        unisDot11APAllAssocAuthUserOnlineTime   TimeTicks,
        unisDot11APAllMacAuthUserOnlineTime     TimeTicks,
        unisDot11APPortalUserLostCnntCnt        Counter32,
        unisDot11APAuthFreeUserLostCnntCnt      Counter32,
        unisDot11APAssocAuthUserLostCnntCnt     Counter32,
        unisDot11APMacAuthUserLostCnntCnt       Counter32,
        unisDot11APPortalAuthReqCnt             Counter32,
        unisDot11APAssocAuthReqCnt              Counter32,
        unisDot11APMacAuthReqCnt                Counter32,
        unisDot11APPortalAuthSucCnt             Counter32,
        unisDot11APAssocAuthSucCnt              Counter32,
        unisDot11APMacAuthSucCnt                Counter32,
        unisDot11APPortalAuthReqFailCnt         Counter32,
        unisDot11APAssocAuthReqFailCnt          Counter32,
        unisDot11APMacAuthReqFailCnt            Counter32,
        unisDot11APAutoAuthOnlineUserNumCM      Integer32,
        unisDot11APAllAutoAuthUserOnlineTimeCM  TimeTicks,
        unisDot11APAutoAuthUserLostCnntCntCM    Counter32,
        unisDot11APAutoAuthReqCntCM             Counter32,
        unisDot11APAutoAuthSucCntCM             Counter32,
        unisDot11APAutoAuthReqFailCntCM         Counter32
    }

unisDot11APPortalOnlineUserNum OBJECT-TYPE
    SYNTAX      Integer32
    MAX-ACCESS  read-only
    STATUS      current
    DESCRIPTION
        "Represents the number of online portal users of this AP, including
        MAC-trigger and IMSIAuth users."
    ::= { unisDot11APUserSecAuthTypeStatisEntry 1 }

unisDot11APAuthFreeOnlineUserNum OBJECT-TYPE
    SYNTAX      Integer32
    MAX-ACCESS  read-only
    STATUS      current
    DESCRIPTION
        "Represents the online number of user free authenticated with this AP."
    ::= { unisDot11APUserSecAuthTypeStatisEntry 2 }

unisDot11APAssocAuthOnlineUserNum OBJECT-TYPE
    SYNTAX      Integer32
    MAX-ACCESS  read-only
    STATUS      current
    DESCRIPTION
        "Represents the number of online users authenticated by associated
        authentication with this AP, excluding AutoAuth users."
    ::= { unisDot11APUserSecAuthTypeStatisEntry 3 }

unisDot11APMacAuthOnlineUserNum OBJECT-TYPE
    SYNTAX      Integer32
    MAX-ACCESS  read-only
    STATUS      current
    DESCRIPTION
        "Represents the online number of user MAC address authenticated with this AP."
    ::= { unisDot11APUserSecAuthTypeStatisEntry 4 }

unisDot11APAllPortalUserOnlineTime OBJECT-TYPE
    SYNTAX      TimeTicks
    MAX-ACCESS  read-only
    STATUS      current
    DESCRIPTION
        "Represents the online time of all user portal authenticated with this AP."
    ::= { unisDot11APUserSecAuthTypeStatisEntry 5 }

unisDot11APAllAuthFreeUserOnlineTime OBJECT-TYPE
    SYNTAX      TimeTicks
    MAX-ACCESS  read-only
    STATUS      current
    DESCRIPTION
        "Represents the online time of all user free authenticated with this AP."
    ::= { unisDot11APUserSecAuthTypeStatisEntry 6 }

unisDot11APAllAssocAuthUserOnlineTime OBJECT-TYPE
    SYNTAX      TimeTicks
    MAX-ACCESS  read-only
    STATUS      current
    DESCRIPTION
        "Represents the online time of all user associated authenticated with this AP."
    ::= { unisDot11APUserSecAuthTypeStatisEntry 7 }

unisDot11APAllMacAuthUserOnlineTime OBJECT-TYPE
    SYNTAX      TimeTicks
    MAX-ACCESS  read-only
    STATUS      current
    DESCRIPTION
        "Represents the online time of all user MAC address authenticated with this AP."
    ::= { unisDot11APUserSecAuthTypeStatisEntry 8 }

unisDot11APPortalUserLostCnntCnt OBJECT-TYPE
    SYNTAX      Counter32
    MAX-ACCESS  read-only
    STATUS      current
    DESCRIPTION
        "Represents the lost connective count of user portal authenticated with this AP."
    ::= { unisDot11APUserSecAuthTypeStatisEntry 9 }

unisDot11APAuthFreeUserLostCnntCnt OBJECT-TYPE
    SYNTAX      Counter32
    MAX-ACCESS  read-only
    STATUS      current
    DESCRIPTION
        "Represents the lost connective count of user free authenticated with this AP."
    ::= { unisDot11APUserSecAuthTypeStatisEntry 10 }

unisDot11APAssocAuthUserLostCnntCnt OBJECT-TYPE
    SYNTAX      Counter32
    MAX-ACCESS  read-only
    STATUS      current
    DESCRIPTION
        "Represents the lost connective count of user associate authenticated with this AP."
    ::= { unisDot11APUserSecAuthTypeStatisEntry 11 }

unisDot11APMacAuthUserLostCnntCnt OBJECT-TYPE
    SYNTAX      Counter32
    MAX-ACCESS  read-only
    STATUS      current
    DESCRIPTION
        "Represents the lost connective count of user MAC address authenticated with this AP."
    ::= { unisDot11APUserSecAuthTypeStatisEntry 12 }

unisDot11APPortalAuthReqCnt OBJECT-TYPE
    SYNTAX      Counter32
    MAX-ACCESS  read-only
    STATUS      current
    DESCRIPTION
        "Represents the request count of user portal authenticated with this AP."
    ::= { unisDot11APUserSecAuthTypeStatisEntry 13 }

unisDot11APAssocAuthReqCnt OBJECT-TYPE
    SYNTAX      Counter32
    MAX-ACCESS  read-only
    STATUS      current
    DESCRIPTION
        "Represents the request count of user associate authenticated with this AP."
    ::= { unisDot11APUserSecAuthTypeStatisEntry 14 }

unisDot11APMacAuthReqCnt OBJECT-TYPE
    SYNTAX      Counter32
    MAX-ACCESS  read-only
    STATUS      current
    DESCRIPTION
        "Represents the request count of user MAC address authenticated with this AP."
    ::= { unisDot11APUserSecAuthTypeStatisEntry 15 }

unisDot11APPortalAuthSucCnt OBJECT-TYPE
    SYNTAX      Counter32
    MAX-ACCESS  read-only
    STATUS      current
    DESCRIPTION
        "Represents the count of user portal authenticated successed with this AP."
    ::= { unisDot11APUserSecAuthTypeStatisEntry 16 }

unisDot11APAssocAuthSucCnt OBJECT-TYPE
    SYNTAX      Counter32
    MAX-ACCESS  read-only
    STATUS      current
    DESCRIPTION
        "Represents the count of user associate authenticated successed with this AP."
    ::= { unisDot11APUserSecAuthTypeStatisEntry 17 }

unisDot11APMacAuthSucCnt OBJECT-TYPE
    SYNTAX      Counter32
    MAX-ACCESS  read-only
    STATUS      current
    DESCRIPTION
        "Represents the count of user MAC address authenticated successed with this AP."
    ::= { unisDot11APUserSecAuthTypeStatisEntry 18 }

unisDot11APPortalAuthReqFailCnt OBJECT-TYPE
    SYNTAX      Counter32
    MAX-ACCESS  read-only
    STATUS      current
    DESCRIPTION
        "Represents the count of user portal authenticated failed with this AP."
    ::= { unisDot11APUserSecAuthTypeStatisEntry 19 }

unisDot11APAssocAuthReqFailCnt OBJECT-TYPE
    SYNTAX      Counter32
    MAX-ACCESS  read-only
    STATUS      current
    DESCRIPTION
        "Represents the count of user associate authenticated failed with this AP."
    ::= { unisDot11APUserSecAuthTypeStatisEntry 20 }

unisDot11APMacAuthReqFailCnt OBJECT-TYPE
    SYNTAX      Counter32
    MAX-ACCESS  read-only
    STATUS      current
    DESCRIPTION
        "Represents the count of user MAC address authenticated failed with this AP."
    ::= { unisDot11APUserSecAuthTypeStatisEntry 21 }

unisDot11APAutoAuthOnlineUserNumCM OBJECT-TYPE
    SYNTAX      Integer32
    MAX-ACCESS  read-only
    STATUS      current
    DESCRIPTION
        "Represents the number of online users authenticated by auto authentication
        with this AP."
    ::= { unisDot11APUserSecAuthTypeStatisEntry 22 }

unisDot11APAllAutoAuthUserOnlineTimeCM OBJECT-TYPE
    SYNTAX      TimeTicks
    MAX-ACCESS  read-only
    STATUS      current
    DESCRIPTION
        "Represents the online time of users authenticated by auto authentication
        with this AP."
    ::= { unisDot11APUserSecAuthTypeStatisEntry 23 }

unisDot11APAutoAuthUserLostCnntCntCM OBJECT-TYPE
    SYNTAX      Counter32
    MAX-ACCESS  read-only
    STATUS      current
    DESCRIPTION
        "Represents the disconnection count of AutoAuth users."
    ::= { unisDot11APUserSecAuthTypeStatisEntry 24 }

unisDot11APAutoAuthReqCntCM OBJECT-TYPE
    SYNTAX      Counter32
    MAX-ACCESS  read-only
    STATUS      current
    DESCRIPTION
        "Represents the count of AutoAuth requests with this AP."
    ::= { unisDot11APUserSecAuthTypeStatisEntry 25 }

unisDot11APAutoAuthSucCntCM OBJECT-TYPE
    SYNTAX      Counter32
    MAX-ACCESS  read-only
    STATUS      current
    DESCRIPTION
        "Represents the count of successful AutoAuth authentications with this AP."
    ::= { unisDot11APUserSecAuthTypeStatisEntry 26 }

unisDot11APAutoAuthReqFailCntCM OBJECT-TYPE
    SYNTAX      Counter32
    MAX-ACCESS  read-only
    STATUS      current
    DESCRIPTION
        "Represents the count of failed AutoAuth requests with this AP."
    ::= { unisDot11APUserSecAuthTypeStatisEntry 27 }

-- *****************************************************************************
-- *  End of unisDot11APUserSecAuthTypeStatisTable Definition
-- *****************************************************************************

-- *****************************************************************************
-- *  unisDot11RadioRxStatis64Table Definition
-- *****************************************************************************
unisDot11RadioRxStatis64Table OBJECT-TYPE
    SYNTAX      SEQUENCE OF UnisDot11RadioRxStatis64Entry
    MAX-ACCESS  not-accessible
    STATUS      current
    DESCRIPTION
        "The table will provide the reception statistic for a specific
        radio of AP."
    ::= { unisDot11APStatisGroup 30 }

unisDot11RadioRxStatis64Entry OBJECT-TYPE
    SYNTAX      UnisDot11RadioRxStatis64Entry
    MAX-ACCESS  not-accessible
    STATUS      current
    DESCRIPTION
        "Each entry of the table will provide the reception statistic
        data for each radio of a specific AP."
    INDEX
        {
            unisDot11CurAPID,
            unisDot11RadioID
        }
    ::= { unisDot11RadioRxStatis64Table 1 }

UnisDot11RadioRxStatis64Entry ::= SEQUENCE
    {
        unisDot11Rx64FrameDupCnt          Counter64,
        unisDot11Rx64FrameCnt             Counter64,
        unisDot11Rx64UcastFrameCnt        Counter64,
        unisDot11Rx64BcastFrameCnt        Counter64,
        unisDot11Rx64McastFrameCnt        Counter64,
        unisDot11Rx64DiscardFrameCnt      Counter64,
        unisDot11Rx64FragCnt              Counter64,
        unisDot11Rx64FcsErrCnt            Counter64,
        unisDot11Rx64FrameBytes           Counter64,
        unisDot11Rx64UcastFrameBytes      Counter64,
        unisDot11Rx64BcastFrameBytes      Counter64,
        unisDot11Rx64McastFrameBytes      Counter64,
        unisDot11Rx64DiscardFrameBytes    Counter64,
        unisDot11Rx64MgmtFrameCnt         Counter64,
        unisDot11Rx64CtrlFrameCnt         Counter64,
        unisDot11Rx64DataFrameCnt         Counter64,
        unisDot11Rx64DecryptErrorCnt      Counter64,
        unisDot11Rx64AuthenFrameCnt       Counter64,
        unisDot11Rx64AssociateFrameCnt    Counter64,
        unisDot11Rx64PhyErrorCnt          Counter64,
        unisDot11Rx64MICErrorCnt          Counter64,
        unisDot11Rx64DataFrameBytes       Counter64,
        unisDot11Rx64PayloadBytes         Counter64,
        unisDot11Rx64DataFrameBytesCM     Counter64
    }

unisDot11Rx64FrameDupCnt OBJECT-TYPE
    SYNTAX      Counter64
    MAX-ACCESS  read-only
    STATUS      current
    DESCRIPTION
        "Represents the number of duplicate frames reception."
    ::= { unisDot11RadioRxStatis64Entry 1 }

unisDot11Rx64FrameCnt OBJECT-TYPE
    SYNTAX      Counter64
    MAX-ACCESS  read-only
    STATUS      current
    DESCRIPTION
        "Represents the number of frames reception."
    ::= { unisDot11RadioRxStatis64Entry 2 }

unisDot11Rx64UcastFrameCnt OBJECT-TYPE
    SYNTAX      Counter64
    MAX-ACCESS  read-only
    STATUS      current
    DESCRIPTION
        "Represents the number of unicast frames reception."
    ::= { unisDot11RadioRxStatis64Entry 3 }

unisDot11Rx64BcastFrameCnt OBJECT-TYPE
    SYNTAX      Counter64
    MAX-ACCESS  read-only
    STATUS      current
    DESCRIPTION
        "Represents the number of broadcast frames reception."
    ::= { unisDot11RadioRxStatis64Entry 4 }

unisDot11Rx64McastFrameCnt OBJECT-TYPE
    SYNTAX      Counter64
    MAX-ACCESS  read-only
    STATUS      current
    DESCRIPTION
        "Represents the number of multicast frames reception."
    ::= { unisDot11RadioRxStatis64Entry 5 }

unisDot11Rx64DiscardFrameCnt OBJECT-TYPE
    SYNTAX      Counter64
    MAX-ACCESS  read-only
    STATUS      current
    DESCRIPTION
        "Represents the number of discarded frames reception."
    ::= { unisDot11RadioRxStatis64Entry 6 }

unisDot11Rx64FragCnt OBJECT-TYPE
    SYNTAX      Counter64
    MAX-ACCESS  read-only
    STATUS      current
    DESCRIPTION
        "Represents the number of frame fragments reception."
    ::= { unisDot11RadioRxStatis64Entry 7 }

unisDot11Rx64FcsErrCnt OBJECT-TYPE
    SYNTAX      Counter64
    MAX-ACCESS  read-only
    STATUS      current
    DESCRIPTION
        "Represents the number of FCS error frames reception."
    ::= { unisDot11RadioRxStatis64Entry 8 }

unisDot11Rx64FrameBytes OBJECT-TYPE
    SYNTAX      Counter64
    MAX-ACCESS  read-only
    STATUS      current
    DESCRIPTION
        "Represents the bytes of frames reception."
    ::= { unisDot11RadioRxStatis64Entry 9 }

unisDot11Rx64UcastFrameBytes OBJECT-TYPE
    SYNTAX      Counter64
    MAX-ACCESS  read-only
    STATUS      current
    DESCRIPTION
        "Represents the bytes of unicast frames reception."
    ::= { unisDot11RadioRxStatis64Entry 10 }

unisDot11Rx64BcastFrameBytes OBJECT-TYPE
    SYNTAX      Counter64
    MAX-ACCESS  read-only
    STATUS      current
    DESCRIPTION
        "Represents the bytes of broadcast frames reception."
    ::= { unisDot11RadioRxStatis64Entry 11 }

unisDot11Rx64McastFrameBytes OBJECT-TYPE
    SYNTAX      Counter64
    MAX-ACCESS  read-only
    STATUS      current
    DESCRIPTION
        "Represents the bytes of multicast frames reception."
    ::= { unisDot11RadioRxStatis64Entry 12 }

unisDot11Rx64DiscardFrameBytes OBJECT-TYPE
    SYNTAX      Counter64
    MAX-ACCESS  read-only
    STATUS      current
    DESCRIPTION
        "Represents the bytes of discarded frames reception."
    ::= { unisDot11RadioRxStatis64Entry 13 }

unisDot11Rx64MgmtFrameCnt OBJECT-TYPE
    SYNTAX      Counter64
    MAX-ACCESS  read-only
    STATUS      current
    DESCRIPTION
        "Represents the number of management frames reception."
    ::= { unisDot11RadioRxStatis64Entry 14 }

unisDot11Rx64CtrlFrameCnt OBJECT-TYPE
    SYNTAX      Counter64
    MAX-ACCESS  read-only
    STATUS      current
    DESCRIPTION
        "Represents the number of control frames reception."
    ::= { unisDot11RadioRxStatis64Entry 15 }

unisDot11Rx64DataFrameCnt OBJECT-TYPE
    SYNTAX      Counter64
    MAX-ACCESS  read-only
    STATUS      current
    DESCRIPTION
        "Represents the number of data frames reception."
    ::= { unisDot11RadioRxStatis64Entry 16 }

unisDot11Rx64DecryptErrorCnt OBJECT-TYPE
    SYNTAX      Counter64
    MAX-ACCESS  read-only
    STATUS      current
    DESCRIPTION
        "Represents the number of decryption error reception."
    ::= { unisDot11RadioRxStatis64Entry 17 }

unisDot11Rx64AuthenFrameCnt OBJECT-TYPE
    SYNTAX      Counter64
    MAX-ACCESS  read-only
    STATUS      current
    DESCRIPTION
        "Represents the number of authentication frame reception."
    ::= { unisDot11RadioRxStatis64Entry 18 }

unisDot11Rx64AssociateFrameCnt OBJECT-TYPE
    SYNTAX      Counter64
    MAX-ACCESS  read-only
    STATUS      current
    DESCRIPTION
        "Represents the number of associate frame reception."
    ::= { unisDot11RadioRxStatis64Entry 19 }

unisDot11Rx64PhyErrorCnt OBJECT-TYPE
    SYNTAX      Counter64
    MAX-ACCESS  read-only
    STATUS      current
    DESCRIPTION
        "Represents the number of physical error reception."
    ::= { unisDot11RadioRxStatis64Entry 20 }

unisDot11Rx64MICErrorCnt OBJECT-TYPE
    SYNTAX      Counter64
    MAX-ACCESS  read-only
    STATUS      current
    DESCRIPTION
        "Represents the number of MIC verification error reception."
    ::= { unisDot11RadioRxStatis64Entry 21 }

unisDot11Rx64DataFrameBytes OBJECT-TYPE
    SYNTAX      Counter64
    MAX-ACCESS  read-only
    STATUS      current
    DESCRIPTION
        "Represents the bytes of data frames reception."
    ::= { unisDot11RadioRxStatis64Entry 22 }

unisDot11Rx64PayloadBytes OBJECT-TYPE
    SYNTAX      Counter64
    MAX-ACCESS  read-only
    STATUS      current
    DESCRIPTION
        "Represents the payload bytes of data frames reception."
    ::= { unisDot11RadioRxStatis64Entry 23 }

unisDot11Rx64DataFrameBytesCM OBJECT-TYPE
    SYNTAX      Counter64
    MAX-ACCESS  read-only
    STATUS      current
    DESCRIPTION
        "Represents the number of received data frames, excluding retransmitted
        frames."
    ::= { unisDot11RadioRxStatis64Entry 24 }

-- *****************************************************************************
-- *  End of unisDot11RadioRxStatis64Table Definition
-- *****************************************************************************

-- *****************************************************************************
-- *  unisDot11RadioTxStatis64Table Definition
-- *****************************************************************************
unisDot11RadioTxStatis64Table OBJECT-TYPE
    SYNTAX      SEQUENCE OF UnisDot11RadioTxStatis64Entry
    MAX-ACCESS  not-accessible
    STATUS      current
    DESCRIPTION
        "The table will provide the transmission statistic for a
        specific radio of AP."
    ::= { unisDot11APStatisGroup 31 }

unisDot11RadioTxStatis64Entry OBJECT-TYPE
    SYNTAX      UnisDot11RadioTxStatis64Entry
    MAX-ACCESS  not-accessible
    STATUS      current
    DESCRIPTION
        "Each entry of the table will provide the transmission
        statistic data for each radio of a specific AP."
    INDEX
        {
            unisDot11CurAPID,
            unisDot11RadioID
        }
    ::= { unisDot11RadioTxStatis64Table 1 }

UnisDot11RadioTxStatis64Entry ::= SEQUENCE
    {
        unisDot11Tx64FragCnt              Counter64,
        unisDot11Tx64FailedCnt            Counter64,
        unisDot11Tx64RetryCnt             Counter64,
        unisDot11Tx64MultiRetryCnt        Counter64,
        unisDot11Tx64RtsSuccessCnt        Counter64,
        unisDot11Tx64RtsFailCnt           Counter64,
        unisDot11Tx64AckFailCnt           Counter64,
        unisDot11Tx64FrameCnt             Counter64,
        unisDot11Tx64UcastFrameCnt        Counter64,
        unisDot11Tx64BcastFrameCnt        Counter64,
        unisDot11Tx64McastFrameCnt        Counter64,
        unisDot11Tx64DiscardFrameCnt      Counter64,
        unisDot11Tx64FrameBytes           Counter64,
        unisDot11Tx64UcastFrameBytes      Counter64,
        unisDot11Tx64BcastFrameBytes      Counter64,
        unisDot11Tx64McastFrameBytes      Counter64,
        unisDot11Tx64DiscardFrameBytes    Counter64,
        unisDot11Tx64AuthenFrameCnt       Counter64,
        unisDot11Tx64AssociateFrameCnt    Counter64,
        unisDot11Tx64DataFrameCnt         Counter64,
        unisDot11Tx64DataFrameBytes       Counter64,
        unisDot11Tx64MSDUCnt              Counter64,
        unisDot11Tx64DiscardMSDUCnt       Counter64,
        unisDot11Tx64RetryMSDUCnt         Counter64,
        unisDot11Tx64PayloadBytes         Counter64,
        unisDot11Tx64MgtFrameCnt          Counter64,
        unisDot11Tx64CtrlFrameCnt         Counter64,
        unisDot11Tx64MACErrCnt            Counter64,
        unisDot11Tx64ErrFrameCnt          Counter64
    }

unisDot11Tx64FragCnt OBJECT-TYPE
    SYNTAX      Counter64
    MAX-ACCESS  read-only
    STATUS      current
    DESCRIPTION
        "Represents the number of fragmented frames transmission."
    ::= { unisDot11RadioTxStatis64Entry 1 }

unisDot11Tx64FailedCnt OBJECT-TYPE
    SYNTAX      Counter64
    MAX-ACCESS  read-only
    STATUS      current
    DESCRIPTION
        "Represents the number of failures transmission."
    ::= { unisDot11RadioTxStatis64Entry 2 }

unisDot11Tx64RetryCnt OBJECT-TYPE
    SYNTAX      Counter64
    MAX-ACCESS  read-only
    STATUS      current
    DESCRIPTION
        "Represents the number of retries transmission."
    ::= { unisDot11RadioTxStatis64Entry 3 }

unisDot11Tx64MultiRetryCnt OBJECT-TYPE
    SYNTAX      Counter64
    MAX-ACCESS  read-only
    STATUS      current
    DESCRIPTION
        "Represents the number of transmits that required more than
        one retry transmission."
    ::= { unisDot11RadioTxStatis64Entry 4 }

unisDot11Tx64RtsSuccessCnt OBJECT-TYPE
    SYNTAX      Counter64
    MAX-ACCESS  read-only
    STATUS      current
    DESCRIPTION
        "Represents the number of successful RTS (Request to send)
        transmission."
    ::= { unisDot11RadioTxStatis64Entry 5 }

unisDot11Tx64RtsFailCnt OBJECT-TYPE
    SYNTAX      Counter64
    MAX-ACCESS  read-only
    STATUS      current
    DESCRIPTION
        "Represents the number of RTS failures transmission."
    ::= { unisDot11RadioTxStatis64Entry 6 }

unisDot11Tx64AckFailCnt OBJECT-TYPE
    SYNTAX      Counter64
    MAX-ACCESS  read-only
    STATUS      current
    DESCRIPTION
        "Represents the number of acknowledgement failures transmission."
    ::= { unisDot11RadioTxStatis64Entry 7 }

unisDot11Tx64FrameCnt OBJECT-TYPE
    SYNTAX      Counter64
    MAX-ACCESS  read-only
    STATUS      current
    DESCRIPTION
        "Represents the total number of frames transmission."
    ::= { unisDot11RadioTxStatis64Entry 8 }

unisDot11Tx64UcastFrameCnt OBJECT-TYPE
    SYNTAX      Counter64
    MAX-ACCESS  read-only
    STATUS      current
    DESCRIPTION
        "Represents the number of unicast frames transmission."
    ::= { unisDot11RadioTxStatis64Entry 9 }

unisDot11Tx64BcastFrameCnt OBJECT-TYPE
    SYNTAX      Counter64
    MAX-ACCESS  read-only
    STATUS      current
    DESCRIPTION
        "Represents the number of broadcast frames transmission."
    ::= { unisDot11RadioTxStatis64Entry 10 }

unisDot11Tx64McastFrameCnt OBJECT-TYPE
    SYNTAX      Counter64
    MAX-ACCESS  read-only
    STATUS      current
    DESCRIPTION
        "Represents the number of multicast frames transmission."
    ::= { unisDot11RadioTxStatis64Entry 11 }

unisDot11Tx64DiscardFrameCnt OBJECT-TYPE
    SYNTAX      Counter64
    MAX-ACCESS  read-only
    STATUS      current
    DESCRIPTION
        "Represents the number of discarded frames transmission."
    ::= { unisDot11RadioTxStatis64Entry 12 }

unisDot11Tx64FrameBytes OBJECT-TYPE
    SYNTAX      Counter64
    MAX-ACCESS  read-only
    STATUS      current
    DESCRIPTION
        "Represents the total bytes of frames transmission."
    ::= { unisDot11RadioTxStatis64Entry 13 }

unisDot11Tx64UcastFrameBytes OBJECT-TYPE
    SYNTAX      Counter64
    MAX-ACCESS  read-only
    STATUS      current
    DESCRIPTION
        "Represents the bytes of unicast frames transmission."
    ::= { unisDot11RadioTxStatis64Entry 14 }

unisDot11Tx64BcastFrameBytes OBJECT-TYPE
    SYNTAX      Counter64
    MAX-ACCESS  read-only
    STATUS      current
    DESCRIPTION
        "Represents the bytes of broadcast frames transmission."
    ::= { unisDot11RadioTxStatis64Entry 15 }

unisDot11Tx64McastFrameBytes OBJECT-TYPE
    SYNTAX      Counter64
    MAX-ACCESS  read-only
    STATUS      current
    DESCRIPTION
        "Represents the bytes of multicast frames transmission."
    ::= { unisDot11RadioTxStatis64Entry 16 }

unisDot11Tx64DiscardFrameBytes OBJECT-TYPE
    SYNTAX      Counter64
    MAX-ACCESS  read-only
    STATUS      current
    DESCRIPTION
        "Represents the bytes of discarded frames transmission."
    ::= { unisDot11RadioTxStatis64Entry 17 }

unisDot11Tx64AuthenFrameCnt OBJECT-TYPE
    SYNTAX      Counter64
    MAX-ACCESS  read-only
    STATUS      current
    DESCRIPTION
        "Represents the number of authentication frame transmission."
    ::= { unisDot11RadioTxStatis64Entry 18 }

unisDot11Tx64AssociateFrameCnt OBJECT-TYPE
    SYNTAX      Counter64
    MAX-ACCESS  read-only
    STATUS      current
    DESCRIPTION
        "Represents the number of associate frame transmission."
    ::= { unisDot11RadioTxStatis64Entry 19 }

unisDot11Tx64DataFrameCnt OBJECT-TYPE
    SYNTAX      Counter64
    MAX-ACCESS  read-only
    STATUS      current
    DESCRIPTION
        "Represents the number of data frame transmission."
    ::= { unisDot11RadioTxStatis64Entry 20 }

unisDot11Tx64DataFrameBytes OBJECT-TYPE
    SYNTAX      Counter64
    MAX-ACCESS  read-only
    STATUS      current
    DESCRIPTION
        "Represents the bytes of data frame transmission."
    ::= { unisDot11RadioTxStatis64Entry 21 }

unisDot11Tx64MSDUCnt OBJECT-TYPE
    SYNTAX      Counter64
    MAX-ACCESS  read-only
    STATUS      current
    DESCRIPTION
        "Represents the total number of MSDU transmission."
    ::= { unisDot11RadioTxStatis64Entry 22 }

unisDot11Tx64DiscardMSDUCnt OBJECT-TYPE
    SYNTAX      Counter64
    MAX-ACCESS  read-only
    STATUS      current
    DESCRIPTION
        "Represents the number of discarded MSDU transmission."
    ::= { unisDot11RadioTxStatis64Entry 23 }

unisDot11Tx64RetryMSDUCnt OBJECT-TYPE
    SYNTAX      Counter64
    MAX-ACCESS  read-only
    STATUS      current
    DESCRIPTION
        "Represents the number of retransfer MSDU transmission."
    ::= { unisDot11RadioTxStatis64Entry 24 }

unisDot11Tx64PayloadBytes OBJECT-TYPE
    SYNTAX      Counter64
    MAX-ACCESS  read-only
    STATUS      current
    DESCRIPTION
        "Represents the payload bytes of data frames transmission."
    ::= { unisDot11RadioTxStatis64Entry 25 }

unisDot11Tx64MgtFrameCnt OBJECT-TYPE
    SYNTAX      Counter64
    MAX-ACCESS  read-only
    STATUS      current
    DESCRIPTION
        "Represents the number of management frames transmission."
    ::= { unisDot11RadioTxStatis64Entry 26 }

unisDot11Tx64CtrlFrameCnt OBJECT-TYPE
    SYNTAX      Counter64
    MAX-ACCESS  read-only
    STATUS      current
    DESCRIPTION
        "Represents the number of control frames transmission."
    ::= { unisDot11RadioTxStatis64Entry 27 }
unisDot11Tx64MACErrCnt OBJECT-TYPE
    SYNTAX      Counter64
    MAX-ACCESS  read-only
    STATUS      current
    DESCRIPTION
        "Represents the number of MAC error frame transmission."
    ::= { unisDot11RadioTxStatis64Entry 28 }

unisDot11Tx64ErrFrameCnt OBJECT-TYPE
    SYNTAX      Counter64
    MAX-ACCESS  read-only
    STATUS      current
    DESCRIPTION
        "Represents the number of error frame transmission."
    ::= { unisDot11RadioTxStatis64Entry 29 }

-- *****************************************************************************
-- *  End of unisDot11RadioTxStatis64Table Definition
-- *****************************************************************************

-- *****************************************************************************
-- *  unisDot11BSSRxStatis64Table Definition
-- *****************************************************************************
unisDot11BSSRxStatis64Table OBJECT-TYPE
    SYNTAX      SEQUENCE OF UnisDot11BSSRxStatis64Entry
    MAX-ACCESS  not-accessible
    STATUS      current
    DESCRIPTION
        "The table will provide the reception statistic for a
        specific BSS on a radio."
    ::= { unisDot11APStatisGroup 32 }

unisDot11BSSRxStatis64Entry OBJECT-TYPE
    SYNTAX      UnisDot11BSSRxStatis64Entry
    MAX-ACCESS  not-accessible
    STATUS      current
    DESCRIPTION
        "Each entry of the table will provide the reception statistic data for
        each BSS on a specific radio."
    INDEX
        {
            unisDot11CurAPID,
            unisDot11RadioID,
            unisDot11WlanID
        }
    ::= { unisDot11BSSRxStatis64Table 1 }

UnisDot11BSSRxStatis64Entry ::= SEQUENCE
    {
        unisDot11BSSRx64FrameCnt             Counter64,
        unisDot11BSSRx64FrameBytes           Counter64,
        unisDot11BSSRx64DataFrameCnt         Counter64,
        unisDot11BSSRx64DataFrameBytes       Counter64,
        unisDot11BSSRx64AssocFrameCnt        Counter64,
        unisDot11BSSRx64PayloadBytes         Counter64,
        unisDot11BSSRx64UniFrameCnt          Counter64,
        unisDot11BSSRx64NonUniFrameCnt       Counter64,
        unisDot11BSSRx64AuthenFrameCnt       Counter64
    }

unisDot11BSSRx64FrameCnt OBJECT-TYPE
    SYNTAX      Counter64
    MAX-ACCESS  read-only
    STATUS      current
    DESCRIPTION
        "Represents the number of frames reception with this BSS."
    ::= { unisDot11BSSRxStatis64Entry 1 }

unisDot11BSSRx64FrameBytes OBJECT-TYPE
    SYNTAX      Counter64
    MAX-ACCESS  read-only
    STATUS      current
    DESCRIPTION
        "Represents the bytes of frames reception with this BSS."
    ::= { unisDot11BSSRxStatis64Entry 2 }

unisDot11BSSRx64DataFrameCnt OBJECT-TYPE
    SYNTAX      Counter64
    MAX-ACCESS  read-only
    STATUS      current
    DESCRIPTION
        "Represents the number of data frames reception with this BSS."
    ::= { unisDot11BSSRxStatis64Entry 3 }

unisDot11BSSRx64DataFrameBytes OBJECT-TYPE
    SYNTAX      Counter64
    MAX-ACCESS  read-only
    STATUS      current
    DESCRIPTION
        "Represents the bytes of data frames reception with this BSS."
    ::= { unisDot11BSSRxStatis64Entry 4 }

unisDot11BSSRx64AssocFrameCnt OBJECT-TYPE
    SYNTAX      Counter64
    MAX-ACCESS  read-only
    STATUS      current
    DESCRIPTION
        "Represents the number of associate frames reception with this BSS."
    ::= { unisDot11BSSRxStatis64Entry 5 }

unisDot11BSSRx64PayloadBytes OBJECT-TYPE
    SYNTAX      Counter64
    MAX-ACCESS  read-only
    STATUS      current
    DESCRIPTION
        "Represents the payload bytes of data frames reception with this BSS."
    ::= { unisDot11BSSRxStatis64Entry 6 }

unisDot11BSSRx64UniFrameCnt OBJECT-TYPE
    SYNTAX      Counter64
    MAX-ACCESS  read-only
    STATUS      current
    DESCRIPTION
        "Represents the number of unicast frames reception with this BSS."
    ::= { unisDot11BSSRxStatis64Entry 7 }

unisDot11BSSRx64NonUniFrameCnt  OBJECT-TYPE
    SYNTAX      Counter64
    MAX-ACCESS  read-only
    STATUS      current
    DESCRIPTION
        "Represents the number of non-unicast frames reception with this BSS."
    ::= { unisDot11BSSRxStatis64Entry 8 }

unisDot11BSSRx64AuthenFrameCnt OBJECT-TYPE
    SYNTAX      Counter64
    MAX-ACCESS  read-only
    STATUS      current
    DESCRIPTION
        "Represents the number of authentication frames reception with this BSS."
    ::= { unisDot11BSSRxStatis64Entry 9 }

-- *****************************************************************************
-- *  End of unisDot11BSSRxStatis64Table Definition
-- *****************************************************************************

-- *****************************************************************************
-- *  unisDot11BSSTxStatis64Table Definition
-- *****************************************************************************
unisDot11BSSTxStatis64Table OBJECT-TYPE
    SYNTAX      SEQUENCE OF UnisDot11BSSTxStatis64Entry
    MAX-ACCESS  not-accessible
    STATUS      current
    DESCRIPTION
        "The table will provide the transmission statistic for a
        specific BSS on a radio."
    ::= { unisDot11APStatisGroup 33 }

unisDot11BSSTxStatis64Entry OBJECT-TYPE
    SYNTAX      UnisDot11BSSTxStatis64Entry
    MAX-ACCESS  not-accessible
    STATUS      current
    DESCRIPTION
        "Each entry of the table will provide the transmission statistic data for
        each BSS on a specific radio."
    INDEX
        {
            unisDot11CurAPID,
            unisDot11RadioID,
            unisDot11WlanID
        }
    ::= { unisDot11BSSTxStatis64Table 1 }

UnisDot11BSSTxStatis64Entry ::= SEQUENCE
    {
        unisDot11BSSTx64FrameCnt             Counter64,
        unisDot11BSSTx64FrameBytes           Counter64,
        unisDot11BSSTx64DataFrameCnt         Counter64,
        unisDot11BSSTx64DataFrameBytes       Counter64,
        unisDot11BSSTx64AssocFrameCnt        Counter64,
        unisDot11BSSTx64PayloadBytes         Counter64,
        unisDot11BSSTx64RetryCnt             Counter64,
        unisDot11BSSTx64UniFrameCnt          Counter64,
        unisDot11BSSTx64NonUniFrameCnt       Counter64,
        unisDot11BSSTx64AuthenFrameCnt       Counter64
    }

unisDot11BSSTx64FrameCnt OBJECT-TYPE
    SYNTAX      Counter64
    MAX-ACCESS  read-only
    STATUS      current
    DESCRIPTION
        "Represents the total number of frames transmission with this BSS."
    ::= { unisDot11BSSTxStatis64Entry 1 }

unisDot11BSSTx64FrameBytes OBJECT-TYPE
    SYNTAX      Counter64
    MAX-ACCESS  read-only
    STATUS      current
    DESCRIPTION
        "Represents the total number of bytes transmission with this BSS."
    ::= { unisDot11BSSTxStatis64Entry 2 }

unisDot11BSSTx64DataFrameCnt OBJECT-TYPE
    SYNTAX      Counter64
    MAX-ACCESS  read-only
    STATUS      current
    DESCRIPTION
        "Represents the number of data frame transmission with this BSS."
    ::= { unisDot11BSSTxStatis64Entry 3 }

unisDot11BSSTx64DataFrameBytes OBJECT-TYPE
    SYNTAX      Counter64
    MAX-ACCESS  read-only
    STATUS      current
    DESCRIPTION
        "Represents the bytes of data frame transmission with this BSS."
    ::= { unisDot11BSSTxStatis64Entry 4 }

unisDot11BSSTx64AssocFrameCnt OBJECT-TYPE
    SYNTAX      Counter64
    MAX-ACCESS  read-only
    STATUS      current
    DESCRIPTION
        "Represents the number of associate frame transmission with this BSS."
    ::= { unisDot11BSSTxStatis64Entry 5 }

unisDot11BSSTx64PayloadBytes OBJECT-TYPE
    SYNTAX      Counter64
    MAX-ACCESS  read-only
    STATUS      current
    DESCRIPTION
        "Represents the payload bytes of data frame transmission with this BSS."
    ::= { unisDot11BSSTxStatis64Entry 6 }

unisDot11BSSTx64RetryCnt   OBJECT-TYPE
    SYNTAX      Counter64
    MAX-ACCESS  read-only
    STATUS      current
    DESCRIPTION
        "Represents the number of bytes retransmitted with this BSS."
    ::= { unisDot11BSSTxStatis64Entry 7 }

unisDot11BSSTx64UniFrameCnt OBJECT-TYPE
    SYNTAX      Counter64
    MAX-ACCESS  read-only
    STATUS      current
    DESCRIPTION
        "Represents the number of unicast frames transmission with this BSS."
    ::= { unisDot11BSSTxStatis64Entry 8 }

unisDot11BSSTx64NonUniFrameCnt OBJECT-TYPE
    SYNTAX      Counter64
    MAX-ACCESS  read-only
    STATUS      current
    DESCRIPTION
        "Represents the number of non-unicast frames transmission with this BSS."
    ::= { unisDot11BSSTxStatis64Entry 9 }

unisDot11BSSTx64AuthenFrameCnt OBJECT-TYPE
    SYNTAX      Counter64
    MAX-ACCESS  read-only
    STATUS      current
    DESCRIPTION
        "Represents the number of authentication frames transmission with this BSS."
    ::= { unisDot11BSSTxStatis64Entry 10 }

-- *****************************************************************************
-- *  End of unisDot11BSSTxStatis64Table Definition
-- *****************************************************************************

-- *****************************************************************************
-- *  unisDot11APPacketMCSRateStatis2Table Definition
-- *****************************************************************************
unisDot11APPacketMCSRateStatis2Table  OBJECT-TYPE
    SYNTAX        SEQUENCE OF UnisDot11APPacketMCSRateStatis2Entry
    MAX-ACCESS    not-accessible
    STATUS        current
    DESCRIPTION
        "This table provides packet statistics based on MCS rate."
    ::= { unisDot11APStatisGroup 34 }

unisDot11APPacketMCSRateStatis2Entry  OBJECT-TYPE
    SYNTAX        UnisDot11APPacketMCSRateStatis2Entry
    MAX-ACCESS    not-accessible
    STATUS        current
    DESCRIPTION
        "Each entry provides packet statistics based on MCS rate for each radio
        of a specific AP."
    INDEX
        {
            unisDot11CurAPID,
            unisDot11RadioID,
            unisDot11APPacketMCS2Rate
        }
    ::= { unisDot11APPacketMCSRateStatis2Table 1 }

UnisDot11APPacketMCSRateStatis2Entry  ::=SEQUENCE
    {
        unisDot11APPacketMCS2Rate          Integer32,
        unisDot11APRXPacketMCSRate2Count   Counter64,
        unisDot11APTXPacketMCSRate2Count   Counter64
    }

unisDot11APPacketMCS2Rate    OBJECT-TYPE
    SYNTAX        Integer32 (1..2000000000)
    MAX-ACCESS    not-accessible
    STATUS        current
    DESCRIPTION
        "Represents data transmission rate(Tenfold as actual rate)."
    ::= { unisDot11APPacketMCSRateStatis2Entry 1 }

unisDot11APRXPacketMCSRate2Count    OBJECT-TYPE
    SYNTAX        Counter64
    MAX-ACCESS    read-only
    STATUS        current
    DESCRIPTION
        "Represents the count of packets received based on data transmission rate."
    ::= { unisDot11APPacketMCSRateStatis2Entry 2 }

unisDot11APTXPacketMCSRate2Count    OBJECT-TYPE
    SYNTAX        Counter64
    MAX-ACCESS    read-only
    STATUS        current
    DESCRIPTION
        "Represents the count of packets transmitted base on data transmission rate."
    ::= { unisDot11APPacketMCSRateStatis2Entry 3 }

-- *****************************************************************************
-- *  End of unisDot11APPacketMcsRateStatis2Table Definition
-- *****************************************************************************

-- *****************************************************************************
-- *  unisDot11APUserSecAuthStatisCMTable Definition
-- *****************************************************************************
unisDot11APUserSecAuthStatisCMTable OBJECT-TYPE
    SYNTAX      SEQUENCE OF UnisDot11APUserSecAuthStatisCMEntry
    MAX-ACCESS  not-accessible
    STATUS      current
    DESCRIPTION
        "The table provides the user authentication statistics."
    ::= { unisDot11APStatisGroup 35 }

unisDot11APUserSecAuthStatisCMEntry OBJECT-TYPE
    SYNTAX      UnisDot11APUserSecAuthStatisCMEntry
    MAX-ACCESS  not-accessible
    STATUS      current
    DESCRIPTION
        "Each entry of the table provides the user authentication statistics
        of AP."
    INDEX
        {
            unisDot11CurAPID,
            unisDot11RadioID,
            unisDot11WlanID
       }
    ::= { unisDot11APUserSecAuthStatisCMTable 1 }

UnisDot11APUserSecAuthStatisCMEntry ::= SEQUENCE
    {
        unisDot11APUserConnFailCntCM              Counter32,
        unisDot11APUserAuthReqCntCM               Counter32,
        unisDot11APUserAuthSuccCntCM              Counter32,
        unisDot11APUserAuthFailCntCM              Counter32,
        unisDot11AllUserOnlineTimeCM              TimeTicks
    }

unisDot11APUserConnFailCntCM OBJECT-TYPE
    SYNTAX      Counter32
    MAX-ACCESS  read-only
    STATUS      current
    DESCRIPTION
        "Represents the failed connection count of users with this AP."
    ::= { unisDot11APUserSecAuthStatisCMEntry 1 }

unisDot11APUserAuthReqCntCM OBJECT-TYPE
    SYNTAX      Counter32
    MAX-ACCESS  read-only
    STATUS      current
    DESCRIPTION
        "Represents the total number of user authentication requests with this AP."
    ::= { unisDot11APUserSecAuthStatisCMEntry 2 }

unisDot11APUserAuthSuccCntCM OBJECT-TYPE
    SYNTAX      Counter32
    MAX-ACCESS  read-only
    STATUS      current
    DESCRIPTION
        "Represents the total number of successful user authentications with this AP."
    ::= { unisDot11APUserSecAuthStatisCMEntry 3 }

unisDot11APUserAuthFailCntCM OBJECT-TYPE
    SYNTAX      Counter32
    MAX-ACCESS  read-only
    STATUS      current
    DESCRIPTION
        "Represents the total number of failed user authentications with this AP."
    ::= { unisDot11APUserSecAuthStatisCMEntry 4 }

unisDot11AllUserOnlineTimeCM OBJECT-TYPE
    SYNTAX      TimeTicks
    MAX-ACCESS  read-only
    STATUS      current
    DESCRIPTION
        "Represents the online time of all users with this AP."
    ::= { unisDot11APUserSecAuthStatisCMEntry 5 }

-- *****************************************************************************
-- *  End of unisDot11APUserSecAuthStatisCMTable Definition
-- *****************************************************************************

-- *****************************************************************************
-- *  unisDot11APUserInfoStatis2CMTable Definition
-- *****************************************************************************
unisDot11APUserInfoStatis2CMTable OBJECT-TYPE
    SYNTAX      SEQUENCE OF UnisDot11APUserInfoStatis2CMEntry
    MAX-ACCESS  not-accessible
    STATUS      current
    DESCRIPTION
        "The table will provide the authentication user information statistic
        of this AP."
    ::= { unisDot11APStatisGroup 36 }

unisDot11APUserInfoStatis2CMEntry OBJECT-TYPE
    SYNTAX      UnisDot11APUserInfoStatis2CMEntry
    MAX-ACCESS  not-accessible
    STATUS      current
    DESCRIPTION
        "Each entry of the table will provide the authentication user information
        statistic of this AP."
    INDEX
        {
            unisDot11CurAPID,
            unisDot11APUserMacAddr2CM
        }
    ::= { unisDot11APUserInfoStatis2CMTable 1 }

UnisDot11APUserInfoStatis2CMEntry ::= SEQUENCE
    {
        unisDot11APUserMacAddr2CM                  MacAddress,
        unisDot11APUserIpAddr2CM                   IpAddress,
        unisDot11APUserLoginName2CM                OCTET STRING,
        unisDot11APUserLoginTime2CM                OCTET STRING,
        unisDot11APUserOnlineTime2CM               TimeTicks,
        unisDot11APUserAuthType2CM                 INTEGER,
        unisDot11APUserTxPacketCnt2CM              Counter32,
        unisDot11APUserTxBytes2CM                  Counter64,
        unisDot11APUserRxPacketCnt2CM              Counter32,
        unisDot11APUserRxBytes2CM                  Counter64,
        unisDot11APUserIPv6Addr2CM                 OCTET STRING,
        unisDot11APUserMac2CM                      MacAddress,
        unisDot11APUserInCirValueCM                Counter32,
        unisDot11APUserOutCirValueCM               Counter32
    }

unisDot11APUserMacAddr2CM OBJECT-TYPE
    SYNTAX      MacAddress
    MAX-ACCESS  not-accessible
    STATUS      current
    DESCRIPTION
        "Represents the mac address of authentication user logging to this AP."
    ::= { unisDot11APUserInfoStatis2CMEntry 1 }

unisDot11APUserIpAddr2CM OBJECT-TYPE
    SYNTAX      IpAddress
    MAX-ACCESS  read-only
    STATUS      current
    DESCRIPTION
        "Represents the ip address of authentication user logging to this AP."
    ::= { unisDot11APUserInfoStatis2CMEntry 2 }

unisDot11APUserLoginName2CM OBJECT-TYPE
    SYNTAX      OCTET STRING
    MAX-ACCESS  read-only
    STATUS      current
    DESCRIPTION
        "Represents the login name of authentication user logging to this AP."
    ::= { unisDot11APUserInfoStatis2CMEntry 3 }

unisDot11APUserLoginTime2CM OBJECT-TYPE
    SYNTAX      OCTET STRING
    MAX-ACCESS  read-only
    STATUS      current
    DESCRIPTION
        "Represents the login time of authentication user with this AP."
    ::= { unisDot11APUserInfoStatis2CMEntry 4 }

unisDot11APUserOnlineTime2CM OBJECT-TYPE
    SYNTAX      TimeTicks
    MAX-ACCESS  read-only
    STATUS      current
    DESCRIPTION
        "Represents how long authentication user has been online."
    ::= { unisDot11APUserInfoStatis2CMEntry 5 }

unisDot11APUserAuthType2CM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { unisDot11APUserInfoStatis2CMEntry 6 }

unisDot11APUserTxPacketCnt2CM OBJECT-TYPE
    SYNTAX      Counter32
    MAX-ACCESS  read-only
    STATUS      current
    DESCRIPTION
        "Represents the total count of packets sent to online users."
    ::= { unisDot11APUserInfoStatis2CMEntry 7 }

unisDot11APUserTxBytes2CM OBJECT-TYPE
    SYNTAX      Counter64
    MAX-ACCESS  read-only
    STATUS      current
    DESCRIPTION
        "Represents the total bytes sent to online users."
    ::= { unisDot11APUserInfoStatis2CMEntry 8 }

unisDot11APUserRxPacketCnt2CM OBJECT-TYPE
    SYNTAX      Counter32
    MAX-ACCESS  read-only
    STATUS      current
    DESCRIPTION
        "Represents the total count of packets received from online users."
    ::= { unisDot11APUserInfoStatis2CMEntry 9 }

unisDot11APUserRxBytes2CM OBJECT-TYPE
    SYNTAX      Counter64
    MAX-ACCESS  read-only
    STATUS      current
    DESCRIPTION
        "Represents the total bytes received from online users."
    ::= { unisDot11APUserInfoStatis2CMEntry 10 }

unisDot11APUserIPv6Addr2CM OBJECT-TYPE
    SYNTAX      OCTET STRING
    MAX-ACCESS  read-only
    STATUS      current
    DESCRIPTION
        "Represents the IPv6 address of online users."
    ::= { unisDot11APUserInfoStatis2CMEntry 11 }

unisDot11APUserMac2CM OBJECT-TYPE
    SYNTAX      MacAddress
    MAX-ACCESS  read-only
    STATUS      current
    DESCRIPTION
        "Represents the mac address of authentication user logging to this AP."
    ::= { unisDot11APUserInfoStatis2CMEntry 12 }

unisDot11APUserInCirValueCM OBJECT-TYPE
    SYNTAX      Counter32
    MAX-ACCESS  read-only
    STATUS      current
    DESCRIPTION
        "Represents the CIR of inbound direction of this user."
    ::= { unisDot11APUserInfoStatis2CMEntry 13 }

unisDot11APUserOutCirValueCM OBJECT-TYPE
    SYNTAX      Counter32
    MAX-ACCESS  read-only
    STATUS      current
    DESCRIPTION
        "Represents the CIR of outbound direction of this user."
    ::= { unisDot11APUserInfoStatis2CMEntry 14 }

-- *****************************************************************************
-- *  End of unisDot11APUserInfoStatis2CMTable Definition
-- *****************************************************************************

-- *****************************************************************************
-- *  AP Management Notifications Definition
-- *****************************************************************************
-- AP Management Notification

        unisDot11APMtTraps OBJECT IDENTIFIER
    ::= { unisDot11APMtNotifyGroup 0 }

unisDot11APMtWorkModeChgTrap NOTIFICATION-TYPE
    OBJECTS
        {
            unisDot11APID,
            unisDot11APChgWorkMode,
            unisDot11APMtTrapAPMacAddress
        }
    STATUS      current
    DESCRIPTION
        "The notification will be sent when AP changes the work mode, and
         unisDot11APWorkMode suggests which work mode will be used by AP."
    ::= { unisDot11APMtTraps 1 }

unisDot11APMtCfgErrorTrap NOTIFICATION-TYPE
    OBJECTS
        {
            unisDot11APID,
            unisDot11RadioID,
            unisDot11APMtTrapCfgErrReason
        }
    STATUS      current
    DESCRIPTION
        "The notification will represent errors caused by the
        configuration operation of AP."
    ::= { unisDot11APMtTraps 2 }

unisDot11APMtRadioFailTrap NOTIFICATION-TYPE
    OBJECTS
        {
            unisDot11APID,
            unisDot11RadioID,
            unisDot11APMtTrapRadioFailReason
        }
    STATUS      current
    DESCRIPTION
        "The notification will notify which the operational status
        of radio becomes down."
    ::= { unisDot11APMtTraps 3 }

unisDot11APMtRadioFailRecoverTrap NOTIFICATION-TYPE
    OBJECTS
        {
            unisDot11APID,
            unisDot11RadioID
        }
    STATUS      current
    DESCRIPTION
        "The notification will notify the operational status of which radio
        becomes up again."
    ::= { unisDot11APMtTraps 4 }

unisDot11APMtRdoChanlChgTrap NOTIFICATION-TYPE
    OBJECTS
        {
            unisDot11APID,
            unisDot11RadioID,
            unisDot11APChannelChgMode,
            unisDot11APMtTrapOldChannel,
            unisDot11APMtTrapNewChannel,
            unisDot11APMtChanlChgCount,
            unisDot11APMtTrapAPMacAddress
        }
    STATUS      current
    DESCRIPTION
        "The notification will represent which radio changes the channel."
    ::= { unisDot11APMtTraps 5 }

unisDot11APMtTimeSynFail NOTIFICATION-TYPE
    OBJECTS
        {
            unisDot11APID
        }
    STATUS      current
    DESCRIPTION
        "The notification will be sent when AC and AP failed to
        synchronize their time."
    ::= { unisDot11APMtTraps 6 }

unisDot11APMtChlIntfDetected NOTIFICATION-TYPE
    OBJECTS
        {
            unisDot11Channel
        }
    STATUS      current
    DESCRIPTION
        "The notification will be sent when some ambient device interferes with
        current channel."
    ::= { unisDot11APMtTraps 7 }

unisDot11APMtIntfAPDetected NOTIFICATION-TYPE
    OBJECTS
        {
            unisDot11Channel,
            unisDot11APIntfDevMACAddress
        }
    STATUS current
    DESCRIPTION
        "The notification will be sent when some ambient AP interferes with
        current channel."
    ::= { unisDot11APMtTraps 8 }

unisDot11APMtIntfStaDetected NOTIFICATION-TYPE
    OBJECTS
        {
            unisDot11Channel,
            unisDot11APIntfDevMACAddress
        }
    STATUS current
    DESCRIPTION
        "The notification will be sent when some ambient station interferes with
        current channel."
    ::= { unisDot11APMtTraps 9 }

unisDot11APMtIPChange NOTIFICATION-TYPE
    OBJECTS
        {
            unisDot11APIPAddress,
            unisDot11APMtTrapOldIPAddr
        }
    STATUS current
    DESCRIPTION
        "The notification will be sent when IP address of the AP changes."
    ::= { unisDot11APMtTraps 10 }

unisDot11APFlashWriteFailure NOTIFICATION-TYPE
    OBJECTS
        {
            unisDot11APID,
            unisDot11APMtFormerApVersion,
            unisDot11APMtTrapAPMacAddress
        }
    STATUS      current
    DESCRIPTION
        "The notification will be sent when AP failed to write data
        into flash."
    ::= { unisDot11APMtTraps 11 }

unisDot11APSysReboot NOTIFICATION-TYPE
    OBJECTS
        {
            unisDot11APID
        }
    STATUS current
    DESCRIPTION
        "The notification will be sent when AP reboots."
    ::= { unisDot11APMtTraps 12 }

unisDot11APMtAvailChlTooLow NOTIFICATION-TYPE
    OBJECTS
        {
            unisDot11RadioID,
            unisDot11APMtAPID,
            unisDot11APMtTrapAPMacAddress
        }
    STATUS current
    DESCRIPTION
        "The notification will be sent when number of available channels is
         too low.
        "
    ::= { unisDot11APMtTraps 13 }

unisDot11APImgDwldSuccess NOTIFICATION-TYPE
    OBJECTS
        {
            unisDot11CurrAPName,
            unisDot11CurrAPIPAddress,
            unisDot11CurrAPSoftwareVersion
        }
    STATUS current
    DESCRIPTION
        "The notification will be sent when AP succeeds to download image from
        AC.
        "
    ::= { unisDot11APMtTraps 14 }

unisDot11APInterfDetectedTrap NOTIFICATION-TYPE
    OBJECTS
        {
            unisDot11Channel,
            unisDot11CurrInterfDetectedNum,
            unisDot11InterfMacList
        }
    STATUS current
    DESCRIPTION
        "This notification will be sent when some ambient AP interferes with
         current channel."
    ::= { unisDot11APMtTraps 15 }

unisDot11APInterfClearTrap NOTIFICATION-TYPE
    OBJECTS
        {
            unisDot11Channel,
            unisDot11APMtAPID,
            unisDot11APMtRadioID,
            unisDot11APMtInterfMacAdd,
            unisDot11APMtFirstTrapTime,
            unisDot11APMtTrapAPMacAddress
        }
    STATUS current
    DESCRIPTION
        "This notification will be sent when interference caused by ambient
         APs on the current channel disappears."
    ::= { unisDot11APMtTraps 16 }

unisDot11StaInterfDetectedTrap NOTIFICATION-TYPE
    OBJECTS
        {
            unisDot11Channel,
            unisDot11CurrInterfDetectedNum,
            unisDot11InterfMacList,
            unisDot11APMtFirstTrapTime
        }
    STATUS current
    DESCRIPTION
        "This notification will be sent when interference caused by ambient
         STAs on the current channel disappears."
    ::= { unisDot11APMtTraps 17 }

unisDot11StaInterfClearTrap NOTIFICATION-TYPE
    OBJECTS
        {
            unisDot11Channel,
            unisDot11APMtAPID,
            unisDot11APMtRadioID,
            unisDot11APMtInterfMacAdd,
            unisDot11APMtFirstTrapTime,
            unisDot11APMtTrapAPMacAddress
        }
    STATUS current
    DESCRIPTION
        "This notification will be sent when interference caused by ambient
         devices on the current channel happens."
    ::= { unisDot11APMtTraps 18 }

unisDot11OtherDevIntDetectedTrap NOTIFICATION-TYPE
    OBJECTS
        {
            unisDot11Channel,
            unisDot11APMtFirstTrapTime
        }
    STATUS      current
    DESCRIPTION
        "This notification will be sent when interference caused by ambient
         devices on the current channel disappears."
    ::= { unisDot11APMtTraps 19 }

unisDot11OtherDevIntClearTrap NOTIFICATION-TYPE
    OBJECTS
        {
            unisDot11Channel,
            unisDot11APMtAPID,
            unisDot11APMtRadioID,
            unisDot11APMtFirstTrapTime,
            unisDot11APMtTrapAPMacAddress
        }
    STATUS      current
    DESCRIPTION
        "This notification will be sent when previous ambient device disappeared with
         the same channel."
    ::= { unisDot11APMtTraps 20 }

unisDot11APModuleTroubleTrap NOTIFICATION-TYPE
    OBJECTS
        {
            unisDot11RadioID,
            unisDot11APMtAPID,
            unisDot11APMtTrapAPMacAddress
        }
    STATUS current
    DESCRIPTION
        "This notification will be sent when WLAN module failed."
    ::= { unisDot11APMtTraps 21 }

unisDot11APModuleTroubleClearTrap NOTIFICATION-TYPE
    OBJECTS
        {
            unisDot11RadioID,
            unisDot11APMtAPID,
            unisDot11APMtTrapAPMacAddress
        }
    STATUS current
    DESCRIPTION
        "The notification will be sent when WLAN module recovered."
    ::= { unisDot11APMtTraps 22 }

unisDot11APRadioDownTrap NOTIFICATION-TYPE
    OBJECTS
        {
            unisDot11RadioID,
            unisDot11APRadioDownReason,
            unisDot11APMtAPID,
            unisDot11APMtFirstTrapTime,
            unisDot11APMtTrapAPMacAddress
        }
    STATUS current
    DESCRIPTION
        "This notification will be sent when WLAN links interrupted."
    ::= { unisDot11APMtTraps 23 }

unisDot11APRadioDownRecovTrap NOTIFICATION-TYPE
    OBJECTS
        {
            unisDot11RadioID,
            unisDot11APMtAPID,
            unisDot11APMtFirstTrapTime,
            unisDot11APMtTrapAPMacAddress
        }
    STATUS current
    DESCRIPTION
        "This notification will be sent when WLAN links recover."
    ::= { unisDot11APMtTraps 24 }

unisDot11APStaFullTrap NOTIFICATION-TYPE
    OBJECTS
        {
            unisDot11APID,
            unisDot11StaLimitNumber,
            unisDot11StaFullReason,
            unisDot11APMtFirstTrapTime,
            unisDot11APMtTrapAPMacAddress
        }
    STATUS current
    DESCRIPTION
        "This notification will be sent when STA number reach limit number."
    ::= { unisDot11APMtTraps 25 }

unisDot11APStaFullRecoverTrap NOTIFICATION-TYPE
    OBJECTS
        {
            unisDot11APID,
            unisDot11StaLimitNumber,
            unisDot11StaFullReason,
            unisDot11APMtFirstTrapTime,
            unisDot11APMtTrapAPMacAddress
        }
    STATUS current
    DESCRIPTION
        "This notification will be sent when STA number recover enough level."
    ::= { unisDot11APMtTraps 26 }

unisDot11DFSFreeCntBelowThrRecov NOTIFICATION-TYPE
    OBJECTS
        {
            unisDot11RadioID,
            unisDot11APMtAPID,
            unisDot11APMtTrapAPMacAddress
        }
    STATUS current
    DESCRIPTION
        "This notification will be sent when available channels number
        recover enough level."
    ::= { unisDot11APMtTraps 27 }

unisDot11APCpuUsageHigh NOTIFICATION-TYPE
    OBJECTS
        {
            unisDot11APID,
            unisDot11APCPURTUsage,
            unisDot11APMtFirstTrapTime,
            unisDot11APMtTrapAPMacAddress
        }
    STATUS current
    DESCRIPTION
        "The notification will be sent when the AP CPU usage exceeds the
         threshold.
        "
    ::= { unisDot11APMtTraps 28 }

unisDot11APCpuUsageHighRecover NOTIFICATION-TYPE
    OBJECTS
        {
            unisDot11APID,
            unisDot11APCPURTUsage,
            unisDot11APMtFirstTrapTime,
            unisDot11APMtTrapAPMacAddress
        }
    STATUS current
    DESCRIPTION
        "The notification will be sent when the AP CPU usage descends the
         threshold.
        "
    ::= { unisDot11APMtTraps 29 }

unisDot11APMemUsageHigh NOTIFICATION-TYPE
    OBJECTS
        {
            unisDot11APID,
            unisDot11APMemRTUsage,
            unisDot11APMtFirstTrapTime,
            unisDot11APMtTrapAPMacAddress
        }
    STATUS current
    DESCRIPTION
        "The notification will be sent when the AP memory usage exceeds the
         threshold.
        "
    ::= { unisDot11APMtTraps 30 }

unisDot11APMemUsageHighRecover NOTIFICATION-TYPE
    OBJECTS
        {
            unisDot11APID,
            unisDot11APMemRTUsage,
            unisDot11APMtFirstTrapTime,
            unisDot11APMtTrapAPMacAddress
        }
    STATUS current
    DESCRIPTION
        "The notification will be sent when the AP memory usage descends the
         threshold.
         "
    ::= { unisDot11APMtTraps 31 }

unisDot11APTrapUserCntExceedThre NOTIFICATION-TYPE
    OBJECTS
        {
            unisDot11APID,
            unisDot11APTrapUserCnt,
            unisDot11APTrapUserThreshold
        }
    STATUS      current
    DESCRIPTION
        "The notification will be sent when the online user counter exceeds
        the threshold."
    ::= { unisDot11APMtTraps 32 }

unisDot11APMtDetectedIntfAP NOTIFICATION-TYPE
    OBJECTS
        {
            unisDot11APMtAPID,
            unisDot11APMtRadioID,
            unisDot11APMtChannel,
            unisDot11APMtInterfMacAdd,
            unisDot11APMtFirstTrapTime,
            unisDot11APMtTrapAPMacAddress
        }
    STATUS current
    DESCRIPTION
        "This notification will be sent when some ambient AP interferes with
         current channel."
    ::= { unisDot11APMtTraps 33 }

unisDot11APMtDetectedIntfSTA NOTIFICATION-TYPE
    OBJECTS
        {
            unisDot11APMtAPID,
            unisDot11APMtRadioID,
            unisDot11APMtChannel,
            unisDot11APMtInterfMacAdd,
            unisDot11APMtFirstTrapTime,
            unisDot11APMtTrapAPMacAddress
        }
    STATUS current
    DESCRIPTION
        "This notification will be sent when some ambient STA interferes with
         current channel."
    ::= { unisDot11APMtTraps 34 }

unisDot11APMtDetectedIntfOtherDev NOTIFICATION-TYPE
    OBJECTS
        {
            unisDot11APMtAPID,
            unisDot11APMtRadioID,
            unisDot11APMtChannel,
            unisDot11APMtTrapAPMacAddress
        }
    STATUS      current
    DESCRIPTION
        "This notification will be sent when other device interferes with
         current channel."
    ::= { unisDot11APMtTraps 35 }

unisDot11DetcAdjChlIntfAP NOTIFICATION-TYPE
    OBJECTS
        {
            unisDot11APMtAPID,
            unisDot11APMtRadioID,
            unisDot11APMtChannel,
            unisDot11APMtAdjChannel,
            unisDot11APMtInterfMacAdd,
            unisDot11APMtFirstTrapTime
        }
    STATUS current
    DESCRIPTION
        "This notification will be sent when some ambient AP interferes with
         adjacent channel."
    ::= { unisDot11APMtTraps 36 }

unisDot11DetcAdjChlIntfAPClear NOTIFICATION-TYPE
    OBJECTS
        {
            unisDot11APMtAPID,
            unisDot11APMtRadioID,
            unisDot11APMtChannel,
            unisDot11APMtAdjChannel,
            unisDot11APMtInterfMacAdd,
            unisDot11APMtFirstTrapTime
        }
    STATUS current
    DESCRIPTION
        "This notification will be sent when interference caused by ambient
         APs on the adjacent channel disappears."
    ::= { unisDot11APMtTraps 37 }

unisDot11APPowerOffTrap NOTIFICATION-TYPE
    OBJECTS
        {
            unisDot11APMtAPID
        }
    STATUS current
    DESCRIPTION
        "This notification will be sent when AP is power-off."
    ::= { unisDot11APMtTraps 38 }

unisDot11APPowerOnTrap NOTIFICATION-TYPE
    OBJECTS
        {
            unisDot11APMtAPID
        }
    STATUS current
    DESCRIPTION
        "This notification will be sent when AP is power-on."
    ::= { unisDot11APMtTraps 39 }

unisDot11UpLinkSwitchTrap NOTIFICATION-TYPE
    OBJECTS
        {
            unisDot11APMtAPID,
            unisDot11APMtUpLinkSwitchInfo,
            unisDot11APMtTrapAPMacAddress,
            unisDot11APMtUpLinkSwitchTime,
            unisDot11APMtOldCellId,
            unisDot11APMtCurCellId,
            unisDot11APMtOldBand,
            unisDot11APMtActiveBand
        }
    STATUS current
    DESCRIPTION
        "This notification will be sent when uplink switches to 3G or 4G."
    ::= { unisDot11APMtTraps 40 }

-- AP Management Notification variable object

unisDot11APMtTrapVarObjects OBJECT IDENTIFIER
    ::= { unisDot11APMtNotifyGroup 1 }

unisDot11APMtTrapCfgErrReason OBJECT-TYPE
    SYNTAX      UnisDot11NotifyReasonType
    MAX-ACCESS  accessible-for-notify
    STATUS      current
    DESCRIPTION
        "Represents errors caused by configuration operation."
    ::= { unisDot11APMtTrapVarObjects 1 }

unisDot11APMtTrapRadioFailReason OBJECT-TYPE
    SYNTAX      INTEGER
        {
            config(1),
            uniserror(2),
            swerror(3),
            radar(4),
            unknown(8)
        }
    MAX-ACCESS  accessible-for-notify
    STATUS      current
    DESCRIPTION
        "Represents errors caused by configuration operation.
        The following values are supported:
        config     - Configuration error
        uniserror  - Hardware error
        swerror    - Software error
        radar      - Radar Detection
        unknown    - Unknown reason"
    ::= { unisDot11APMtTrapVarObjects 2 }

unisDot11APMtTrapOldChannel OBJECT-TYPE
    SYNTAX      UnisDot11ChannelScopeType
    MAX-ACCESS  accessible-for-notify
    STATUS      current
    DESCRIPTION
        "Represents which channel the radio used to use."
    ::= { unisDot11APMtTrapVarObjects 3 }

unisDot11APMtTrapNewChannel OBJECT-TYPE
    SYNTAX      UnisDot11ChannelScopeType
    MAX-ACCESS  accessible-for-notify
    STATUS      current
    DESCRIPTION
        "Represents which channel the radio will use."
    ::= { unisDot11APMtTrapVarObjects 4 }

unisDot11APChannelChgMode OBJECT-TYPE
    SYNTAX      UnisDot11RFModeType
    MAX-ACCESS  accessible-for-notify
    STATUS      current
    DESCRIPTION
        "Represents the channel change mode for a radio."
    ::= { unisDot11APMtTrapVarObjects 5 }

unisDot11APChgWorkMode OBJECT-TYPE
    SYNTAX      INTEGER
        {
            normal(1),
            monitor(2),
            hybrid(3)
        }
    MAX-ACCESS  accessible-for-notify
    STATUS      current
    DESCRIPTION
        "Represents what work mode for AP.
        The following values are supported:
        normal  - AP will supply WLAN service.
        monitor - AP will be a monitor to detect attack.
        hybrid  - AP will supply WLAN service and detect attack."
    ::= { unisDot11APMtTrapVarObjects 6 }

unisDot11APIntfDevMACAddress OBJECT-TYPE
    SYNTAX      MacAddress
    MAX-ACCESS  accessible-for-notify
    STATUS      current
    DESCRIPTION
        "Represents MAC address of the device which triggers the notification."
    ::= { unisDot11APMtTrapVarObjects 7 }

unisDot11APMtTrapOldIPAddr OBJECT-TYPE
    SYNTAX      IpAddress
    MAX-ACCESS  accessible-for-notify
    STATUS      current
    DESCRIPTION
        "Represents the IP address of AP."
    ::= { unisDot11APMtTrapVarObjects 8 }

unisDot11CurrInterfDetectedNum OBJECT-TYPE
    SYNTAX      Integer32
    MAX-ACCESS  accessible-for-notify
    STATUS      current
    DESCRIPTION
        "Represents the number of interfere detected."
    ::= { unisDot11APMtTrapVarObjects 9 }

unisDot11StaFullReason OBJECT-TYPE
    SYNTAX      INTEGER
        {
            ap(1),
            bss(2),
            radio(3),
            radioConcur(4),
            radiopolicy(5),
            ac(6),
            acConcur(7),
            aid(8)
        }
    MAX-ACCESS  accessible-for-notify
    STATUS      current
    DESCRIPTION
        "Reports which kind maximum number of STA
         is reached.  New STA is not able to associate."
    ::= { unisDot11APMtTrapVarObjects 10 }

unisDot11StaLimitNumber OBJECT-TYPE
    SYNTAX      Integer32
    MAX-ACCESS  accessible-for-notify
    STATUS      current
    DESCRIPTION
        "Represents the limit number of STA."
    ::= { unisDot11APMtTrapVarObjects 11 }

unisDot11APRadioDownReason OBJECT-TYPE
    SYNTAX  INTEGER
        {
            phyicalUnusable(1),
            configDisable(2),
            operatinUnusable(3),
            apTunnelDown(4)
        }
    MAX-ACCESS  accessible-for-notify
    STATUS      current
    DESCRIPTION
        "Reports the reason why WLAN links is interrupted."
    ::= { unisDot11APMtTrapVarObjects 12 }

unisDot11InterfMacList OBJECT-TYPE
    SYNTAX      OCTET STRING
    MAX-ACCESS  accessible-for-notify
    STATUS      current
    DESCRIPTION
        "Represents MAC address list of interfere detected."
    ::= { unisDot11APMtTrapVarObjects 13 }

unisDot11APTrapUserCnt OBJECT-TYPE
    SYNTAX      Integer32
    MAX-ACCESS  accessible-for-notify
    STATUS      current
    DESCRIPTION
        "Represents the online user counter of AP."
    ::= { unisDot11APMtTrapVarObjects 14 }

unisDot11APTrapUserThreshold OBJECT-TYPE
    SYNTAX      Integer32
    MAX-ACCESS  accessible-for-notify
    STATUS      current
    DESCRIPTION
        "Represents threshold of AP's online user counter."
    ::= { unisDot11APMtTrapVarObjects 15 }

unisDot11APMtChanlChgCount OBJECT-TYPE
    SYNTAX      Integer32
    MAX-ACCESS  accessible-for-notify
    STATUS      current
    DESCRIPTION
        "Represents how many times that channel changed."
    ::= { unisDot11APMtTrapVarObjects 16 }

unisDot11APMtFormerApVersion OBJECT-TYPE
    SYNTAX      OCTET STRING
    MAX-ACCESS  accessible-for-notify
    STATUS      current
    DESCRIPTION
        "Represents former software version of AP."
    ::= { unisDot11APMtTrapVarObjects 17 }

unisDot11APMtAPID OBJECT-TYPE
    SYNTAX      UnisDot11ObjectIDType
    MAX-ACCESS  accessible-for-notify
    STATUS      current
    DESCRIPTION
        "To uniquely identify each AP."
    ::= { unisDot11APMtTrapVarObjects 18 }

unisDot11APMtRadioID OBJECT-TYPE
    SYNTAX      UnisDot11RadioScopeType
    MAX-ACCESS  accessible-for-notify
    STATUS      current
    DESCRIPTION
        "Represents each radio."
    ::= { unisDot11APMtTrapVarObjects 19 }

unisDot11APMtChannel OBJECT-TYPE
    SYNTAX      UnisDot11ChannelScopeType
    MAX-ACCESS  accessible-for-notify
    STATUS      current
    DESCRIPTION
        "Represents the current channel allocation for radio."
    ::= { unisDot11APMtTrapVarObjects 20 }

unisDot11APMtInterfMacAdd OBJECT-TYPE
    SYNTAX      MacAddress
    MAX-ACCESS  accessible-for-notify
    STATUS      current
    DESCRIPTION
        "Represents the MAC address of an AP."
    ::= { unisDot11APMtTrapVarObjects 21 }

unisDot11APMtAdjChannel OBJECT-TYPE
    SYNTAX      UnisDot11ChannelScopeType
    MAX-ACCESS  accessible-for-notify
    STATUS      current
    DESCRIPTION
        "Represents the adjacent channel of radio."
    ::= { unisDot11APMtTrapVarObjects 22 }

unisDot11APMtFirstTrapTime OBJECT-TYPE
    SYNTAX      TimeTicks
    MAX-ACCESS  accessible-for-notify
    STATUS      current
    DESCRIPTION
        "Represents the first trap time."
    ::= { unisDot11APMtTrapVarObjects 23 }

unisDot11APMtTrapAPMacAddress OBJECT-TYPE
    SYNTAX      MacAddress
    MAX-ACCESS  accessible-for-notify
    STATUS      current
    DESCRIPTION
        "Represents the MAC address of an AP."
    ::= {unisDot11APMtTrapVarObjects 24}

unisDot11APMtUpLinkSwitchInfo OBJECT-TYPE
    SYNTAX      INTEGER
        {
            unknown(1),
            tdscdma(2),
            tdlte(3)
        }
    MAX-ACCESS  accessible-for-notify
    STATUS      current
    DESCRIPTION
        "Represents the type which uplink switches to.
        The following values are supported:
        TDSCDMA - The uplink switches to TDSCDMA.
        TDLTE - The uplink switches to TDLTE.
        unknown - Unknown uplink type."
    ::= {unisDot11APMtTrapVarObjects 25}

unisDot11APMtUpLinkSwitchTime OBJECT-TYPE
    SYNTAX      TimeStamp
    MAX-ACCESS  accessible-for-notify
    STATUS      current
    DESCRIPTION
        "Represents the time when uplink switches."
    ::= { unisDot11APMtTrapVarObjects 26 }

unisDot11APMtOldCellId OBJECT-TYPE
    SYNTAX      Integer32
    MAX-ACCESS  accessible-for-notify
    STATUS      current
    DESCRIPTION
        "Represents the cell id before uplink switch."
    ::= { unisDot11APMtTrapVarObjects 27 }

unisDot11APMtCurCellId OBJECT-TYPE
    SYNTAX      Integer32
    MAX-ACCESS  accessible-for-notify
    STATUS      current
    DESCRIPTION
        "Represents the cell id after uplink switch."
    ::= { unisDot11APMtTrapVarObjects 28 }

unisDot11APMtOldBand OBJECT-TYPE
    SYNTAX      OCTET STRING
    MAX-ACCESS  accessible-for-notify
    STATUS      current
    DESCRIPTION
        "Represents the band before uplink switch."
    ::= { unisDot11APMtTrapVarObjects 29 }

unisDot11APMtActiveBand OBJECT-TYPE
    SYNTAX      OCTET STRING
    MAX-ACCESS  accessible-for-notify
    STATUS      current
    DESCRIPTION
        "Represents the band after uplink switch."
    ::= { unisDot11APMtTrapVarObjects 30 }

-- *****************************************************************************
-- *  End of AP Management Notification  Definition
-- *****************************************************************************
END
