-- ============================================================================
-- Copyright (c) 2020 Unisyue Technologies Co., Ltd.  All rights reserved.
--
-- Description: Flowtemplate Management Information Base.
-- Reference: 
-- Version: 1.0
-- History:
-- V1.0 created by tangshun.
-- ============================================================================
UNIS-FLOWTEMPLATE-MIB DEFINITIONS ::= BEGIN

        IMPORTS
            unisCommon
                FROM UNIS-OID-MIB
            ifIndex
                FROM RFC1213-MIB
            Integer32, OBJECT-TYPE, MODULE-IDENTITY
                FROM SNMPv2-SMI
            RowStatus, MacAddress
                FROM SNMPv2-TC;

--
-- Nodes definitions
--
        unisFlowTemplate MODULE-IDENTITY 
            LAST-UPDATED "200511241320Z"    -- Nov 24, 2005 at 13:20 GMT
            ORGANIZATION
                "Unisyue Technologies Co., Ltd."
            CONTACT-INFO
                ""
            DESCRIPTION 
                "Flow template management information base."
            ::= { unisCommon 64 }

        unisFlowTemplateMibObject OBJECT IDENTIFIER ::= { unisFlowTemplate 1 }

        unisFTConfigGroup OBJECT IDENTIFIER ::= { unisFlowTemplateMibObject 1 }

        unisFTGroupNextIndex OBJECT-TYPE
            SYNTAX Integer32
            MAX-ACCESS read-only
            STATUS current
            DESCRIPTION
                "This object contains an appropriate value to be used for unisFTGroupIndex 
                 when creating rows in the unisFTGroupTable.  If it is 2147483647, 
                 it denotes that unisFTGroupTable can't create any instance. 
                "
            ::= { unisFTConfigGroup 1 }    

        unisFTGroupTable OBJECT-TYPE   
            SYNTAX SEQUENCE OF UnisFTGroupEntry
            MAX-ACCESS not-accessible
            STATUS current
            DESCRIPTION
                "A table of flow template group.
                 A flow template group, which is applied to interface,
                 must use unisFTGroupTable to create a instance 
                 and unisFTBasicGroupTable or unisFTExtendGroupTable 
                 to configure flow template's need item.
                 A basic flow template must use unisFTBasicGroupTable 
                 to configure some basic flow template's need item, 
                 such as: address, protocol, priority.
                 A extend flow template must use unisFTExtendGroupTable
                 to configure packet's type and offset and length.
                "
            ::= { unisFTConfigGroup 2 }

        unisFTGroupEntry OBJECT-TYPE
            SYNTAX UnisFTGroupEntry
            MAX-ACCESS not-accessible
            STATUS current
            DESCRIPTION
                "Flow template group information."
            INDEX { unisFTGroupIndex }
            ::= { unisFTGroupTable 1 }

        UnisFTGroupEntry ::=
            SEQUENCE
            {
                unisFTGroupIndex
                    Integer32,
                unisFTGroupName
                    OCTET STRING,
                unisFTGroupType
                    INTEGER,
                unisFTGroupRowStatus
                    RowStatus
            }

        unisFTGroupIndex OBJECT-TYPE
            SYNTAX Integer32
            MAX-ACCESS not-accessible
            STATUS current
            DESCRIPTION
                "Flow template group index."
            ::= { unisFTGroupEntry 1 }

        unisFTGroupName OBJECT-TYPE
            SYNTAX OCTET STRING (SIZE(1..31))
            MAX-ACCESS read-create
            STATUS current
            DESCRIPTION
                "Flow template group name."
            ::= { unisFTGroupEntry 2 }

        unisFTGroupType OBJECT-TYPE
            SYNTAX INTEGER 
            {
                basic(1),
                extend(2)
            }
            MAX-ACCESS read-create
            STATUS current
            DESCRIPTION
                "Type of flow template."
            ::= { unisFTGroupEntry 3 }

        unisFTGroupRowStatus OBJECT-TYPE
            SYNTAX RowStatus
            MAX-ACCESS read-create
            STATUS current
            DESCRIPTION
                "RowStatus."
            ::= { unisFTGroupEntry 4 }
--
--nodes of unisFTBasicGroupTable
--
        unisFTBasicGroupTable OBJECT-TYPE   
            SYNTAX SEQUENCE OF UnisFTBasicGroupEntry
            MAX-ACCESS not-accessible
            STATUS current
            DESCRIPTION
                "A table of basic flow template group."
            ::= { unisFTConfigGroup 3 }

        unisFTBasicGroupEntry OBJECT-TYPE
            SYNTAX UnisFTBasicGroupEntry
            MAX-ACCESS not-accessible
            STATUS current
            DESCRIPTION
                "Basic flow template group information."
            INDEX { unisFTGroupIndex }
            ::= { unisFTBasicGroupTable 1 }

        UnisFTBasicGroupEntry ::=
            SEQUENCE
            {
                unisFTBasicGroupAddressType
                    BITS,
                unisFTBasicGroupPriorityType
                    BITS,
                unisFTBasicGroupProtocolType
                    BITS,
                unisFTBasicGroupSMacWildCard
                    MacAddress,
                unisFTBasicGroupDMacWildCard
                    MacAddress,
                unisFTBasicGroupRowStatus
                    RowStatus
            }

        unisFTBasicGroupAddressType OBJECT-TYPE
            SYNTAX BITS
            {
                sourceIpv4Address(0),
                destIPv4Address(1),
                sourceIPv6Address(2),
                destIPv6Address(3),
                sourceMacAddress(4),
                destMacAddress(5)
            }
            MAX-ACCESS read-create
            STATUS current
            DESCRIPTION
                "Type of MAC and IP address.
                 This is a bit-map of possible conditions.
                 The various bit positions are:
                 sourceIpv4Address    source IPv4's address    
                 destIPv4Address      destination IPv4's address
                 sourceIPv6Address    source IPv6 address
                 destIPv6Address      destination IPv6 address
                 sourceMacAddress     source MAC address
                 destMacAddress       destination MAC address
                "
            ::= { unisFTBasicGroupEntry 1 }

        unisFTBasicGroupPriorityType OBJECT-TYPE
            SYNTAX BITS
            {
                vlanID(0),
                cos(1),
                topVlanID(2),
                topCos(3),
                fragment(4),
                tcpFlag(5),
                tos(6),
                dscp(7),
                ipprecedence(8)
            }
            MAX-ACCESS read-create
            STATUS current
            DESCRIPTION
                "Type of priority.
                 This is a bit-map of possible conditions.
                 The various bit positions are:
                 vlanID         VlanID
                 cos            802.1p priority
                 topVlanID      VlanID of top layer
                 topCos         802.1p priority of top layer
                 fragment       fragment
                 tcpFlag        TCP flag
                 tos            type of service
                 dscp           DSCP
                 ipprecedence   IP precedence
                "
            ::= { unisFTBasicGroupEntry 2 }

        unisFTBasicGroupProtocolType OBJECT-TYPE
            SYNTAX BITS
            {
                l2Potocol(0),
                ipv4L3Protocol(1),
                ipv6L3Protocol(2),
                icmpProtocolType(3),
                icmpProtocolCode(4),
                icmpv6ProtocolType(5),
                icmpv6ProtocolCode(6),
                sourceL4Port(7),
                destL4Port(8)
            }
            MAX-ACCESS read-create
            STATUS current
            DESCRIPTION
                "Type of protocol.
                 This is a bit-map of possible conditions.
                 The various bit positions are:
                 l2Potocol               layer 2 protocol
                 ipv4L3Protocol          layer 3 protocol of IPv4 
                 ipv6L3Protocol          layer 3 protocol of IPv6
                 icmpProtocolType        Type of ICMP protocol of IPv4
                 icmpProtocolCode        Code of ICMP protocol of IPv4
                 icmpv6ProtocolType      Type of ICMP protocol of IPv6
                 icmpv6ProtocolCode      Code of ICMP protocol of IPv6
                 sourceL4Port            port of layer 4 of source
                 destL4Port              port of layer 4 of destination
                "
            ::= { unisFTBasicGroupEntry 3 }

        unisFTBasicGroupSMacWildCard OBJECT-TYPE
            SYNTAX MacAddress
            MAX-ACCESS read-create
            STATUS current
            DESCRIPTION
                "Source MAC address field in Ethernet packet head."
            ::= { unisFTBasicGroupEntry 4 }

        unisFTBasicGroupDMacWildCard OBJECT-TYPE
            SYNTAX MacAddress
            MAX-ACCESS read-create
            STATUS current
            DESCRIPTION
                "Destination MAC address field in Ethernet packet head."
            ::= { unisFTBasicGroupEntry 5 }

        unisFTBasicGroupRowStatus OBJECT-TYPE
            SYNTAX RowStatus
            MAX-ACCESS read-create
            STATUS current
            DESCRIPTION
                "RowStatus."
            ::= { unisFTBasicGroupEntry 6 }
--
--nodes of unisFTExtendGroupTable
--
        unisFTExtendGroupTable OBJECT-TYPE
            SYNTAX SEQUENCE OF UnisFTExtendGroupEntry
            MAX-ACCESS not-accessible
            STATUS current
            DESCRIPTION
                "A table of extend flow template group information."
            ::= { unisFTConfigGroup 4 }

        unisFTExtendGroupEntry OBJECT-TYPE
            SYNTAX UnisFTExtendGroupEntry
            MAX-ACCESS not-accessible
            STATUS current
            DESCRIPTION
                "Extend flow template group information entry."
            INDEX { unisFTGroupIndex, unisFTExtendGroupOffsetType }
            ::= { unisFTExtendGroupTable 1 }

        UnisFTExtendGroupEntry ::=
            SEQUENCE
            {
                unisFTExtendGroupOffsetType
                    INTEGER,
                unisFTExtendGroupOffsetMaxValue
                    Integer32,
                unisFTExtendGroupLengthMaxValue
                    Integer32,
                unisFTExtendGroupRowStatus
                    RowStatus
            }

        unisFTExtendGroupOffsetType OBJECT-TYPE
            SYNTAX INTEGER
            {
                start(1),
                mpls(2),
                l2(3),
                l4(4),
                l5(5),
                ipv4(6),
                ipv6(7)
            }
            MAX-ACCESS not-accessible
            STATUS current
            DESCRIPTION
                "Offset type of the packet.
                 start    Offset from the start of the packet
                 mpls     Offset from the head of MPLS
                 l2       Offset from the head of the L2 frame
                 l4       Offset from the head of L4 packet
                 l5       Offset from the head of the L5 packet
                 ipv4     Offset from the head of the IPv4 packet
                 ipv6     Offset from the head of the IPv6 packet
                "
            ::= { unisFTExtendGroupEntry 1 }

        unisFTExtendGroupOffsetMaxValue OBJECT-TYPE
            SYNTAX Integer32
            MAX-ACCESS read-create
            STATUS current
            DESCRIPTION
                "The max value of offset."
            ::= { unisFTExtendGroupEntry 2 }    

        unisFTExtendGroupLengthMaxValue OBJECT-TYPE
            SYNTAX Integer32
            MAX-ACCESS read-create
            STATUS current
            DESCRIPTION
                "The max value of length."
            ::= { unisFTExtendGroupEntry 3 }

        unisFTExtendGroupRowStatus OBJECT-TYPE
            SYNTAX RowStatus
            MAX-ACCESS read-create
            STATUS current
            DESCRIPTION
                "RowStatus."
            ::= { unisFTExtendGroupEntry 4 }

--
--nodes of unisFTApplyGroup
--
        unisFTApplyGroup OBJECT IDENTIFIER ::= { unisFlowTemplateMibObject 2 }

        unisFTIfApplyTable OBJECT-TYPE
            SYNTAX SEQUENCE OF UnisFTIfApplyEntry
            MAX-ACCESS not-accessible
            STATUS current
            DESCRIPTION
                "A table of any interface with flowtemplate.
                 A flow template, which will be applied interface,
                 is an instance at unisFTGroupTable 
                 and unisFTBasicGroupTable or unisFTExtendGroupTable.
                 A basic flow template is an instance at unisFTGroupTable 
                 and unisFTBasicGroupTable, and the instance's RowStatus 
                 must be 'active' at each table.
                 A extend flow template is an instance at unisFTGroupTable
                 and unisFTExtendGroupTable, and the instance's RowStatus 
                 must be 'active' at each table.  
                "
            ::= { unisFTApplyGroup 1 }

        unisFTIfApplyEntry OBJECT-TYPE
            SYNTAX UnisFTIfApplyEntry
            MAX-ACCESS not-accessible
            STATUS current
            DESCRIPTION
                "Any interface with flowtemplate information." 
            INDEX { ifIndex, unisFTGroupIndex }
            ::= { unisFTIfApplyTable 1 } 

        UnisFTIfApplyEntry ::=
            SEQUENCE
            {
                unisFTIfApplyGroupName
                    OCTET STRING,
                unisFTIfApplyRowStatus
                    RowStatus
            }

        unisFTIfApplyGroupName OBJECT-TYPE
            SYNTAX OCTET STRING
            MAX-ACCESS read-only
            STATUS current
            DESCRIPTION
                "The name of flow template."
            ::= { unisFTIfApplyEntry 1 }

        unisFTIfApplyRowStatus OBJECT-TYPE
            SYNTAX RowStatus
            MAX-ACCESS read-create
            STATUS current
            DESCRIPTION
                "RowStatus."
            ::= { unisFTIfApplyEntry 2 }
END
