-- =================================================================
-- Copyright (c) 2020 Unisyue Technologies Co., Ltd.  All rights reserved.
--
-- Description: Private MIB File For LB
-- Reference:
-- Version: V1.3
-- History:
-- V1.0  2013-11 Initial Version created by y04448.
-- V1.1  2014-04 updated by yuhongqiang.
--       Change MAX-ACCESS from not-accessible to accessible-for-notify for the
--       following MIB nodes:
--         unisLBv2RSStatChassis, unisLBv2RSStatSlot, unisLBv2RSStatCpuid.
--       Add the following MIB nodes:
--         unisLBv2RSConnectionsLimit, unisLBv2RSConnectionsRateLimit,
--         unisLBv2RSStatConnectionsRate.
--       Add the following trap nodes:
--         unisLBv2RSConnOverloadTrap, unisLBv2RSConnRecoveryTrap,
--         unisLBv2RSConnsRateOverloadTrap, unisLBv2RSConnsRateRecoveryTrap.
--       Change the description of unisLBv2VSConnsRateRecoveryTrap.
-- V1.2  2016-11 modified description of unisLBv2VSActiveTrap, unisLBv2VSInactiveTrap,
--         unisLBv2RSAvailableTrap, unisLBv2RSUnavailableTrap, unisLBv2SFActiveTrap,
--         unisLBv2SFInactiveTrap, unisLBv2ActionInUseSFChangeTrap, unisLBv2VSInUseSFChangeTrap  by l08992.
-- V1.3  2019-05 updated by m16825.
--         Add the following MIB table:
--         unisLBv2GlobalStatsTable
--       Add the following MIB nodes:
--         unisLBv2GlobalStatChassis,unisLBv2GlobalStatSlot,unisLBv2GlobalStatCpuid,
--         unisLBv2GlobalStatTotalConnections, unisLBv2GlobalStatActiveConnections,unisLBv2GlobalStatConnectionsRate.
-- =================================================================
UNIS-LBV2-MIB DEFINITIONS ::= BEGIN

IMPORTS
    unisCommon
        FROM UNIS-OID-MIB
    MODULE-IDENTITY, OBJECT-TYPE, Unsigned32, Counter64, NOTIFICATION-TYPE, Gauge32
        FROM SNMPv2-SMI         -- [RFC2578]
    RowStatus, DisplayString
        FROM SNMPv2-TC;         -- [RFC2578]

unisLBv2 MODULE-IDENTITY
    LAST-UPDATED "201905130000Z"
    ORGANIZATION
        "Unisyue Technologies Co., Ltd."
    CONTACT-INFO
        ""
    DESCRIPTION
        "The private MIB file includes the LB information of
         the device."
    REVISION      "201905130000Z"
    DESCRIPTION
        "Add MIB table unisLBv2GlobalStatsTable."
    REVISION      "201311010000Z"
    DESCRIPTION
        "Initial revision of this MIB module."
    ::= { unisCommon 148 }

unisLBv2GlobalObjects OBJECT IDENTIFIER ::= { unisLBv2 1 }

unisLBv2TrapEnable OBJECT-TYPE
    SYNTAX      INTEGER {
         enabled     (1),
         disabled    (2)
    }
    MAX-ACCESS  read-write
    STATUS      current
    DESCRIPTION
        "Indicates whether the module of LB will generate
         traps for events defined in this MIB.  'enabled'
         results in SNMP traps; 'disabled', no traps are sent."
    DEFVAL { enabled }
    ::= { unisLBv2GlobalObjects 1 }

unisLBv2GlobalStatsTable OBJECT-TYPE
-- =================================================================
--    LB Global Statistic Table
-- =================================================================
    SYNTAX SEQUENCE OF UnisLBv2GlobalStatsEntry
    MAX-ACCESS  not-accessible
    STATUS      current
    DESCRIPTION
        "Global statistic table for LB."
  ::= { unisLBv2GlobalObjects 2 }

unisLBv2GlobalStatsEntry OBJECT-TYPE
    SYNTAX      UnisLBv2GlobalStatsEntry
    MAX-ACCESS  not-accessible
    STATUS      current
    DESCRIPTION
        "An entry contains the statistic information of LB."
    INDEX {
            unisLBv2GlobalStatChassis,
            unisLBv2GlobalStatSlot,
            unisLBv2GlobalStatCpuid
          }
    ::= { unisLBv2GlobalStatsTable 1 }

UnisLBv2GlobalStatsEntry  ::=
    SEQUENCE{
        unisLBv2GlobalStatChassis                  Unsigned32,
        unisLBv2GlobalStatSlot                     Unsigned32,
        unisLBv2GlobalStatCpuid                    Unsigned32,
        unisLBv2GlobalStatTotalConnections         Counter64,
        unisLBv2GlobalStatActiveConnections        Gauge32,
        unisLBv2GlobalStatConnectionsRate          Gauge32
    }

unisLBv2GlobalStatChassis OBJECT-TYPE
    SYNTAX      Unsigned32(0..255)
    MAX-ACCESS  not-accessible
    STATUS      current
    DESCRIPTION
        "ID of the device that holds the card."
    ::= { unisLBv2GlobalStatsEntry 1 }

unisLBv2GlobalStatSlot OBJECT-TYPE
    SYNTAX      Unsigned32(0..255)
    MAX-ACCESS  not-accessible
    STATUS      current
    DESCRIPTION
        "Member ID of the card on device."
    ::= { unisLBv2GlobalStatsEntry 2 }

unisLBv2GlobalStatCpuid OBJECT-TYPE
    SYNTAX      Unsigned32(0..255)
    MAX-ACCESS  not-accessible
    STATUS      current
    DESCRIPTION
        "ID of the CPU on the card."
    ::= { unisLBv2GlobalStatsEntry 3 }

unisLBv2GlobalStatTotalConnections OBJECT-TYPE
    SYNTAX      Counter64
    MAX-ACCESS  read-only
    STATUS      current
    DESCRIPTION
        "Total number of connections of LB."
    ::= { unisLBv2GlobalStatsEntry 4 }

unisLBv2GlobalStatActiveConnections OBJECT-TYPE
    SYNTAX      Gauge32
    MAX-ACCESS  read-only
    STATUS      current
    DESCRIPTION
        "Active connections of LB."
    ::= { unisLBv2GlobalStatsEntry 5}

unisLBv2GlobalStatConnectionsRate OBJECT-TYPE
    SYNTAX      Gauge32
    UNITS       "cps"
    MAX-ACCESS  read-only
    STATUS      current
    DESCRIPTION
        "Connection rate of LB."
    ::= { unisLBv2GlobalStatsEntry 6 }

unisLBv2ActionTables OBJECT IDENTIFIER ::= { unisLBv2 2 }
-- =================================================================
--    LB Action Table
-- =================================================================
unisLBv2ActionTable OBJECT-TYPE
    SYNTAX SEQUENCE OF UnisLBv2ActionEntry
    MAX-ACCESS  not-accessible
    STATUS      current
    DESCRIPTION
        "Action table for LB."
    ::= { unisLBv2ActionTables 1 }

unisLBv2ActionEntry OBJECT-TYPE
    SYNTAX      UnisLBv2ActionEntry
    MAX-ACCESS  not-accessible
    STATUS      current
    DESCRIPTION
        "An entry contains the information of the action."
    INDEX {
            unisLBv2ActionName
          }
    ::= { unisLBv2ActionTable 1 }

UnisLBv2ActionEntry  ::=
    SEQUENCE{
        unisLBv2ActionName                     DisplayString,
        unisLBv2ActionDefaultSF                DisplayString,
        unisLBv2ActionBackupSF                 DisplayString,
        unisLBv2ActionInUseSF                  DisplayString,
        unisLBv2ActionRowStatus                RowStatus
    }

unisLBv2ActionName OBJECT-TYPE
    SYNTAX      DisplayString(SIZE(1..63))
    MAX-ACCESS  accessible-for-notify
    STATUS      current
    DESCRIPTION
        "Name of the action."
    ::= { unisLBv2ActionEntry 1 }

unisLBv2ActionDefaultSF OBJECT-TYPE
    SYNTAX      DisplayString(SIZE(0..63))
    MAX-ACCESS  read-create
    STATUS      current
    DESCRIPTION
        "Default server farm quoted by the action.  A zero length
         string indicates no default server farm has been assigned."
    ::= { unisLBv2ActionEntry 2 }

unisLBv2ActionBackupSF OBJECT-TYPE
    SYNTAX      DisplayString(SIZE(0..63))
    MAX-ACCESS  read-create
    STATUS      current
    DESCRIPTION
        "Backup server farm quoted by the action.  A zero length
         string indicates no backup server farm has been assigned."
    ::= { unisLBv2ActionEntry 3 }

unisLBv2ActionInUseSF OBJECT-TYPE
    SYNTAX      DisplayString(SIZE(0..63))
    MAX-ACCESS  read-only
    STATUS      current
    DESCRIPTION
        "Server farm in use quoted by the action."
    ::= { unisLBv2ActionEntry 4 }

unisLBv2ActionRowStatus OBJECT-TYPE
    SYNTAX      RowStatus
    MAX-ACCESS  read-create
    STATUS      current
    DESCRIPTION
        "Status of this conceptual row.  When create an action, default
         server farm and backup server farm are optional."
    ::= { unisLBv2ActionEntry 5 }

unisLBv2VSTables OBJECT IDENTIFIER ::= { unisLBv2 3 }
-- =================================================================
--    LB Virtual Server Table
-- =================================================================
unisLBv2VSTable OBJECT-TYPE
    SYNTAX SEQUENCE OF UnisLBv2VSEntry
    MAX-ACCESS  not-accessible
    STATUS      current
    DESCRIPTION
        "Virtual server table for LB."
    ::= { unisLBv2VSTables 1 }

unisLBv2VSEntry OBJECT-TYPE
    SYNTAX      UnisLBv2VSEntry
    MAX-ACCESS  not-accessible
    STATUS      current
    DESCRIPTION
        "An entry contains the information of the virtual server."
    INDEX {
            unisLBv2VSName
          }
    ::= { unisLBv2VSTable 1 }

UnisLBv2VSEntry  ::=
    SEQUENCE{
        unisLBv2VSName                         DisplayString,
        unisLBv2VSConnectionsLimit             Unsigned32,
        unisLBv2VSConnectionsRateLimit         Unsigned32,
        unisLBv2VSDefaultSF                    DisplayString,
        unisLBv2VSBackupSF                     DisplayString,
        unisLBv2VSInUseSF                      DisplayString,
        unisLBv2VSRowStatus                    RowStatus
    }

unisLBv2VSName OBJECT-TYPE
    SYNTAX      DisplayString(SIZE(1..63))
    MAX-ACCESS  accessible-for-notify
    STATUS      current
    DESCRIPTION
        "Name of the virtual server."
    ::= { unisLBv2VSEntry 1 }

unisLBv2VSConnectionsLimit OBJECT-TYPE
    SYNTAX      Unsigned32
    MAX-ACCESS  read-create
    STATUS      current
    DESCRIPTION
        "Max connections limit of the virtual server.  0 means there is
         no limit."
    DEFVAL { 0 }
    ::= { unisLBv2VSEntry 2 }

unisLBv2VSConnectionsRateLimit OBJECT-TYPE
    SYNTAX      Unsigned32
    MAX-ACCESS  read-create
    STATUS      current
    DESCRIPTION
        "Max connections rate limit of the virtual server.  0 means there is
         no limit."
    DEFVAL { 0 }
    ::= { unisLBv2VSEntry 3 }

unisLBv2VSDefaultSF OBJECT-TYPE
    SYNTAX      DisplayString(SIZE(0..63))
    MAX-ACCESS  read-create
    STATUS      current
    DESCRIPTION
        "Default server farm quoted by the virtual server.  A zero length
         string indicates no default server farm has been assigned."
    ::= { unisLBv2VSEntry 4 }

unisLBv2VSBackupSF OBJECT-TYPE
    SYNTAX      DisplayString(SIZE(0..63))
    MAX-ACCESS  read-create
    STATUS      current
    DESCRIPTION
        "Backup server farm quoted by the virtual server.  A zero length
         string indicates no backup server farm has been assigned."
    ::= { unisLBv2VSEntry 5 }

unisLBv2VSInUseSF OBJECT-TYPE
    SYNTAX      DisplayString(SIZE(0..63))
    MAX-ACCESS  read-only
    STATUS      current
    DESCRIPTION
        "Server farm in use quoted by the virtual server."
    ::= { unisLBv2VSEntry 6 }

unisLBv2VSRowStatus OBJECT-TYPE
    SYNTAX      RowStatus
    MAX-ACCESS  read-create
    STATUS      current
    DESCRIPTION
        "Status of this conceptual row.  When create an virtual server,
         default server farm and backup server farm are optional."
    ::= { unisLBv2VSEntry 7 }

-- =================================================================
--    LB Virtual Server Statistic Table
-- =================================================================
unisLBv2VSStatsTable OBJECT-TYPE
    SYNTAX SEQUENCE OF UnisLBv2VSStatsEntry
    MAX-ACCESS  not-accessible
    STATUS      current
    DESCRIPTION
        "Virtual server statistic table for LB."
    ::= { unisLBv2VSTables 2 }

unisLBv2VSStatsEntry OBJECT-TYPE
    SYNTAX      UnisLBv2VSStatsEntry
    MAX-ACCESS  not-accessible
    STATUS      current
    DESCRIPTION
        "An entry contains the statistic information of the virtual server."
    INDEX {
            unisLBv2VSName,
            unisLBv2VSStatChassis,
            unisLBv2VSStatSlot,
            unisLBv2VSStatCpuid
          }
    ::= { unisLBv2VSStatsTable 1 }

UnisLBv2VSStatsEntry  ::=
    SEQUENCE{
        unisLBv2VSStatChassis                  Unsigned32,
        unisLBv2VSStatSlot                     Unsigned32,
        unisLBv2VSStatCpuid                    Unsigned32,
        unisLBv2VSStatTotalConnections         Counter64,
        unisLBv2VSStatActiveConnections        Unsigned32,
        unisLBv2VSStatClientSidePKTsIn         Counter64,
        unisLBv2VSStatClientSidePKTsOut        Counter64,
        unisLBv2VSStatDroppedPackets           Counter64,
        unisLBv2VSStatClientSideBytesIn        Counter64,
        unisLBv2VSStatClientSideBytesOut       Counter64,
        unisLBv2VSStatReceivedRequests         Counter64,
        unisLBv2VSStatSentResponses            Counter64,
        unisLBv2VSStatConnectionsRate          Unsigned32
    }

unisLBv2VSStatChassis OBJECT-TYPE
    SYNTAX      Unsigned32(0..255)
    MAX-ACCESS  accessible-for-notify
    STATUS      current
    DESCRIPTION
        "ID of the device that holds the card."
    ::= { unisLBv2VSStatsEntry 1 }

unisLBv2VSStatSlot OBJECT-TYPE
    SYNTAX      Unsigned32(0..255)
    MAX-ACCESS  accessible-for-notify
    STATUS      current
    DESCRIPTION
        "Member ID of the card on device."
    ::= { unisLBv2VSStatsEntry 2 }

unisLBv2VSStatCpuid OBJECT-TYPE
    SYNTAX      Unsigned32(0..255)
    MAX-ACCESS  accessible-for-notify
    STATUS      current
    DESCRIPTION
        "ID of the CPU on the card."
    ::= { unisLBv2VSStatsEntry 3 }

unisLBv2VSStatTotalConnections OBJECT-TYPE
    SYNTAX      Counter64
    MAX-ACCESS  read-only
    STATUS      current
    DESCRIPTION
        "Total number of connections that the virtual server received."
    ::= { unisLBv2VSStatsEntry 4 }

unisLBv2VSStatActiveConnections OBJECT-TYPE
    SYNTAX      Unsigned32
    MAX-ACCESS  read-only
    STATUS      current
    DESCRIPTION
        "Active connections that the virtual server received."
    ::= { unisLBv2VSStatsEntry 5 }

unisLBv2VSStatClientSidePKTsIn OBJECT-TYPE
    SYNTAX      Counter64
    MAX-ACCESS  read-only
    STATUS      current
    DESCRIPTION
        "Number of packets that the virtual server received from client."
    ::= { unisLBv2VSStatsEntry 6 }

unisLBv2VSStatClientSidePKTsOut OBJECT-TYPE
    SYNTAX      Counter64
    MAX-ACCESS  read-only
    STATUS      current
    DESCRIPTION
        "Number of packets that the virtual server sent to client."
    ::= { unisLBv2VSStatsEntry 7 }

unisLBv2VSStatDroppedPackets OBJECT-TYPE
    SYNTAX      Counter64
    MAX-ACCESS  read-only
    STATUS      current
    DESCRIPTION
        "Number of packets that the virtual server dropped."
    ::= { unisLBv2VSStatsEntry 8 }

unisLBv2VSStatClientSideBytesIn OBJECT-TYPE
    SYNTAX      Counter64
    UNITS       "byte"
    MAX-ACCESS  read-only
    STATUS      current
    DESCRIPTION
        "Number of bytes that the virtual server received from client."
    ::= { unisLBv2VSStatsEntry 9 }

unisLBv2VSStatClientSideBytesOut OBJECT-TYPE
    SYNTAX      Counter64
    UNITS       "byte"
    MAX-ACCESS  read-only
    STATUS      current
    DESCRIPTION
        "Number of bytes that the virtual server sent to client."
    ::= { unisLBv2VSStatsEntry 10 }

unisLBv2VSStatReceivedRequests OBJECT-TYPE
    SYNTAX      Counter64
    MAX-ACCESS  read-only
    STATUS      current
    DESCRIPTION
        "Number of requests that the virtual server received from client."
    ::= { unisLBv2VSStatsEntry 11 }

unisLBv2VSStatSentResponses OBJECT-TYPE
    SYNTAX      Counter64
    MAX-ACCESS  read-only
    STATUS      current
    DESCRIPTION
        "Number of responses that the virtual server sent to client."
    ::= { unisLBv2VSStatsEntry 12 }

unisLBv2VSStatConnectionsRate OBJECT-TYPE
    SYNTAX      Unsigned32
    UNITS       "cps"
    MAX-ACCESS  read-only
    STATUS      current
    DESCRIPTION
        "Connections rate of the virtual server."
    ::= { unisLBv2VSStatsEntry 13 }

unisLBv2RSTables OBJECT IDENTIFIER ::= { unisLBv2 4 }
-- =================================================================
--    LB Real Server Table
-- =================================================================
unisLBv2RSTable OBJECT-TYPE
    SYNTAX SEQUENCE OF UnisLBv2RSEntry
    MAX-ACCESS  not-accessible
    STATUS      current
    DESCRIPTION
        "Real server table for LB."
    ::= { unisLBv2RSTables 1 }

unisLBv2RSEntry OBJECT-TYPE
    SYNTAX      UnisLBv2RSEntry
    MAX-ACCESS  not-accessible
    STATUS      current
    DESCRIPTION
        "An entry contains the information of the real server."
    INDEX {
            unisLBv2RSName
          }
    ::= { unisLBv2RSTable 1 }

UnisLBv2RSEntry  ::=
    SEQUENCE{
        unisLBv2RSName                         DisplayString,
        unisLBv2RSRowStatus                    RowStatus,
        unisLBv2RSConnectionsLimit             Unsigned32,
        unisLBv2RSConnectionsRateLimit         Unsigned32
    }

unisLBv2RSName OBJECT-TYPE
    SYNTAX      DisplayString(SIZE(1..63))
    MAX-ACCESS  accessible-for-notify
    STATUS      current
    DESCRIPTION
        "Name of the real server."
    ::= { unisLBv2RSEntry 1 }

unisLBv2RSRowStatus OBJECT-TYPE
    SYNTAX      RowStatus
    MAX-ACCESS  read-create
    STATUS      current
    DESCRIPTION
        "Status of this conceptual row."
    ::= { unisLBv2RSEntry 2 }

unisLBv2RSConnectionsLimit OBJECT-TYPE
    SYNTAX      Unsigned32
    MAX-ACCESS  read-create
    STATUS      current
    DESCRIPTION
        "Max connections limit of the real server.  0 means there is
         no limit."
    DEFVAL { 0 }
    ::= { unisLBv2RSEntry 3 }

unisLBv2RSConnectionsRateLimit OBJECT-TYPE
    SYNTAX      Unsigned32
    MAX-ACCESS  read-create
    STATUS      current
    DESCRIPTION
        "Max connections rate limit of the real server.  0 means there is
         no limit."
    DEFVAL { 0 }
    ::= { unisLBv2RSEntry 4 }

-- =================================================================
--    LB Real Server Statistic Table
-- =================================================================
unisLBv2RSStatsTable OBJECT-TYPE
    SYNTAX SEQUENCE OF UnisLBv2RSStatsEntry
    MAX-ACCESS  not-accessible
    STATUS      current
    DESCRIPTION
        "Real server statistic table for LB."
    ::= { unisLBv2RSTables 2 }

unisLBv2RSStatsEntry OBJECT-TYPE
    SYNTAX      UnisLBv2RSStatsEntry
    MAX-ACCESS  not-accessible
    STATUS      current
    DESCRIPTION
        "An entry contains the statistic information of the real server."
    INDEX {
            unisLBv2RSName,
            unisLBv2RSStatChassis,
            unisLBv2RSStatSlot,
            unisLBv2RSStatCpuid
          }
    ::= { unisLBv2RSStatsTable 1 }

UnisLBv2RSStatsEntry  ::=
    SEQUENCE{
        unisLBv2RSStatChassis                  Unsigned32,
        unisLBv2RSStatSlot                     Unsigned32,
        unisLBv2RSStatCpuid                    Unsigned32,
        unisLBv2RSStatTotalConnections         Counter64,
        unisLBv2RSStatActiveConnections        Unsigned32,
        unisLBv2RSStatServerSidePKTsIn         Counter64,
        unisLBv2RSStatServerSidePKTsOut        Counter64,
        unisLBv2RSStatDroppedPackets           Counter64,
        unisLBv2RSStatServerSideBytesIn        Counter64,
        unisLBv2RSStatServerSideBytesOut       Counter64,
        unisLBv2RSStatReceivedRequests         Counter64,
        unisLBv2RSStatSentResponses            Counter64,
        unisLBv2RSStatConnectionsRate          Unsigned32
    }

unisLBv2RSStatChassis OBJECT-TYPE
    SYNTAX      Unsigned32(0..255)
    MAX-ACCESS  accessible-for-notify
    STATUS      current
    DESCRIPTION
        "ID of the device that holds the card."
    ::= { unisLBv2RSStatsEntry 1 }

unisLBv2RSStatSlot OBJECT-TYPE
    SYNTAX      Unsigned32(0..255)
    MAX-ACCESS  accessible-for-notify
    STATUS      current
    DESCRIPTION
        "Member ID of the card on device."
    ::= { unisLBv2RSStatsEntry 2 }

unisLBv2RSStatCpuid OBJECT-TYPE
    SYNTAX      Unsigned32(0..255)
    MAX-ACCESS  accessible-for-notify
    STATUS      current
    DESCRIPTION
        "ID of the CPU on the card."
    ::= { unisLBv2RSStatsEntry 3 }

unisLBv2RSStatTotalConnections OBJECT-TYPE
    SYNTAX      Counter64
    MAX-ACCESS  read-only
    STATUS      current
    DESCRIPTION
        "Total number of connections that the real server received."
    ::= { unisLBv2RSStatsEntry 4 }

unisLBv2RSStatActiveConnections OBJECT-TYPE
    SYNTAX      Unsigned32
    MAX-ACCESS  read-only
    STATUS      current
    DESCRIPTION
        "Active connections that the real server received."
    ::= { unisLBv2RSStatsEntry 5 }

unisLBv2RSStatServerSidePKTsIn OBJECT-TYPE
    SYNTAX      Counter64
    MAX-ACCESS  read-only
    STATUS      current
    DESCRIPTION
        "Number of packets that the real server received from device."
    ::= { unisLBv2RSStatsEntry 6 }

unisLBv2RSStatServerSidePKTsOut OBJECT-TYPE
    SYNTAX      Counter64
    MAX-ACCESS  read-only
    STATUS      current
    DESCRIPTION
        "Number of packets that the real server sent."
    ::= { unisLBv2RSStatsEntry 7 }

unisLBv2RSStatDroppedPackets OBJECT-TYPE
    SYNTAX      Counter64
    MAX-ACCESS  read-only
    STATUS      current
    DESCRIPTION
        "Number of packets that the real server dropped."
    ::= { unisLBv2RSStatsEntry 8 }

unisLBv2RSStatServerSideBytesIn OBJECT-TYPE
    SYNTAX      Counter64
    UNITS       "byte"
    MAX-ACCESS  read-only
    STATUS      current
    DESCRIPTION
        "Number of bytes that the real server received from device."
    ::= { unisLBv2RSStatsEntry 9 }

unisLBv2RSStatServerSideBytesOut OBJECT-TYPE
    SYNTAX      Counter64
    UNITS       "byte"
    MAX-ACCESS  read-only
    STATUS      current
    DESCRIPTION
        "Number of bytes that the real server sent."
    ::= { unisLBv2RSStatsEntry 10 }

unisLBv2RSStatReceivedRequests OBJECT-TYPE
    SYNTAX      Counter64
    MAX-ACCESS  read-only
    STATUS      current
    DESCRIPTION
        "Number of requests that the real server received from device."
    ::= { unisLBv2RSStatsEntry 11 }

unisLBv2RSStatSentResponses OBJECT-TYPE
    SYNTAX      Counter64
    MAX-ACCESS  read-only
    STATUS      current
    DESCRIPTION
        "Number of responses that the real server sent to device."
    ::= { unisLBv2RSStatsEntry 12 }

unisLBv2RSStatConnectionsRate OBJECT-TYPE
    SYNTAX      Unsigned32
    UNITS       "cps"
    MAX-ACCESS  read-only
    STATUS      current
    DESCRIPTION
        "Connections rate of the real server."
    ::= { unisLBv2RSStatsEntry 13 }

unisLBv2SFTables OBJECT IDENTIFIER ::= { unisLBv2 5 }
-- =================================================================
--    LB Server Farm Table
-- =================================================================
unisLBv2SFTable OBJECT-TYPE
    SYNTAX SEQUENCE OF UnisLBv2SFEntry
    MAX-ACCESS  not-accessible
    STATUS      current
    DESCRIPTION
        "Server farm table for LB."
    ::= { unisLBv2SFTables 1 }

unisLBv2SFEntry OBJECT-TYPE
    SYNTAX      UnisLBv2SFEntry
    MAX-ACCESS  not-accessible
    STATUS      current
    DESCRIPTION
        "An entry contains the information of the server farm."
    INDEX {
            unisLBv2SFName
          }
    ::= { unisLBv2SFTable 1 }

UnisLBv2SFEntry  ::=
    SEQUENCE{
        unisLBv2SFName                         DisplayString,
        unisLBv2SFRowStatus                    RowStatus
    }

unisLBv2SFName OBJECT-TYPE
    SYNTAX      DisplayString(SIZE(1..63))
    MAX-ACCESS  accessible-for-notify
    STATUS      current
    DESCRIPTION
        "Name of the server farm."
    ::= { unisLBv2SFEntry 1 }

unisLBv2SFRowStatus OBJECT-TYPE
    SYNTAX      RowStatus
    MAX-ACCESS  read-create
    STATUS      current
    DESCRIPTION
        "Status of this conceptual row."
    ::= { unisLBv2SFEntry 2 }

-- =================================================================
--    LB Server Farm Statistic Table
-- =================================================================
unisLBv2SFStatsTable OBJECT-TYPE
    SYNTAX SEQUENCE OF UnisLBv2SFStatsEntry
    MAX-ACCESS  not-accessible
    STATUS      current
    DESCRIPTION
        "Server farm statistic for LB."
    ::= { unisLBv2SFTables 2 }

unisLBv2SFStatsEntry OBJECT-TYPE
    SYNTAX      UnisLBv2SFStatsEntry
    MAX-ACCESS  not-accessible
    STATUS      current
    DESCRIPTION
        "An entry contains the statistic information of the server farm."
    INDEX {
            unisLBv2SFName,
            unisLBv2SFStatChassis,
            unisLBv2SFStatSlot,
            unisLBv2SFStatCpuid
          }
    ::= { unisLBv2SFStatsTable 1 }

UnisLBv2SFStatsEntry  ::=
    SEQUENCE{
        unisLBv2SFStatChassis                  Unsigned32,
        unisLBv2SFStatSlot                     Unsigned32,
        unisLBv2SFStatCpuid                    Unsigned32,
        unisLBv2SFStatTotalConnections         Counter64,
        unisLBv2SFStatActiveConnections        Unsigned32,
        unisLBv2SFStatServerSidePKTsIn         Counter64,
        unisLBv2SFStatServerSidePKTsOut        Counter64,
        unisLBv2SFStatDroppedPackets           Counter64,
        unisLBv2SFStatServerSideBytesIn        Counter64,
        unisLBv2SFStatServerSideBytesOut       Counter64,
        unisLBv2SFStatReceivedRequests         Counter64,
        unisLBv2SFStatSentResponses            Counter64
    }

unisLBv2SFStatChassis OBJECT-TYPE
    SYNTAX      Unsigned32(0..255)
    MAX-ACCESS  not-accessible
    STATUS      current
    DESCRIPTION
        "ID of the device that holds the card."
    ::= { unisLBv2SFStatsEntry 1 }

unisLBv2SFStatSlot OBJECT-TYPE
    SYNTAX      Unsigned32(0..255)
    MAX-ACCESS  not-accessible
    STATUS      current
    DESCRIPTION
        "Member ID of the card on device."
    ::= { unisLBv2SFStatsEntry 2 }

unisLBv2SFStatCpuid OBJECT-TYPE
    SYNTAX      Unsigned32(0..255)
    MAX-ACCESS  not-accessible
    STATUS      current
    DESCRIPTION
        "ID of the CPU on the card."
    ::= { unisLBv2SFStatsEntry 3 }

unisLBv2SFStatTotalConnections OBJECT-TYPE
    SYNTAX      Counter64
    MAX-ACCESS  read-only
    STATUS      current
    DESCRIPTION
        "Total number of connections that the server farm received."
    ::= { unisLBv2SFStatsEntry 4 }

unisLBv2SFStatActiveConnections OBJECT-TYPE
    SYNTAX      Unsigned32
    MAX-ACCESS  read-only
    STATUS      current
    DESCRIPTION
        "Active connections that the server farm received."
    ::= { unisLBv2SFStatsEntry 5 }

unisLBv2SFStatServerSidePKTsIn OBJECT-TYPE
    SYNTAX      Counter64
    MAX-ACCESS  read-only
    STATUS      current
    DESCRIPTION
        "Number of packets that the server farm received from device."
    ::= { unisLBv2SFStatsEntry 6 }

unisLBv2SFStatServerSidePKTsOut OBJECT-TYPE
    SYNTAX      Counter64
    MAX-ACCESS  read-only
    STATUS      current
    DESCRIPTION
        "Number of packets that the server farm sent."
    ::= { unisLBv2SFStatsEntry 7 }

unisLBv2SFStatDroppedPackets OBJECT-TYPE
    SYNTAX      Counter64
    MAX-ACCESS  read-only
    STATUS      current
    DESCRIPTION
        "Number of packets that the server farm dropped."
    ::= { unisLBv2SFStatsEntry 8 }

unisLBv2SFStatServerSideBytesIn OBJECT-TYPE
    SYNTAX      Counter64
    UNITS       "byte"
    MAX-ACCESS  read-only
    STATUS      current
    DESCRIPTION
        "Number of bytes that the server farm received."
    ::= { unisLBv2SFStatsEntry 9 }

unisLBv2SFStatServerSideBytesOut OBJECT-TYPE
    SYNTAX      Counter64
    UNITS       "byte"
    MAX-ACCESS  read-only
    STATUS      current
    DESCRIPTION
        "Number of bytes that the server farm sent."
    ::= { unisLBv2SFStatsEntry 10 }

unisLBv2SFStatReceivedRequests OBJECT-TYPE
    SYNTAX      Counter64
    MAX-ACCESS  read-only
    STATUS      current
    DESCRIPTION
        "Number of requests that all real servers in the server farm
         received from device."
    ::= { unisLBv2SFStatsEntry 11 }

unisLBv2SFStatSentResponses OBJECT-TYPE
    SYNTAX      Counter64
    MAX-ACCESS  read-only
    STATUS      current
    DESCRIPTION
        "Number of responses that the server farm sent to device."
    ::= { unisLBv2SFStatsEntry 12 }

-- =================================================================
--    LB NOTIFICATION
-- =================================================================
unisLBv2Trap OBJECT IDENTIFIER ::= { unisLBv2 6 }

unisLBv2TrapPrefix OBJECT IDENTIFIER ::= { unisLBv2Trap 0 }
-- =================================================================
--    Virtual Server Connections Overload Notification
-- =================================================================
unisLBv2VSConnOverloadTrap NOTIFICATION-TYPE
    OBJECTS
        {
            unisLBv2VSName,
            unisLBv2VSConnectionsLimit,
            unisLBv2VSStatChassis,
            unisLBv2VSStatSlot,
            unisLBv2VSStatCpuid,
            unisLBv2VSStatActiveConnections
        }
    STATUS      current
    DESCRIPTION
        "A unisLBv2VSConnOverloadTrap notification is sent when
         the number of active connections of the virtual server
         has reached the upper limit. "
    ::= { unisLBv2TrapPrefix 1 }

-- =================================================================
--    Virtual Server Connections Overload Recovery Notification
-- =================================================================
unisLBv2VSConnRecoveryTrap NOTIFICATION-TYPE
    OBJECTS
        {
            unisLBv2VSName,
            unisLBv2VSConnectionsLimit,
            unisLBv2VSStatChassis,
            unisLBv2VSStatSlot,
            unisLBv2VSStatCpuid,
            unisLBv2VSStatActiveConnections
        }
    STATUS      current
    DESCRIPTION
        "A unisLBv2VSConnRecoveryTrap notification is sent when
         the number of active connections of the virtual server
         is less than the upper limit."
    ::= { unisLBv2TrapPrefix 2 }
-- =================================================================
--    Virtual Server Connections Rate Overload Notification
-- =================================================================
unisLBv2VSConnsRateOverloadTrap NOTIFICATION-TYPE
    OBJECTS
        {
            unisLBv2VSName,
            unisLBv2VSConnectionsRateLimit,
            unisLBv2VSStatChassis,
            unisLBv2VSStatSlot,
            unisLBv2VSStatCpuid,
            unisLBv2VSStatConnectionsRate
        }
    STATUS      current
    DESCRIPTION
        "A unisLBv2VSConnsRateOverloadTrap notification is sent
         when the connection rate of the virtual server has
         reached the upper limit."
    ::= { unisLBv2TrapPrefix 3 }

-- =================================================================
--    Virtual Server Connections Rate Overload Recovery Notification
-- =================================================================
unisLBv2VSConnsRateRecoveryTrap NOTIFICATION-TYPE
    OBJECTS
        {
            unisLBv2VSName,
            unisLBv2VSConnectionsRateLimit,
            unisLBv2VSStatChassis,
            unisLBv2VSStatSlot,
            unisLBv2VSStatCpuid,
            unisLBv2VSStatConnectionsRate
        }
    STATUS      current
    DESCRIPTION
        "A unisLBv2VSConnsRateRecoveryTrap notification is sent
         when the connection rate of the virtual server is smaller than
         the upper limit."
    ::= { unisLBv2TrapPrefix 4 }

-- =================================================================
--    Virtual Server Active Notification
-- =================================================================
unisLBv2VSActiveTrap NOTIFICATION-TYPE
    OBJECTS
        {
            unisLBv2VSName
        }
    STATUS      current
    DESCRIPTION
        "A unisLBv2VSActiveTrap notification is sent when virtual
         server status changes to active."
    ::= { unisLBv2TrapPrefix 5 }

-- =================================================================
--    Virtual Server Inactive Notification
-- =================================================================
unisLBv2VSInactiveTrap NOTIFICATION-TYPE
    OBJECTS
        {
            unisLBv2VSName
        }
    STATUS      current
    DESCRIPTION
        "A unisLBv2VSInactiveTrap notification is sent when virtual
         server status changes to inactive."
    ::= { unisLBv2TrapPrefix 6 }

-- =================================================================
--    Real Server Available Notification
-- =================================================================
unisLBv2RSAvailableTrap NOTIFICATION-TYPE
    OBJECTS
        {
            unisLBv2RSName
        }
    STATUS      current
    DESCRIPTION
        "A unisLBv2RSAvailableTrap notification is sent when the status of
         the real server changes to available."
    ::= { unisLBv2TrapPrefix 7 }

-- =================================================================
--    Real Server Unavailable Notification
-- =================================================================
unisLBv2RSUnavailableTrap NOTIFICATION-TYPE
    OBJECTS
        {
            unisLBv2RSName
        }
    STATUS      current
    DESCRIPTION
        "A unisLBv2RSUnavailableTrap notification is sent when the status of
         the real server changes to unavailable."
    ::= { unisLBv2TrapPrefix 8 }

-- =================================================================
--    Server Farm Active Notification
-- =================================================================
unisLBv2SFActiveTrap NOTIFICATION-TYPE
    OBJECTS
        {
            unisLBv2SFName
        }
    STATUS      current
    DESCRIPTION
        "A unisLBv2SFActiveTrap notification is sent when the status of
         the server farm changes to active."
    ::= { unisLBv2TrapPrefix 9 }

-- =================================================================
--    Server Farm Inactive Notification
-- =================================================================
unisLBv2SFInactiveTrap NOTIFICATION-TYPE
    OBJECTS
        {
            unisLBv2SFName
        }
    STATUS      current
    DESCRIPTION
        "A unisLBv2SFInactiveTrap notification is sent when the status of
         the server farm changes to inactive."
    ::= { unisLBv2TrapPrefix 10 }

-- =================================================================
--    Server Farm In Use Of Action Changes Notification
-- =================================================================
unisLBv2ActionInUseSFChangeTrap NOTIFICATION-TYPE
    OBJECTS
        {
            unisLBv2ActionName,
            unisLBv2ActionDefaultSF,
            unisLBv2ActionBackupSF,
            unisLBv2ActionInUseSF
        }
    STATUS      current
    DESCRIPTION
         "A unisLBv2ActionInUseSFChangeTrap notification is sent when the
         server farm which is in use quoted by action changes."
    ::= { unisLBv2TrapPrefix 11 }

-- =================================================================
--    Server Farm In Use Of Virtual Server Changes Notification
-- =================================================================
unisLBv2VSInUseSFChangeTrap NOTIFICATION-TYPE
    OBJECTS
        {
            unisLBv2VSName,
            unisLBv2VSDefaultSF,
            unisLBv2VSBackupSF,
            unisLBv2VSInUseSF
        }
    STATUS      current
    DESCRIPTION
        "A unisLBv2VSInUseSFChangeTrap notification is sent when
         the server farm which is in use quoted by virtual server
         changes."
    ::= { unisLBv2TrapPrefix 12 }

-- =================================================================
--    Real Server Connections Overload Notification
-- =================================================================
unisLBv2RSConnOverloadTrap NOTIFICATION-TYPE
    OBJECTS
        {
            unisLBv2RSName,
            unisLBv2RSConnectionsLimit,
            unisLBv2RSStatChassis,
            unisLBv2RSStatSlot,
            unisLBv2RSStatCpuid,
            unisLBv2RSStatActiveConnections
        }
    STATUS      current
    DESCRIPTION
        "A unisLBv2RSConnOverloadTrap notification is sent when
         the number of active connections of the real server
         has reached the upper limit. "
    ::= { unisLBv2TrapPrefix 13 }

-- =================================================================
--    Real Server Connections Overload Recovery Notification
-- =================================================================
unisLBv2RSConnRecoveryTrap NOTIFICATION-TYPE
    OBJECTS
        {
            unisLBv2RSName,
            unisLBv2RSConnectionsLimit,
            unisLBv2RSStatChassis,
            unisLBv2RSStatSlot,
            unisLBv2RSStatCpuid,
            unisLBv2RSStatActiveConnections
        }
    STATUS      current
    DESCRIPTION
        "A unisLBv2RSConnRecoveryTrap notification is sent when
         the number of active connections of the real server
         is less than the upper limit."
    ::= { unisLBv2TrapPrefix 14 }
-- =================================================================
--    Real Server Connections Rate Overload Notification
-- =================================================================
unisLBv2RSConnsRateOverloadTrap NOTIFICATION-TYPE
    OBJECTS
        {
            unisLBv2RSName,
            unisLBv2RSConnectionsRateLimit,
            unisLBv2RSStatChassis,
            unisLBv2RSStatSlot,
            unisLBv2RSStatCpuid,
            unisLBv2RSStatConnectionsRate
        }
    STATUS      current
    DESCRIPTION
        "A unisLBv2RSConnsRateOverloadTrap notification is sent
         when the connection rate of the real server has
         reached the upper limit."
    ::= { unisLBv2TrapPrefix 15 }

-- =================================================================
--    Real Server Connections Rate Overload Recovery Notification
-- =================================================================
unisLBv2RSConnsRateRecoveryTrap NOTIFICATION-TYPE
    OBJECTS
        {
            unisLBv2RSName,
            unisLBv2RSConnectionsRateLimit,
            unisLBv2RSStatChassis,
            unisLBv2RSStatSlot,
            unisLBv2RSStatCpuid,
            unisLBv2RSStatConnectionsRate
        }
    STATUS      current
    DESCRIPTION
        "A unisLBv2RSConnsRateRecoveryTrap notification is sent
         when the connection rate of the real server is smaller than
         the upper limit."
    ::= { unisLBv2TrapPrefix 16 }

END
