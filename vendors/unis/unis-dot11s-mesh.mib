-- =============================================================================
-- Copyright (c) 2020 Unisyue Technologies Co., Ltd.  All rights reserved.
--
-- Description:
--   The file defines a MIB to provide MESH configuration information.
-- Reference:
-- Version: V1.6
-- History:
--   V1.0 2008-07-08 Initial version, created by ChangHuifeng
--   V1.1 2008-11-07 modified by liyugang
--        Add unisDot11sMeshLinkStatisTable, unisDot11sMeshNbrStatusTable
--        to unisDot11sMeshStatusGroup
--   V1.2 2009-08-01 modified by Wang Shaojie
--        Add unisDot11sMeshLinkIFName to unisDot11sMeshLinkStatisTable.
--   V1.3 2013-09-14 modified by Zhang Siyu
--        Add unisDot11sMeshLinkType to unisDot11sMeshLinkStatusTable
--   V1.4 2015-02-02 modified by Xiao min
--        Add unisDot11sMeshLinkSNR to unisDot11sMeshLinkStatusTable
--        Add unisDot11sMeshLinkNoise to unisDot11sMeshLinkStatusTable
--        Add unisDot11sMeshLinkPeerSNR to unisDot11sMeshLinkStatusTable
--        Add unisDot11sMeshLinkPeerNoise to unisDot11sMeshLinkStatusTable
--   V1.5 2015-05-6 modified by guoxuzhen
--        Add unisDot11sMeshAKMMode, unisDot11sSimplerKey to UnisDot11sMeshPflTable
--        Add unisDot11sBindInterface to unisDot11sRadioCfgTable
--        2015-08-14 modified by Xiao min
--        Add unisDot11sMeshLinkPeerIPAddress to unisDot11sMeshLinkStatusTable
--        Add unisDot11sMeshLinkPeerSystemName to unisDot11sMeshLinkStatusTable
--   V1.6 2018-05-15 modified by liuxiaolong
--        Add unisDot11sMlspExtCfgTable to unisDot11sConfigGroup
--        Add unisDot11sMeshLinkNotifyGroup to unisDot11sMesh
--        Add unisDot11sMlspMode to unisDot11sMpPlcyTable
--        Add unisDot11sWaveGuideHoldRSSI to unisDot11sMpPlcyTable
--        Add unisDot11sWaveGuideSwitch to unisDot11sMpPlcyTable
--        Add unisDot11sOptimizeEnable to unisDot11sMpPlcyTable
--        Add unisDot11sOptimizeThreshold to unisDot11sMpPlcyTable
--        Add unisDot11sMlspLogEnable to unisDot11sMpPlcyTable
--        Add unisDot11sMlspLogInterval to unisDot11sMpPlcyTable
--        Add unisDot11sActiveKeepaliveCount to unisDot11sMpPlcyTable
--        Add unisDot11sLinkEstaThreshold to unisDot11sMpPlcyTable
--        Add unisDot11sTransmissionMethod to unisDot11sMpPlcyTable
--        Add unisDot11sTransmitLevel to unisDot11sMpPlcyTable
--        Add unisDot11sTempLinkEnable to unisDot11sMpPlcyTable
-- =============================================================================
UNIS-DOT11S-MESH-MIB DEFINITIONS ::= BEGIN

IMPORTS
        TruthValue,
        MacAddress,
        RowStatus
    FROM SNMPv2-TC
        MODULE-IDENTITY,
        OBJECT-TYPE,
        Integer32,
        Unsigned32,
        Counter32,
        IpAddress,
        NOTIFICATION-TYPE
    FROM SNMPv2-SMI
        unisDot11, UnisDot11RadioElementIndex, unisDot11APElementIndex, UnisDot11AKMType
    FROM UNIS-DOT11-REF-MIB;

unisDot11sMesh MODULE-IDENTITY
    LAST-UPDATED "201805151000Z"        -- May 15, 2018 at 10:00 GMT
    ORGANIZATION
        "Unisyue Technologies Co., Ltd."
    CONTACT-INFO
        ""
    DESCRIPTION
        "The file defines a MIB to provide MESH configuration information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        BSS
        IEEE 802.11 Basic Service Set (Radio Cell).  The
        BSS of an AP comprises of the stations directly
        associating with the AP.

        Radio
        The chip set to receive and send wireless signal.

        Mesh
        A network consisting of two or more mesh points
        which communicate with each other via mesh services.

        Mesh Point (MP)
        An IEEE 802.11 entity that contains an IEEE 802.11-conformant
        medium access control (MAC) and physical layer (PHY) interface
        to the wireless medium (WM) that supports mesh services.

        Mesh Access Point (MAP)
        A mesh point that is collocated with one or more access points.

        Mesh Portal Point (MPP)
        A mesh point that is collocated with one or more portals.

        Mesh Link
        A link between two MPs.

        Simultaneous Authentication of Equals (SAE)
        A password-authenticated key exchange based on
        a zero-knowledge proof."
    REVISION "201805151000Z"        -- May 15, 2018 at 10:00 GMT
    DESCRIPTION
        "Add new nodes and new table"
    REVISION "201508141000Z"        -- Aug 01, 2009 at 10:00 GMT
    DESCRIPTION
        "Add unisDot11sMeshLinkPeerIPAddress to unisDot11sMeshLinkStatusTable,
         Add unisDot11sMeshLinkPeerSystemName to unisDot11sMeshLinkStatusTable"
    REVISION "201505061500Z"        -- May 6, 2015 at 15:00 GMT
    DESCRIPTION
        "Add new nodes."
    REVISION "200908011000Z"        -- Aug 01, 2009 at 10:00 GMT
    DESCRIPTION
        "Add new nodes."
    REVISION "200811071000Z"        -- Nov 07, 2008 at 10:00 GMT
    DESCRIPTION
        "Modified to add new nodes and a new table."
    REVISION "200807081800Z"        -- July 8, 2008 at 18:00 GMT
    DESCRIPTION
        "The initial revision of this MIB module."
    ::= { unisDot11 11 }

-- *****************************************************************************
-- *  Major sections
-- *****************************************************************************

unisDot11sConfigGroup OBJECT IDENTIFIER  ::= { unisDot11sMesh 1 }
--  Dot11s Configuration Group has the following children:
--  unisDot11sMeshGlobalPara             ::= { unisDot11sConfigGroup 1 }
--  unisDot11sMeshPflTable               ::= { unisDot11sConfigGroup 2 }
--  unisDot11sMpPlcyTable                ::= { unisDot11sConfigGroup 3 }
--  unisDot11sMlspCfgTable               ::= { unisDot11sConfigGroup 4 }
--  unisDot11sRadioCfgTable              ::= { unisDot11sConfigGroup 5 }
--  unisDot11sAPCfgTable                 ::= { unisDot11sConfigGroup 6 }
--  unisDot11sMlspExtCfgTable            ::= { unisDot11sConfigGroup 7 }

unisDot11sWDSConfigGroup OBJECT IDENTIFIER ::= { unisDot11sMesh 2 }
--  Dot11s WDS Configuration Group has the following children:
--  unisDot11sWDSPeerMacTable         ::= { unisDot11sWDSConfigGroup 1 }

unisDot11sMeshStatusGroup OBJECT IDENTIFIER ::= { unisDot11sMesh 3 }
--  Dot11s Mesh Status Group has the following children:
--  unisDot11sMeshLinkStatusTable    ::= { unisDot11sMeshStatusGroup 1 }
--  unisDot11sMeshLinkStatisTable    ::= { unisDot11sMeshStatusGroup 2 }
--  unisDot11sMeshNbrStatusTable     ::= { unisDot11sMeshStatusGroup 3 }

unisDot11sMeshLinkNotifyGroup OBJECT IDENTIFIER ::= { unisDot11sMesh 4 }
-- *****************************************************************************
-- *  unisDot11sMeshGlobalPara Definition
-- *****************************************************************************
unisDot11sMeshGlobalPara OBJECT IDENTIFIER  ::= { unisDot11sConfigGroup 1 }

unisDot11sMeshMkdID OBJECT-TYPE
    SYNTAX      MacAddress
    MAX-ACCESS  read-write
    STATUS      current
    DESCRIPTION
        "This object represents the mesh key distributor identifier (MKD-ID).
        If the MKD-ID is not configured, the value is '00:00:00:00:00:00'."
    ::= { unisDot11sMeshGlobalPara 1 }

-- *****************************************************************************
-- * End of unisDot11sMeshGlobalPara Definition
-- *****************************************************************************
-- *****************************************************************************
-- *  unisDot11sMeshPflTable Definition
-- *****************************************************************************
unisDot11sMeshPflTable OBJECT-TYPE
    SYNTAX      SEQUENCE OF UnisDot11sMeshPflEntry
    MAX-ACCESS  not-accessible
    STATUS      current
    DESCRIPTION
        "This table is used to configure mesh profile.
        A mesh profile is created and mapped to a MP so that
        it can provide mesh services to other MPs which have the same
        mesh ID.
        When the mesh profile is enabled, all of the object in this table
        cannot be modified except unisDot11sMeshPflEnable.
        The mesh profile cannot be deleted when it is bound with the radio."
    ::= { unisDot11sConfigGroup 2 }

unisDot11sMeshPflEntry OBJECT-TYPE
    SYNTAX      UnisDot11sMeshPflEntry
    MAX-ACCESS  not-accessible
    STATUS      current
    DESCRIPTION
        "Each entry contains information of a mesh profile."
    INDEX
        {
            unisDot11sMeshPflIndex
        }
    ::= { unisDot11sMeshPflTable 1 }

UnisDot11sMeshPflEntry ::= SEQUENCE
    {
        unisDot11sMeshPflIndex         Integer32,
        unisDot11sMeshPflMeshID        OCTET STRING,
        unisDot11sMeshPflBindIntNum    Integer32,
        unisDot11sMeshPflKeepAlive     Integer32,
        unisDot11sMeshPflBackhaulRate  Integer32,
        unisDot11sMeshMkdServEnable    TruthValue,
        unisDot11sMeshPflEnable        TruthValue,
        unisDot11sMeshPflRowStatus     RowStatus,
        unisDot11sMeshAKMMode          UnisDot11AKMType,
        unisDot11sMeshSimpleKey        OCTET STRING
    }

unisDot11sMeshPflIndex OBJECT-TYPE
    SYNTAX      Integer32
    MAX-ACCESS  not-accessible
    STATUS      current
    DESCRIPTION
        "This object represents the index of the mesh profile."
    ::= { unisDot11sMeshPflEntry 1 }

unisDot11sMeshPflMeshID OBJECT-TYPE
    SYNTAX      OCTET STRING (SIZE (0..32))
    MAX-ACCESS  read-create
    STATUS      current
    DESCRIPTION
        "This object represents the mesh ID of the mesh profile.
        The string length of this object is zero when the mesh ID is not
        configured.  If the mesh ID is not configured, unisDot11sMeshPflEnable
        cannot be set to 'true'."
    ::= { unisDot11sMeshPflEntry 2 }

unisDot11sMeshPflBindIntNum OBJECT-TYPE
    SYNTAX      Integer32
    MAX-ACCESS  read-create
    STATUS      current
    DESCRIPTION
        "This object represents the specified mesh interface number
        bound to the mesh profile.
        If the value is set to -1, the binding will be removed."
    DEFVAL      { -1 }
    ::= { unisDot11sMeshPflEntry 3 }

unisDot11sMeshPflKeepAlive OBJECT-TYPE
    SYNTAX      Integer32(1..1800)
    UNITS       "second"
    MAX-ACCESS  read-create
    STATUS      current
    DESCRIPTION
        "This object represents the mesh link keep-alive interval."
    ::= { unisDot11sMeshPflEntry 4 }

unisDot11sMeshPflBackhaulRate OBJECT-TYPE
    SYNTAX      Integer32
    UNITS       "Kbps"
    MAX-ACCESS  read-create
    STATUS      current
    DESCRIPTION
        "This object represents the link backhaul rate."
    ::= { unisDot11sMeshPflEntry 5 }

unisDot11sMeshMkdServEnable OBJECT-TYPE
    SYNTAX      TruthValue
    MAX-ACCESS  read-create
    STATUS      current
    DESCRIPTION
        "This object indicates whether the mesh key distributor (MKD)
        service for the mesh profile is enabled.
        'true': The MKD service for the mesh profile is enabled.
        'false': The MKD service for the mesh profile is disabled."
    DEFVAL      { false }
    ::= { unisDot11sMeshPflEntry 6 }

unisDot11sMeshPflEnable OBJECT-TYPE
    SYNTAX      TruthValue
    MAX-ACCESS  read-create
    STATUS      current
    DESCRIPTION
        "This object indicates whether the mesh profile is enabled.
        'true': The mesh profile is enabled.
        'false': The mesh profile is disabled."
    DEFVAL      { false }
    ::= { unisDot11sMeshPflEntry 7 }

unisDot11sMeshPflRowStatus OBJECT-TYPE
    SYNTAX      RowStatus
    MAX-ACCESS  read-create
    STATUS      current
    DESCRIPTION
        "The status of this table entry."
    ::= { unisDot11sMeshPflEntry 8 }

unisDot11sMeshAKMMode OBJECT-TYPE
    SYNTAX      UnisDot11AKMType
    MAX-ACCESS  read-create
    STATUS      current
    DESCRIPTION
        "Represents the authentication and key management mode defined by 802.11s.
        The following values are supported:
        'none': No key management mode configured.
        'psk': pre-shared key authentication."
    DEFVAL      { none }
    ::= { unisDot11sMeshPflEntry 9 }

unisDot11sMeshSimpleKey OBJECT-TYPE
    SYNTAX      OCTET STRING
    MAX-ACCESS  read-create
    STATUS      current
    DESCRIPTION
        "Represents the simple key for SAE."
    ::= { unisDot11sMeshPflEntry 10 }

-- *****************************************************************************
-- * End of unisDot11sMeshPflTable Definition
-- *****************************************************************************
-- *****************************************************************************
-- *  unisDot11sMpPlcyTable Definition
-- *****************************************************************************
unisDot11sMpPlcyTable OBJECT-TYPE
    SYNTAX      SEQUENCE OF UnisDot11sMpPlcyEntry
    MAX-ACCESS  not-accessible
    STATUS      current
    DESCRIPTION
        "This table is used to configure MP policy.
        There is a default policy on system and its index is 1.
        The default policy cannot be deleted or modified.
        The MP policy cannot be deleted when it is applied to a radio."
    ::= { unisDot11sConfigGroup 3 }

unisDot11sMpPlcyEntry OBJECT-TYPE
    SYNTAX      UnisDot11sMpPlcyEntry
    MAX-ACCESS  not-accessible
    STATUS      current
    DESCRIPTION
        "Each entry contains information of a MP policy."
    INDEX
        {
            unisDot11sMpPlcyIndex
        }
    ::= { unisDot11sMpPlcyTable 1 }

UnisDot11sMpPlcyEntry ::= SEQUENCE
    {
        unisDot11sMpPlcyIndex          Integer32,
        unisDot11sMpPlcyName           OCTET STRING,
        unisDot11sMpPlcyInitEnable     TruthValue,
        unisDot11sMlspEnable           TruthValue,
        unisDot11sProbReqInterval      Integer32,
        unisDot11sRoleAuthEnable       TruthValue,
        unisDot11sLinkHoldRSSI         Integer32,
        unisDot11sLinkHoldTime         Integer32,
        unisDot11sSwitchMargin         Integer32,
        unisDot11sLinkSaturationRSSI   Integer32,
        unisDot11sLinkRateMode         INTEGER,
        unisDot11sMaxLinkNum           Integer32,
        unisDot11sMpPlcyRowStatus      RowStatus,
        unisDot11sMlspMode             INTEGER,
        unisDot11sWaveGuideHoldRSSI    Integer32,
        unisDot11sWaveGuideSwitch      TruthValue,
        unisDot11sOptimizeEnable       TruthValue,
        unisDot11sOptimizeThreshold    Integer32,
        unisDot11sMlspLogEnable        TruthValue,
        unisDot11sMlspLogInterval      Integer32,
        unisDot11sActiveKeepaliveCount Integer32,
        unisDot11sLinkEstaThreshold    Integer32,
        unisDot11sTransmissionMethod   INTEGER,
        unisDot11sTransmitLevel        Integer32,
        unisDot11sTempLinkEnable       TruthValue
    }

unisDot11sMpPlcyIndex OBJECT-TYPE
    SYNTAX      Integer32
    MAX-ACCESS  not-accessible
    STATUS      current
    DESCRIPTION
        "This object represents the MP policy index."
    ::= { unisDot11sMpPlcyEntry 1 }

unisDot11sMpPlcyName OBJECT-TYPE
    SYNTAX      OCTET STRING (SIZE (1..31))
    MAX-ACCESS  read-create
    STATUS      current
    DESCRIPTION
        "This object represents the MP policy name.
        MP policy cannot be created with the name of the
        default policy.
        Modification is not supported."
    ::= { unisDot11sMpPlcyEntry 2 }

unisDot11sMpPlcyInitEnable OBJECT-TYPE
    SYNTAX      TruthValue
    MAX-ACCESS  read-create
    STATUS      current
    DESCRIPTION
        "This object indicates whether the link initiation for
        the MP policy is enabled.
        'true': The link initiation for the MP policy is enabled.
        'false': The link initiation for the MP policy is disabled."
    DEFVAL      { true }
    ::= { unisDot11sMpPlcyEntry 3 }

unisDot11sMlspEnable OBJECT-TYPE
    SYNTAX      TruthValue
    MAX-ACCESS  read-create
    STATUS      current
    DESCRIPTION
        "This object indicates whether the mesh link switch protocol (MLSP)
        is enabled.
        'true': MLSP is enabled.
        'false': MLSP is disabled."
    DEFVAL      { false }
    ::= { unisDot11sMpPlcyEntry 4 }

unisDot11sProbReqInterval OBJECT-TYPE
    SYNTAX      Integer32
    UNITS       "millisecond"
    MAX-ACCESS  read-create
    STATUS      current
    DESCRIPTION
        "This object represents the probe request interval."
    ::= { unisDot11sMpPlcyEntry 5 }

unisDot11sRoleAuthEnable OBJECT-TYPE
    SYNTAX      TruthValue
    MAX-ACCESS  read-create
    STATUS      current
    DESCRIPTION
        "This object indicates whether the device can play as the role
        of an authenticator."
    DEFVAL      { true }
    ::= { unisDot11sMpPlcyEntry 6 }

unisDot11sLinkHoldRSSI OBJECT-TYPE
    SYNTAX      Integer32(5..100)
    UNITS       "dBm"
    MAX-ACCESS  read-create
    STATUS      current
    DESCRIPTION
        "This object represents the link-hold
        receive signal strength indicator (RSSI)."
    ::= { unisDot11sMpPlcyEntry 7 }

unisDot11sLinkHoldTime OBJECT-TYPE
    SYNTAX      Integer32(1000..20000)
    UNITS       "millisecond"
    MAX-ACCESS  read-create
    STATUS      current
    DESCRIPTION
        "This object represents the link-hold time."
    ::= { unisDot11sMpPlcyEntry 8 }

unisDot11sSwitchMargin OBJECT-TYPE
    SYNTAX      Integer32(1..100)
    UNITS       "dBm"
    MAX-ACCESS  read-create
    STATUS      current
    DESCRIPTION
        "This object represents the link-switch margin."
    ::= { unisDot11sMpPlcyEntry 9 }

unisDot11sLinkSaturationRSSI OBJECT-TYPE
    SYNTAX      Integer32(30..150)
    UNITS       "dBm"
    MAX-ACCESS  read-create
    STATUS      current
    DESCRIPTION
        "This object represents the link saturation
        receive signal strength indicator (RSSI)."
    ::= { unisDot11sMpPlcyEntry 10 }

unisDot11sLinkRateMode OBJECT-TYPE
    SYNTAX      INTEGER
        {
            fixed(1),
            realtime(2)
        }
    MAX-ACCESS  read-create
    STATUS      current
    DESCRIPTION
        "This object represents the rate mode of the mesh link."
    DEFVAL      { fixed }
    ::= { unisDot11sMpPlcyEntry 11 }

unisDot11sMaxLinkNum OBJECT-TYPE
    SYNTAX      Integer32
    MAX-ACCESS  read-create
    STATUS      current
    DESCRIPTION
        "This object represents the maximum number of the mesh link."
    ::= { unisDot11sMpPlcyEntry 12 }

unisDot11sMpPlcyRowStatus OBJECT-TYPE
    SYNTAX      RowStatus
    MAX-ACCESS  read-create
    STATUS      current
    DESCRIPTION
        "The status of this table entry."
    ::= { unisDot11sMpPlcyEntry 13 }

unisDot11sMlspMode OBJECT-TYPE
    SYNTAX      INTEGER
        {
            normal(0),
            satble(1)
        }
    MAX-ACCESS  read-create
    STATUS      current
    DESCRIPTION
        "This object represents the MLSP mode."
    DEFVAL      { normal }
    ::= { unisDot11sMpPlcyEntry 14 }

unisDot11sWaveGuideHoldRSSI OBJECT-TYPE
    SYNTAX      Integer32(5..100)
    UNITS       "dBm"
    MAX-ACCESS  read-create
    STATUS      current
    DESCRIPTION
        "This object represents the link-hold
        receive signal strength indicator (RSSI) of wave guides."
    DEFVAL      { 15 }
    ::= { unisDot11sMpPlcyEntry 15 }

unisDot11sWaveGuideSwitch OBJECT-TYPE
    SYNTAX      TruthValue
    MAX-ACCESS  read-create
    STATUS      current
    DESCRIPTION
        "This object represents the wave-guide switch state."
    DEFVAL      { false }
    ::= { unisDot11sMpPlcyEntry 16 }

unisDot11sOptimizeEnable OBJECT-TYPE
    SYNTAX      TruthValue
    MAX-ACCESS  read-create
    STATUS      current
    DESCRIPTION
        "This object indicates whether the mesh link switch protocol (MLSP)
        optimization function is enabled."
    DEFVAL      { false }
    ::= { unisDot11sMpPlcyEntry 17 }

unisDot11sOptimizeThreshold OBJECT-TYPE
    SYNTAX      Integer32(15..80)
    UNITS       "dBm"
    MAX-ACCESS  read-create
    STATUS      current
    DESCRIPTION
        "This object represents the mesh link switch protocol (MLSP)
        optimization threshold."
    DEFVAL      { 30 }
    ::= { unisDot11sMpPlcyEntry 18 }

unisDot11sMlspLogEnable OBJECT-TYPE
    SYNTAX      TruthValue
    MAX-ACCESS  read-create
    STATUS      current
    DESCRIPTION
        "This object indicates whether the mesh link switch protocol (MLSP)
        link switch logging function is enabled."
    DEFVAL      { false }
    ::= { unisDot11sMpPlcyEntry 19 }

unisDot11sMlspLogInterval OBJECT-TYPE
    SYNTAX      Integer32(500..4000)
    UNITS       "millisecond"
    MAX-ACCESS  read-create
    STATUS      current
    DESCRIPTION
        "This object represents the mesh link switch protocol (MLSP)
        link switch logging interval."
    DEFVAL      { 1000 }
    ::= { unisDot11sMpPlcyEntry 20 }

unisDot11sActiveKeepaliveCount OBJECT-TYPE
    SYNTAX      Integer32(1..100)
    MAX-ACCESS  read-create
    STATUS      current
    DESCRIPTION
        "This object represents the mesh link switch protocol (MLSP)
        active link keepalive packet limit."
    DEFVAL      { 6 }
    ::= { unisDot11sMpPlcyEntry 21 }

unisDot11sLinkEstaThreshold OBJECT-TYPE
    SYNTAX      Integer32(1..100)
    UNITS       "dBm"
    MAX-ACCESS  read-create
    STATUS      current
    DESCRIPTION
        "This object represents the mesh link establishment threshold."
    DEFVAL      { 5 }
    ::= { unisDot11sMpPlcyEntry 22 }

unisDot11sTransmissionMethod OBJECT-TYPE
    SYNTAX      INTEGER
        {
            air(0),
            waveGuide(1)
        }
    MAX-ACCESS  read-create
    STATUS      current
    DESCRIPTION
        "This object represents the method for mesh link signal transmission."
    DEFVAL      { air }
    ::= { unisDot11sMpPlcyEntry 23 }

unisDot11sTransmitLevel OBJECT-TYPE
    SYNTAX      Integer32(0..4)
    MAX-ACCESS  read-create
    STATUS      current
    DESCRIPTION
        "This object represents the active mesh link keepalive packet transmission level."
    DEFVAL      { 0 }
    ::= { unisDot11sMpPlcyEntry 24 }

unisDot11sTempLinkEnable OBJECT-TYPE
    SYNTAX      TruthValue
    MAX-ACCESS  read-create
    STATUS      current
    DESCRIPTION
        "This object indicates whether to allow temporary mesh link establishment."
    DEFVAL      { true }
    ::= { unisDot11sMpPlcyEntry 25 }

-- *****************************************************************************
-- * End of unisDot11sMpPlcyTable Definition
-- *****************************************************************************
-- *****************************************************************************
-- *  unisDot11sMlspCfgTable Definition
-- *****************************************************************************
unisDot11sMlspCfgTable OBJECT-TYPE
    SYNTAX      SEQUENCE OF UnisDot11sMlspCfgEntry
    MAX-ACCESS  not-accessible
    STATUS      current
    DESCRIPTION
        "This table is used to configure MLSP proxy MAC address.
        Only if the specified MP policy is modifiable and the MLSP
        is enabled, the row of this table can be created and deleted.
        The row of this table cannot be modified."
    ::= { unisDot11sConfigGroup 4 }

unisDot11sMlspCfgEntry OBJECT-TYPE
    SYNTAX      UnisDot11sMlspCfgEntry
    MAX-ACCESS  not-accessible
    STATUS      current
    DESCRIPTION
        "Each entry contains information of MLSP proxy MAC address."
    INDEX
        {
            unisDot11sMpPlcyIndex,
            unisDot11sMlspProxyIndex
        }
    ::= { unisDot11sMlspCfgTable 1 }

UnisDot11sMlspCfgEntry ::= SEQUENCE
    {
        unisDot11sMlspProxyIndex       Integer32,
        unisDot11sMlspProxyMac         MacAddress,
        unisDot11sMlspRowStatus        RowStatus
    }

unisDot11sMlspProxyIndex OBJECT-TYPE
    SYNTAX      Integer32
    MAX-ACCESS  not-accessible
    STATUS      current
    DESCRIPTION
        "This object represents the MLSP proxy MAC address index."
    ::= { unisDot11sMlspCfgEntry 1 }

unisDot11sMlspProxyMac OBJECT-TYPE
    SYNTAX      MacAddress
    MAX-ACCESS  read-create
    STATUS      current
    DESCRIPTION
        "This object represents the MLSP proxy MAC address."
    ::= { unisDot11sMlspCfgEntry 2 }

unisDot11sMlspRowStatus OBJECT-TYPE
    SYNTAX      RowStatus
    MAX-ACCESS  read-create
    STATUS      current
    DESCRIPTION
        "The status of this table entry."
    ::= { unisDot11sMlspCfgEntry 3 }

-- *****************************************************************************
-- * End of unisDot11sMlspCfgTable Definition
-- *****************************************************************************
-- *****************************************************************************
-- *  unisDot11sRadioCfgTable Definition
-- *****************************************************************************
unisDot11sRadioCfgTable OBJECT-TYPE
    SYNTAX      SEQUENCE OF UnisDot11sRadioCfgEntry
    MAX-ACCESS  not-accessible
    STATUS      current
    DESCRIPTION
        "This table is used to configure mesh to the specified radio."
    ::= { unisDot11sConfigGroup 5 }

unisDot11sRadioCfgEntry OBJECT-TYPE
    SYNTAX      UnisDot11sRadioCfgEntry
    MAX-ACCESS  not-accessible
    STATUS      current
    DESCRIPTION
        "Each entry contains mesh configure information
        of the specified radio."
    INDEX
        {
            unisDot11sCfgRadioIndex
        }
    ::= { unisDot11sRadioCfgTable 1 }

UnisDot11sRadioCfgEntry ::= SEQUENCE
    {
        unisDot11sCfgRadioIndex        UnisDot11RadioElementIndex,
        unisDot11sMeshPflMap           Integer32,
        unisDot11sMpPlcyMap            Integer32,
        unisDot11sBindInterface        Integer32
    }

unisDot11sCfgRadioIndex OBJECT-TYPE
    SYNTAX      UnisDot11RadioElementIndex
    MAX-ACCESS  not-accessible
    STATUS      current
    DESCRIPTION
        "Represents index of the radio."
    ::= { unisDot11sRadioCfgEntry 1 }

unisDot11sMeshPflMap OBJECT-TYPE
    SYNTAX      Integer32
    MAX-ACCESS  read-write
    STATUS      current
    DESCRIPTION
        "This object represents the number of the mesh profile mapped to
        the specified radio.  The value is zero when the radio is not
        bound to a mesh profile."
    DEFVAL      { 0 }
    ::= { unisDot11sRadioCfgEntry 2 }

unisDot11sMpPlcyMap OBJECT-TYPE
    SYNTAX      Integer32
    MAX-ACCESS  read-write
    STATUS      current
    DESCRIPTION
        "This object represents the index of the MP policy mapped to the
        specified radio.  The MP policy is the default policy when the radio
        is not bound to the user-defined MP policy.
        The index of the default policy is 1.
        This object cannot be modified when the radio is enabled."
    DEFVAL      { 1 }
    ::= { unisDot11sRadioCfgEntry 3 }

unisDot11sBindInterface OBJECT-TYPE
    SYNTAX      Integer32
    MAX-ACCESS  read-write
    STATUS      current
    DESCRIPTION
        "This object represents the number of the WLAN-Mesh interface
        mapped to the specified radio.  The value is -1 when the
        radio is not bound to a WLAN-Mesh interface."
    DEFVAL      { -1 }
    ::= { unisDot11sRadioCfgEntry 4 }

-- *****************************************************************************
-- * End of unisDot11sRadioCfgTable Definition
-- *****************************************************************************
-- *****************************************************************************
-- *  unisDot11sAPCfgTable Definition
-- *****************************************************************************
unisDot11sAPCfgTable OBJECT-TYPE
    SYNTAX      SEQUENCE OF UnisDot11sAPCfgEntry
    MAX-ACCESS  not-accessible
    STATUS      current
    DESCRIPTION
        "This table is used to configure mesh to the specified AP."
    ::= { unisDot11sConfigGroup 6 }

unisDot11sAPCfgEntry OBJECT-TYPE
    SYNTAX      UnisDot11sAPCfgEntry
    MAX-ACCESS  not-accessible
    STATUS      current
    DESCRIPTION
        "Each entry contains mesh configure information
        of the specified AP."
    INDEX
        {
            unisDot11APElementIndex
        }
    ::= { unisDot11sAPCfgTable 1 }

UnisDot11sAPCfgEntry ::= SEQUENCE
    {
        unisDot11sPortalEnable         TruthValue
    }

unisDot11sPortalEnable OBJECT-TYPE
    SYNTAX      TruthValue
    MAX-ACCESS  read-write
    STATUS      current
    DESCRIPTION
        "This object indicates whether the portal service is enabled.
        'true': The portal service is enabled.
        'false': The portal service is disabled."
    DEFVAL      { false }
    ::= { unisDot11sAPCfgEntry 1 }

-- *****************************************************************************
-- * End of unisDot11sAPCfgTable Definition
-- *****************************************************************************
-- *****************************************************************************
-- *  unisDot11sWDSPeerMacTable Definition
-- *****************************************************************************
unisDot11sWDSPeerMacTable OBJECT-TYPE
    SYNTAX      SEQUENCE OF UnisDot11sWDSPeerMacEntry
    MAX-ACCESS  not-accessible
    STATUS      current
    DESCRIPTION
        "This table is used to configure wireless distribution system (WDS).
        The row of this table cannot be modified."
    ::= { unisDot11sWDSConfigGroup 1 }

unisDot11sWDSPeerMacEntry OBJECT-TYPE
    SYNTAX      UnisDot11sWDSPeerMacEntry
    MAX-ACCESS  not-accessible
    STATUS      current
    DESCRIPTION
        "Each entry contains information of WDS."
    INDEX
        {
            unisDot11sCfgRadioIndex,
            unisDot11sWDSPeerMacIndex
        }
    ::= { unisDot11sWDSPeerMacTable 1 }

UnisDot11sWDSPeerMacEntry ::= SEQUENCE
    {
        unisDot11sWDSPeerMacIndex      Integer32,
        unisDot11sWDSPeerMacAddrss     MacAddress,
        unisDot11sWDSPeerMacRowStatus  RowStatus
    }

unisDot11sWDSPeerMacIndex OBJECT-TYPE
    SYNTAX      Integer32
    MAX-ACCESS  not-accessible
    STATUS      current
    DESCRIPTION
        "This object represents the peer MAC address index."
    ::= { unisDot11sWDSPeerMacEntry 1 }

unisDot11sWDSPeerMacAddrss OBJECT-TYPE
    SYNTAX      MacAddress
    MAX-ACCESS  read-create
    STATUS      current
    DESCRIPTION
        "This object represents the peer MAC address."
    ::= { unisDot11sWDSPeerMacEntry 2 }

unisDot11sWDSPeerMacRowStatus OBJECT-TYPE
    SYNTAX      RowStatus
    MAX-ACCESS  read-create
    STATUS      current
    DESCRIPTION
        "The status of this table entry."
    ::= { unisDot11sWDSPeerMacEntry 3 }

-- *****************************************************************************
-- * End of unisDot11sWDSPeerMacTable Definition
-- *****************************************************************************
-- *****************************************************************************
-- *  unisDot11sMlspExtCfgTable Definition
-- *****************************************************************************
unisDot11sMlspExtCfgTable OBJECT-TYPE
    SYNTAX      SEQUENCE OF UnisDot11sMlspExtCfgEntry
    MAX-ACCESS  not-accessible
    STATUS      current
    DESCRIPTION
        "This table is used to configure MLSP proxy MAC address.
        Only if the specified MP policy is modifiable and MLSP
        is enabled, the row of this table can be created and deleted.
        The row of this table cannot be modified."
    ::= { unisDot11sConfigGroup 7 }

unisDot11sMlspExtCfgEntry OBJECT-TYPE
    SYNTAX      UnisDot11sMlspExtCfgEntry
    MAX-ACCESS  not-accessible
    STATUS      current
    DESCRIPTION
        "Each entry contains MLSP proxy MAC address infomation."
    INDEX
        {
            unisDot11sMlspExtPolicyName,
            unisDot11sMlspExtProxyMac,
            unisDot11sMlspExtProxyVlanID
        }
    ::= { unisDot11sMlspExtCfgTable 1 }

UnisDot11sMlspExtCfgEntry ::= SEQUENCE
    {
            unisDot11sMlspExtPolicyName       OCTET STRING,
            unisDot11sMlspExtProxyMac         MacAddress,
            unisDot11sMlspExtProxyVlanID      Integer32,
            unisDot11sMlspExtProxyIP          IpAddress,
            unisDot11sMlspExtRowStatus        RowStatus
    }
unisDot11sMlspExtPolicyName OBJECT-TYPE
    SYNTAX      OCTET STRING (SIZE (1..31))
    MAX-ACCESS  read-only
    STATUS      current
    DESCRIPTION
        "This object represents the MP policy name.
        An MP policy cannot be created with the name of the
        default policy.
        Modification is not supported."
    ::= { unisDot11sMlspExtCfgEntry 1 }

unisDot11sMlspExtProxyMac OBJECT-TYPE
    SYNTAX      MacAddress
    MAX-ACCESS  read-only
    STATUS      current
    DESCRIPTION
        "This object represents the MLSP proxy MAC address."
    ::= { unisDot11sMlspExtCfgEntry 2 }


unisDot11sMlspExtProxyVlanID OBJECT-TYPE
    SYNTAX      Integer32(1..4096)
    MAX-ACCESS  read-only
    STATUS      current
    DESCRIPTION
        "This object represents the MLSP proxy VLAN ID."
    ::= { unisDot11sMlspExtCfgEntry 3 }

unisDot11sMlspExtProxyIP OBJECT-TYPE
    SYNTAX      IpAddress
    MAX-ACCESS  read-create
    STATUS      current
    DESCRIPTION
        "This object represents the MLSP proxy IP address."
    ::= { unisDot11sMlspExtCfgEntry 4 }

unisDot11sMlspExtRowStatus OBJECT-TYPE
    SYNTAX      RowStatus
    MAX-ACCESS  read-create
    STATUS      current
    DESCRIPTION
        "The status of this table entry."
    ::= { unisDot11sMlspExtCfgEntry 5 }

-- *****************************************************************************
-- * End of unisDot11sMlspExtCfgTable Definition
-- *****************************************************************************
-- *****************************************************************************
-- *  unisDot11sMeshLinkStatusTable Definition
-- *****************************************************************************
unisDot11sMeshLinkStatusTable OBJECT-TYPE
    SYNTAX      SEQUENCE OF UnisDot11sMeshLinkStatusEntry
    MAX-ACCESS  not-accessible
    STATUS      current
    DESCRIPTION
        "This table is used to represent the status of mesh link."
    ::= { unisDot11sMeshStatusGroup 1 }

unisDot11sMeshLinkStatusEntry OBJECT-TYPE
    SYNTAX      UnisDot11sMeshLinkStatusEntry
    MAX-ACCESS  not-accessible
    STATUS      current
    DESCRIPTION
        "Each entry contains status information of mesh link."
    INDEX
        {
            unisDot11sMeshLinkIfIndex
        }
    ::= { unisDot11sMeshLinkStatusTable 1 }

UnisDot11sMeshLinkStatusEntry ::= SEQUENCE
    {
        unisDot11sMeshLinkIfIndex        Unsigned32,
        unisDot11sMeshLinkName           OCTET STRING,
        unisDot11sMeshLinkBSSID          MacAddress,
        unisDot11sMeshLinkPeerMac        MacAddress,
        unisDot11sMeshLinkExistDuration  Integer32,
        unisDot11sMeshLinkType           INTEGER,
        unisDot11sMeshLinkSNR            Integer32,
        unisDot11sMeshLinkNoise          Integer32,
        unisDot11sMeshLinkPeerSNR        Integer32,
        unisDot11sMeshLinkPeerNoise      Integer32,
        unisDot11sMeshLinkPeerIPAddress  IpAddress,
        unisDot11sMeshLinkPeerSystemName OCTET STRING
    }

unisDot11sMeshLinkIfIndex OBJECT-TYPE
    SYNTAX      Unsigned32
    MAX-ACCESS  not-accessible
    STATUS      current
    DESCRIPTION
        "This object represents the interface index of the mesh link."
    ::= { unisDot11sMeshLinkStatusEntry 1 }

unisDot11sMeshLinkName OBJECT-TYPE
    SYNTAX      OCTET STRING
    MAX-ACCESS  read-only
    STATUS      current
    DESCRIPTION
        "This object represents the name of the mesh link."
    ::= { unisDot11sMeshLinkStatusEntry 2 }

unisDot11sMeshLinkBSSID OBJECT-TYPE
    SYNTAX      MacAddress
    MAX-ACCESS  read-only
    STATUS      current
    DESCRIPTION
        "This object represents the BSS ID of the mesh link."
    ::= { unisDot11sMeshLinkStatusEntry 3 }

unisDot11sMeshLinkPeerMac OBJECT-TYPE
    SYNTAX      MacAddress
    MAX-ACCESS  read-only
    STATUS      current
    DESCRIPTION
        "This object represents the peer MAC address of the mesh link."
    ::= { unisDot11sMeshLinkStatusEntry 4 }

unisDot11sMeshLinkExistDuration OBJECT-TYPE
    SYNTAX      Integer32
    UNITS       "second"
    MAX-ACCESS  read-only
    STATUS      current
    DESCRIPTION
        "This object represents the time for which the link has been up."
    ::= { unisDot11sMeshLinkStatusEntry 5 }

unisDot11sMeshLinkType OBJECT-TYPE
    SYNTAX      INTEGER
        {
            active(1),
            dormant(2)
        }
    MAX-ACCESS  read-only
    STATUS      current
    DESCRIPTION
        "This object represents the type for the link."
    ::= { unisDot11sMeshLinkStatusEntry 6 }

unisDot11sMeshLinkSNR OBJECT-TYPE
    SYNTAX      Integer32
    UNITS       "percent"
    MAX-ACCESS  read-only
    STATUS      current
    DESCRIPTION
        "Represents the SNR for the link."
    ::= { unisDot11sMeshLinkStatusEntry 7 }

unisDot11sMeshLinkNoise OBJECT-TYPE
    SYNTAX      Integer32
    MAX-ACCESS  read-only
    STATUS      current
    DESCRIPTION
        "Represents the noise for the link."
    ::= { unisDot11sMeshLinkStatusEntry 8 }

unisDot11sMeshLinkPeerSNR OBJECT-TYPE
    SYNTAX      Integer32
    UNITS       "percent"
    MAX-ACCESS  read-only
    STATUS      current
    DESCRIPTION
        "Represents the SNR transferred from the neighbor of this mesh link."
    ::= { unisDot11sMeshLinkStatusEntry 9 }

unisDot11sMeshLinkPeerNoise OBJECT-TYPE
    SYNTAX      Integer32
    MAX-ACCESS  read-only
    STATUS      current
    DESCRIPTION
        "Represents the noise transferred from the neighbor of this mesh link."
    ::= { unisDot11sMeshLinkStatusEntry 10 }

unisDot11sMeshLinkPeerIPAddress OBJECT-TYPE
    SYNTAX      IpAddress
    MAX-ACCESS  read-only
    STATUS      current
    DESCRIPTION
        "Represents the IP address of the neighbor of this mesh link."
    ::= { unisDot11sMeshLinkStatusEntry 11 }

unisDot11sMeshLinkPeerSystemName OBJECT-TYPE
    SYNTAX      OCTET STRING
    MAX-ACCESS  read-only
    STATUS      current
    DESCRIPTION
        "Represents the system name of the neighbor of this mesh link."
    ::= { unisDot11sMeshLinkStatusEntry 12 }

-- *****************************************************************************
-- * End of unisDot11sMeshLinkStatusTable Definition
-- *****************************************************************************

-- *****************************************************************************
-- *  unisDot11sMeshLinkStatisTable Definition
-- *****************************************************************************
unisDot11sMeshLinkStatisTable OBJECT-TYPE
    SYNTAX      SEQUENCE OF UnisDot11sMeshLinkStatisEntry
    MAX-ACCESS  not-accessible
    STATUS      current
    DESCRIPTION
        "This table is used to represent the statistical information of
         mesh link."
    ::= { unisDot11sMeshStatusGroup 2 }

unisDot11sMeshLinkStatisEntry OBJECT-TYPE
    SYNTAX      UnisDot11sMeshLinkStatisEntry
    MAX-ACCESS  not-accessible
    STATUS      current
    DESCRIPTION
        "Each entry contains statistical information of mesh link."
    INDEX
        {
            unisDot11APElementIndex,
            unisDot11sMeshLinkStatIfIndex
        }
    ::= { unisDot11sMeshLinkStatisTable 1 }

UnisDot11sMeshLinkStatisEntry ::= SEQUENCE
    {
        unisDot11sMeshLinkStatIfIndex    Unsigned32,
        unisDot11sMeshLinkNbrIndex       Unsigned32,
        unisDot11sMeshLinkRxTotByte      Counter32,
        unisDot11sMeshLinkRxTotPkt       Counter32,
        unisDot11sMeshLinkRxUniPkt       Counter32,
        unisDot11sMeshLinkRxBrocPkt      Counter32,
        unisDot11sMeshLinkRxMuticPkt     Counter32,
        unisDot11sMeshLinkRxDiscPkt      Counter32,
        unisDot11sMeshLinkTxTotByte      Counter32,
        unisDot11sMeshLinkTxTotPkt       Counter32,
        unisDot11sMeshLinkTxUniPkt       Counter32,
        unisDot11sMeshLinkTxBrocPkt      Counter32,
        unisDot11sMeshLinkTxMuticPkt     Counter32,
        unisDot11sMeshLinkTxDiscPkt      Counter32,
        unisDot11sMeshLinkIFName         OCTET STRING
    }

unisDot11sMeshLinkStatIfIndex OBJECT-TYPE
    SYNTAX      Unsigned32
    MAX-ACCESS  not-accessible
    STATUS      current
    DESCRIPTION
        "This object represents the interface index of the mesh link."
    ::= { unisDot11sMeshLinkStatisEntry 1 }

unisDot11sMeshLinkNbrIndex OBJECT-TYPE
    SYNTAX      Unsigned32
    MAX-ACCESS  read-only
    STATUS      current
    DESCRIPTION
        "Represents the neighbor index of the mesh link."
    ::= { unisDot11sMeshLinkStatisEntry 2 }

unisDot11sMeshLinkRxTotByte OBJECT-TYPE
    SYNTAX      Counter32
    MAX-ACCESS  read-only
    STATUS      current
    DESCRIPTION
        "Represents the amount of bytes that the mesh link received."
    ::= { unisDot11sMeshLinkStatisEntry 3 }

unisDot11sMeshLinkRxTotPkt OBJECT-TYPE
    SYNTAX      Counter32
    MAX-ACCESS  read-only
    STATUS      current
    DESCRIPTION
        "Represents the amount of packets that the mesh link received."
    ::= { unisDot11sMeshLinkStatisEntry 4 }

unisDot11sMeshLinkRxUniPkt OBJECT-TYPE
    SYNTAX      Counter32
    MAX-ACCESS  read-only
    STATUS      current
    DESCRIPTION
        "Represents the amount of unicast packets that the mesh link received."
    ::= { unisDot11sMeshLinkStatisEntry 5 }

unisDot11sMeshLinkRxBrocPkt OBJECT-TYPE
    SYNTAX      Counter32
    MAX-ACCESS  read-only
    STATUS      current
    DESCRIPTION
        "Represents the amount of broadcast packets that the mesh link
         received."
    ::= { unisDot11sMeshLinkStatisEntry 6 }

unisDot11sMeshLinkRxMuticPkt OBJECT-TYPE
    SYNTAX      Counter32
    MAX-ACCESS  read-only
    STATUS      current
    DESCRIPTION
        "Represents the amount of multicast packets that the mesh link
         received."
    ::= { unisDot11sMeshLinkStatisEntry 7 }

unisDot11sMeshLinkRxDiscPkt OBJECT-TYPE
    SYNTAX      Counter32
    MAX-ACCESS  read-only
    STATUS      current
    DESCRIPTION
        "Represents the amount of packets that the mesh link discarded."
    ::= { unisDot11sMeshLinkStatisEntry 8 }

unisDot11sMeshLinkTxTotByte OBJECT-TYPE
    SYNTAX      Counter32
    MAX-ACCESS  read-only
    STATUS      current
    DESCRIPTION
        "Represents the total amount of bytes that the mesh link transmitted."
    ::= { unisDot11sMeshLinkStatisEntry 9 }

unisDot11sMeshLinkTxTotPkt OBJECT-TYPE
    SYNTAX      Counter32
    MAX-ACCESS  read-only
    STATUS      current
    DESCRIPTION
        "Represents the total amount of packets that the mesh link transmitted."
    ::= { unisDot11sMeshLinkStatisEntry 10 }

unisDot11sMeshLinkTxUniPkt OBJECT-TYPE
    SYNTAX      Counter32
    MAX-ACCESS  read-only
    STATUS      current
    DESCRIPTION
        "Represents the amount of unicast packets that the mesh link
         transmitted."
    ::= { unisDot11sMeshLinkStatisEntry 11 }

unisDot11sMeshLinkTxBrocPkt OBJECT-TYPE
    SYNTAX      Counter32
    MAX-ACCESS  read-only
    STATUS      current
    DESCRIPTION
        "Represents the amount of broadcast packets that the mesh link
         transmitted."
    ::= { unisDot11sMeshLinkStatisEntry 12 }

unisDot11sMeshLinkTxMuticPkt OBJECT-TYPE
    SYNTAX      Counter32
    MAX-ACCESS  read-only
    STATUS      current
    DESCRIPTION
        "Represents the amount of multicast packets that the mesh link
         transmitted."
    ::= { unisDot11sMeshLinkStatisEntry 13 }

unisDot11sMeshLinkTxDiscPkt OBJECT-TYPE
    SYNTAX      Counter32
    MAX-ACCESS  read-only
    STATUS      current
    DESCRIPTION
        "Represents the amount of discarded packets that the mesh link
         transmitted."
    ::= { unisDot11sMeshLinkStatisEntry 14 }

unisDot11sMeshLinkIFName    OBJECT-TYPE
    SYNTAX      OCTET STRING
    MAX-ACCESS  read-only
    STATUS      current
    DESCRIPTION
        "Represents the name of mesh link interface."
    ::= { unisDot11sMeshLinkStatisEntry 15 }

-- *****************************************************************************
-- * End of unisDot11sMeshLinkStatisTable Definition
-- *****************************************************************************

-- *****************************************************************************
-- *  unisDot11sMeshNbrStatusTable Definition
-- *****************************************************************************
unisDot11sMeshNbrStatusTable OBJECT-TYPE
    SYNTAX      SEQUENCE OF UnisDot11sMeshNbrStatusEntry
    MAX-ACCESS  not-accessible
    STATUS      current
    DESCRIPTION
        "This table represents the status information for the neighbors of MP."
    ::= { unisDot11sMeshStatusGroup 3 }

unisDot11sMeshNbrStatusEntry OBJECT-TYPE
    SYNTAX      UnisDot11sMeshNbrStatusEntry
    MAX-ACCESS  not-accessible
    STATUS      current
    DESCRIPTION
        "Each entry of the table will provide status information for the
         neighbors of MP."
    INDEX
        {
            unisDot11APElementIndex,
            unisDot11sMeshNbrIndex
        }
    ::= { unisDot11sMeshNbrStatusTable 1 }

UnisDot11sMeshNbrStatusEntry ::= SEQUENCE
    {
        unisDot11sMeshNbrIndex          Unsigned32,
        unisDot11sMeshNbrRadioID        Unsigned32,
        unisDot11sMeshLocalMeshID       OCTET STRING,
        unisDot11sMeshNbrMeshID         OCTET STRING,
        unisDot11sMeshNbrBSSID          MacAddress,
        unisDot11sMeshNbrPeerMac        MacAddress,
        unisDot11sMeshLinkInMp          Unsigned32,
        unisDot11sMeshMPLinkStatus      INTEGER,
        unisDot11sMeshNbrChannel        Unsigned32,
        unisDot11sMeshNbrLinkDuration   Integer32,
        unisDot11sMeshNbrRSSI           Integer32,
        unisDot11sMeshNbrSNR            Integer32
    }

unisDot11sMeshNbrIndex OBJECT-TYPE
    SYNTAX      Unsigned32
    MAX-ACCESS  not-accessible
    STATUS      current
    DESCRIPTION
        "Represents the index for the neighbor."
    ::= { unisDot11sMeshNbrStatusEntry 1 }

unisDot11sMeshNbrRadioID OBJECT-TYPE
    SYNTAX      Unsigned32
    MAX-ACCESS  read-only
    STATUS      current
    DESCRIPTION
        "Represents the radio ID of the neighbor."
    ::= { unisDot11sMeshNbrStatusEntry 2 }

unisDot11sMeshLocalMeshID OBJECT-TYPE
    SYNTAX      OCTET STRING(SIZE(0..32))
    MAX-ACCESS  read-only
    STATUS      current
    DESCRIPTION
        "Represents the local mesh ID."
    ::= { unisDot11sMeshNbrStatusEntry 3 }

unisDot11sMeshNbrMeshID OBJECT-TYPE
    SYNTAX      OCTET STRING(SIZE(0..32))
    MAX-ACCESS  read-only
    STATUS      current
    DESCRIPTION
        "Represents the mesh ID of the neighbor."
    ::= { unisDot11sMeshNbrStatusEntry 4 }

unisDot11sMeshNbrBSSID OBJECT-TYPE
    SYNTAX      MacAddress
    MAX-ACCESS  read-only
    STATUS      current
    DESCRIPTION
        "Represents the BSS ID of the neighbor."
    ::= { unisDot11sMeshNbrStatusEntry 5 }

unisDot11sMeshNbrPeerMac OBJECT-TYPE
    SYNTAX      MacAddress
    MAX-ACCESS  read-only
    STATUS      current
    DESCRIPTION
        "Represents the MAC address of the peer neighbor."
    ::= { unisDot11sMeshNbrStatusEntry 6 }

unisDot11sMeshLinkInMp OBJECT-TYPE
    SYNTAX      Unsigned32
    MAX-ACCESS  read-only
    STATUS      current
    DESCRIPTION
        "Represents the interface index of mesh link that used to connect with
         this neighbor."
    ::= { unisDot11sMeshNbrStatusEntry 7 }

unisDot11sMeshMPLinkStatus OBJECT-TYPE
    SYNTAX      INTEGER
        {
            processing(1),
            up(2),
            down(3)
        }
    MAX-ACCESS  read-only
    STATUS      current
    DESCRIPTION
        "Represents the status of mesh link that used to connect with this
         neighbor."
    ::= { unisDot11sMeshNbrStatusEntry 8 }

unisDot11sMeshNbrChannel OBJECT-TYPE
    SYNTAX      Unsigned32
    MAX-ACCESS  read-only
    STATUS      current
    DESCRIPTION
        "Represents the channel number used by this neighbor."
    ::= { unisDot11sMeshNbrStatusEntry 9 }

unisDot11sMeshNbrLinkDuration OBJECT-TYPE
    SYNTAX      Integer32
    UNITS       "second"
    MAX-ACCESS  read-only
    STATUS      current
    DESCRIPTION
        "Represents the duration of mesh link that used to connect with this
         neighbor."
    ::= { unisDot11sMeshNbrStatusEntry 10 }

unisDot11sMeshNbrRSSI OBJECT-TYPE
    SYNTAX      Integer32
    MAX-ACCESS  read-only
    STATUS      current
    DESCRIPTION
        "Represents the RSSI of mesh link that used to connect with this
         neighbor."
    ::= { unisDot11sMeshNbrStatusEntry 11 }

unisDot11sMeshNbrSNR OBJECT-TYPE
    SYNTAX      Integer32
    UNITS       "percent"
    MAX-ACCESS  read-only
    STATUS      current
    DESCRIPTION
        "Represents the SNR of mesh link that used to connect with this
         neighbor."
    ::= { unisDot11sMeshNbrStatusEntry 12 }

-- *****************************************************************************
-- *  End of unisDot11sMeshNbrStatusTable Definition
-- *****************************************************************************
-- *****************************************************************************
-- *  unisDot11sMeshLinkTraps Definition
-- *****************************************************************************

unisDot11sMeshLinkTraps OBJECT IDENTIFIER ::= { unisDot11sMeshLinkNotifyGroup 0 }

unisDot11sMeshLinkSwitchTrap NOTIFICATION-TYPE
    OBJECTS
        {
            unisDot11sMeshLinkBSSIDMAC,
            unisDot11sMeshLinkPeerMAC
        }
    STATUS        current
    DESCRIPTION
        "This notification is to indicate the occurrence of a mesh link switchover."
    ::= { unisDot11sMeshLinkTraps 1 }

unisDot11sMeshLinkTrapObjects OBJECT IDENTIFIER ::= { unisDot11sMeshLinkNotifyGroup 1 }

unisDot11sMeshLinkBSSIDMAC OBJECT-TYPE
    SYNTAX      MacAddress
    MAX-ACCESS  accessible-for-notify
    STATUS      current
    DESCRIPTION
        "Represents the BSSID of the MP."
    ::= { unisDot11sMeshLinkTrapObjects 1 }

unisDot11sMeshLinkPeerMAC OBJECT-TYPE
    SYNTAX      MacAddress
    MAX-ACCESS  accessible-for-notify
    STATUS      current
    DESCRIPTION
        "Represents the MAC address of the peer MP after mesh link switchover."
    ::= { unisDot11sMeshLinkTrapObjects 2 }
END
