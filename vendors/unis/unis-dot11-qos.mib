-- =====================================================================
-- Copyright (c) 2020 Unisyue Technologies Co., Ltd.  All rights reserved.
--
-- Description: The file defines a MIB to provide WLAN QoS configuration.
-- configuration information.
-- Reference:
-- Version: V1.2
-- History:
-- V1.0 2008-7-23 created by heziqi
-- V1.1 2010-03-15 Modified by Wang Lu
--      Add unisDot11RadioWmmEdcaCfg2Table
-- V1.2 2013-02-17 Modified by Xiao min
--      Change SYNTAX of unisDot11RadioCacUserNum
-- =====================================================================
UNIS-DOT11-QOS-MIB DEFINITIONS ::= BEGIN

IMPORTS
        TruthValue,
        TEXTUAL-CONVENTION
    FROM SNMPv2-TC
        MODULE-IDENTITY,
        OBJECT-TYPE,
        Integer32
    FROM SNMPv2-SMI
        unisDot11,
        UnisDot11QosAcType,
        UnisDot11RadioElementIndex,
        UnisDot11ObjectIDType,
        UnisDot11RadioScopeType
    FROM UNIS-DOT11-REF-MIB;

unisDot11QoS MODULE-IDENTITY
    LAST-UPDATED "200807231200Z"
    ORGANIZATION
        "Unisyue Technologies Co., Ltd."
    CONTACT-INFO
        ""
    DESCRIPTION
        "This MIB provides information about WLAN QoS configuration.

        GLOSSARY

        IEEE 802.11
        Standard to encourage interoperability among
        wireless networking equipment.

        WMM
        WMM is a wireless QoS protocol designed to preferentially
        transmit packets with high priority, thus guaranteeing
        better QoS services for voice and video applications in
        a wireless network.

        EDCA
        Enhanced distributed channel access (EDCA) is a channel
        contention mechanism designed by WMM to preferentially
        transmit packets with high priority and allocate more
        bandwidth to such packets.

        AC
        Access category (AC), is used for channel contention.
        WMM defines four access categories; they are AC-VO (voice),
        AC-VI (video), AC-BE (best-effort), and AC-BK (background)
        in the descending order of priority.  When contending for a
        channel, a high-priority AC preempts a low-priority AC.

        CAC
        Connection admission control (CAC) limits the number of
        clients that are using high-priority ACs (AC-VO and AC-VI)
        to guarantee sufficient bandwidth for existing high-priority
        traffic.

        U-APSD
        Unscheduled automatic power-save delivery (U-APSD) is a new
        power saving mechanism defined by WMM to enhance the power
        saving capability of clients.

        SVP
        SpectraLink voice priority (SVP) is a voice priority protocol
        designed by the Spectralink company to guarantee QoS for voice
        traffic."

    REVISION "200807231200Z"
    DESCRIPTION
            "The initial revision of this MIB module."
    ::= { unisDot11 9 }

-- ==================================================================
-- Textual Conventions
-- ==================================================================
UnisDot11WMMSVPMapAC ::=  TEXTUAL-CONVENTION
    STATUS      current
    DESCRIPTION
        "The AC level which SVP packets are assigned to.
         acbk    : for background access category,
         acbe    : for best-effort access category,
         acvi    : for voice access category,
         acvo    : for video access category,
         disable : for disable SVP feature
        "
    SYNTAX      INTEGER
        {
            acbk(1),
            acbe(2),
            acvi(3),
            acvo(4),
            disable(5)
        }

UnisDot11WMMCACPolicy ::=  TEXTUAL-CONVENTION
    STATUS      current
    DESCRIPTION
        "The policy of CAC.
         channelUtilization : the channel utilization-based admission policy
                                 for CAC,
         userNumber         : the users-based admission policy for CAC"
    SYNTAX      INTEGER
        {
            channelUtilization(1),
            userNumber(2)
        }



-- ==================================================================
-- Major sections
-- ==================================================================
unisDot11WmmCfgGroup OBJECT IDENTIFIER   ::= { unisDot11QoS 1 }
--  Roaming Configuration Group has the following children:
--  unisDot11RadioWmmCfgTable            ::= { unisDot11WmmCfgGroup 1 }
--  unisDot11RadioWmmEdcaCfgTable        ::= { unisDot11WmmCfgGroup 2 }
--  unisDot11StationWmmEdcaTable         ::= { unisDot11WmmCfgGroup 3 }
--  unisDot11WmmResetGroup               ::= { unisDot11WmmCfgGroup 4 }

-- ==================================================================
-- unisDot11WmmCfgGroup Definition
-- ==================================================================
-- ==================================================================
-- unisDot11RadioWmmCfgTable Definition
-- ==================================================================
unisDot11RadioWmmCfgTable OBJECT-TYPE
    SYNTAX      SEQUENCE OF UnisDot11RadioWmmCfgEntry
    MAX-ACCESS  not-accessible
    STATUS      current
    DESCRIPTION
        "The table defines the basic parameters for WMM configuration."
    ::= { unisDot11WmmCfgGroup 1 }

unisDot11RadioWmmCfgEntry OBJECT-TYPE
    SYNTAX      UnisDot11RadioWmmCfgEntry
    MAX-ACCESS  not-accessible
    STATUS      current
    DESCRIPTION
        "This entry contains the basic information for WMM configuration."
    INDEX
        {
            unisDot11WmmRadioIndex
        }
    ::= { unisDot11RadioWmmCfgTable 1 }

UnisDot11RadioWmmCfgEntry ::= SEQUENCE
    {
        unisDot11WmmRadioIndex           UnisDot11RadioElementIndex,
        unisDot11RadioWmmEnabled         TruthValue,
        unisDot11RadioSVPMapToAC         UnisDot11WMMSVPMapAC,
        unisDot11RadioCacPolicy          UnisDot11WMMCACPolicy,
        unisDot11RadioCacChlUtlValue     Integer32,
        unisDot11RadioCacUserNum         Integer32
    }

unisDot11WmmRadioIndex OBJECT-TYPE
    SYNTAX      UnisDot11RadioElementIndex
    MAX-ACCESS  not-accessible
    STATUS      current
    DESCRIPTION
        "Represents index of the radio."
    ::= { unisDot11RadioWmmCfgEntry 1 }

unisDot11RadioWmmEnabled OBJECT-TYPE
    SYNTAX      TruthValue
    MAX-ACCESS  read-write
    STATUS      current
    DESCRIPTION
        "Represents the status of WMM in radio.
         'true' : The WMM function is enabled.
         'false': The WMM function is disabled."
    ::= { unisDot11RadioWmmCfgEntry 2 }

unisDot11RadioSVPMapToAC OBJECT-TYPE
    SYNTAX      UnisDot11WMMSVPMapAC
    MAX-ACCESS  read-write
    STATUS      current
    DESCRIPTION
        "Represents the AC level which SVP packets are assigned to.
         'acbk'   : Specifies the AC-BK (background traffic) queue.
         'acbe'   : Specifies the AC-BE (best-effort traffic) queue.
         'acvi'   : Specifies the AC-VI (video traffic) queue.
         'acvo'   : Specifies the AC-VO (voice traffic) queue.
         'disable' : Disable SVP packet mapping."
    ::= { unisDot11RadioWmmCfgEntry 3 }

unisDot11RadioCacPolicy OBJECT-TYPE
    SYNTAX      UnisDot11WMMCACPolicy
    MAX-ACCESS  read-write
    STATUS      current
    DESCRIPTION
        "Represents the policy for CAC.
         CAC requires that a client obtain permission of the AP before it can
         use a high-priority AC for transmission, thus guaranteeing bandwidth
         to the clients that have gained access.  CAC controls real time traffic
         (AC-VO and AC-VI traffic) but not common data traffic (AC-BE and AC-BK
         traffic)."
    ::= { unisDot11RadioWmmCfgEntry 4 }

unisDot11RadioCacChlUtlValue OBJECT-TYPE
    SYNTAX      Integer32(0..100)
    UNITS       "percent"
    MAX-ACCESS  read-write
    STATUS      current
    DESCRIPTION
        "Represents Maximum channel utilization rate, that is, the medium
         time of the accepted AC-VO traffic and AC-VI traffic to the valid
         time during the unit time.
         This object can be set only if the value of unisDot11RadioCacPolicy is
         ChannelUtilization."
    ::= { unisDot11RadioWmmCfgEntry 5 }

unisDot11RadioCacUserNum OBJECT-TYPE
    SYNTAX      Integer32(0..124)
    MAX-ACCESS  read-write
    STATUS      current
    DESCRIPTION
        "Represents the users-based admission policy for CAC.
         This object can be set only if the value of unisDot11RadioCacPolicy is
         userNumber."
    ::= { unisDot11RadioWmmCfgEntry 6 }

-- ==================================================================
-- unisDot11RadioWmmEdcaCfgTable Definition
-- ==================================================================
unisDot11RadioWmmEdcaCfgTable OBJECT-TYPE
    SYNTAX      SEQUENCE OF UnisDot11RadioWmmEdcaCfgEntry
    MAX-ACCESS  not-accessible
    STATUS      current
    DESCRIPTION
        "The table defines the basic parameters for EDCA configuration of
         radio."
    ::= { unisDot11WmmCfgGroup 2 }

unisDot11RadioWmmEdcaCfgEntry OBJECT-TYPE
    SYNTAX      UnisDot11RadioWmmEdcaCfgEntry
    MAX-ACCESS  not-accessible
    STATUS      current
    DESCRIPTION
        "This entry contains the basic information for EDCA configuration of
         radio."
    INDEX
        {
            unisDot11WmmRadioIndex,
            unisDot11RadioWmmAC
        }
    ::= { unisDot11RadioWmmEdcaCfgTable 1 }

UnisDot11RadioWmmEdcaCfgEntry ::= SEQUENCE
    {
        unisDot11RadioWmmAC          UnisDot11QosAcType,
        unisDot11RadioWmmAifsn       Integer32,
        unisDot11RadioWmmEcwMin      Integer32,
        unisDot11RadioWmmEcwMax      Integer32,
        unisDot11RadioWmmTxoplimit   Integer32,
        unisDot11RadioWmmNoAck       TruthValue
    }

unisDot11RadioWmmAC OBJECT-TYPE
    SYNTAX      UnisDot11QosAcType
    MAX-ACCESS  not-accessible
    STATUS      current
    DESCRIPTION
        "Represents the AC level index of EDCA parameters of radio.
         'acbk' : Specifies AC-BK (background traffic).
         'acbe' : Specifies AC-BE (best-effort traffic).
         'acvi' : Specifies AC-VI (video traffic).
         'acvo' : Specifies AC-VO (voice traffic)."
    ::= { unisDot11RadioWmmEdcaCfgEntry 1 }

unisDot11RadioWmmAifsn OBJECT-TYPE
    SYNTAX      Integer32(1..15)
    MAX-ACCESS  read-write
    STATUS      current
    DESCRIPTION
        "Represents AIFSN parameter of EDCA.  The value range of this
         object is limited by the radio chip capability."
    ::= { unisDot11RadioWmmEdcaCfgEntry 2 }

unisDot11RadioWmmEcwMin OBJECT-TYPE
    SYNTAX      Integer32(0..15)
    MAX-ACCESS  read-write
    STATUS      current
    DESCRIPTION
        "Represents ECWmin parameter of EDCA.  The value range of this
         object is limited by the radio chip capability.
         ECWmin parameter of EDCA must be smaller than ECWmax parameter."
    ::= { unisDot11RadioWmmEdcaCfgEntry 3 }

unisDot11RadioWmmEcwMax OBJECT-TYPE
    SYNTAX      Integer32(0..15)
    MAX-ACCESS  read-write
    STATUS      current
    DESCRIPTION
        "Represents ECWmax parameter of EDCA.  The value range of this
         object is limited by the radio chip capability.
         ECWmin parameter of EDCA must be larger than ECWmax parameter."
    ::= { unisDot11RadioWmmEdcaCfgEntry 4 }

unisDot11RadioWmmTxoplimit OBJECT-TYPE
    SYNTAX      Integer32(0..65535)
    MAX-ACCESS  read-write
    STATUS      current
    DESCRIPTION
        "Represents TXOPLimit parameter of EDCA, the value must be
         in the range of 0 to 65535 (in units of 32 microseconds).
         The TXOP value of 0 indicates that only one MPDU can be
         transmitted.  The range of this argument is limited by the
         radio chip capability."
    ::= { unisDot11RadioWmmEdcaCfgEntry 5 }

unisDot11RadioWmmNoAck OBJECT-TYPE
    SYNTAX      TruthValue
    MAX-ACCESS  read-write
    STATUS      current
    DESCRIPTION
        "Represents the AC to adopt the No ACK policy.  The protocol
         defines two ACK policies: Normal ACK and No ACK."
    ::= { unisDot11RadioWmmEdcaCfgEntry 6 }

-- ==================================================================
-- unisDot11StationWmmEdcaTable Definition
-- ==================================================================
unisDot11StationWmmEdcaTable OBJECT-TYPE
    SYNTAX      SEQUENCE OF UnisDot11StationWmmEdcaEntry
    MAX-ACCESS  not-accessible
    STATUS      current
    DESCRIPTION
        "The table defines the basic parameters for EDCA configuration of
         station."
    ::= { unisDot11WmmCfgGroup 3 }

unisDot11StationWmmEdcaEntry OBJECT-TYPE
    SYNTAX      UnisDot11StationWmmEdcaEntry
    MAX-ACCESS  not-accessible
    STATUS      current
    DESCRIPTION
        "This entry contains the basic information for EDCA configuration of
         client.  If CAC is enabled for an AC, CAC is also enabled for ACs with
         higher priority.  For example, if CAC is enabled for AC-VI, CAC
         is also enabled for AC-VO.  However, enabling CAC for AC-VO does
         not enable CAC for AC-VI."
    INDEX
        {
            unisDot11WmmRadioIndex,
            unisDot11StationWmmAC
        }
    ::= { unisDot11StationWmmEdcaTable 1 }

UnisDot11StationWmmEdcaEntry ::= SEQUENCE
    {
        unisDot11StationWmmAC            UnisDot11QosAcType,
        unisDot11StationWmmAifsn         Integer32,
        unisDot11StationWmmEcwMin        Integer32,
        unisDot11StationWmmEcwMax        Integer32,
        unisDot11StationWmmTxoplimit     Integer32,
        unisDot11StationWmmCacEnabled    TruthValue
    }

unisDot11StationWmmAC OBJECT-TYPE
    SYNTAX      UnisDot11QosAcType
    MAX-ACCESS  not-accessible
    STATUS      current
    DESCRIPTION
        "Represents the AC level index of EDCA parameters of client.
         'acbk' : Specifies AC-BK (background traffic).
         'acbe' : Specifies AC-BE (best-effort traffic).
         'acvi' : Specifies AC-VI (video traffic).
         'acvo' : Specifies AC-VO (voice traffic)."
    ::= { unisDot11StationWmmEdcaEntry 1 }

unisDot11StationWmmAifsn OBJECT-TYPE
    SYNTAX      Integer32(2..15)
    MAX-ACCESS  read-write
    STATUS      current
    DESCRIPTION
        "Represents AIFSN parameter of EDCA."
    ::= { unisDot11StationWmmEdcaEntry 2 }

unisDot11StationWmmEcwMin OBJECT-TYPE
    SYNTAX      Integer32(0..15)
    MAX-ACCESS  read-write
    STATUS      current
    DESCRIPTION
        "Represents ECWmin parameter of EDCA."
    ::= { unisDot11StationWmmEdcaEntry 3 }

unisDot11StationWmmEcwMax OBJECT-TYPE
    SYNTAX      Integer32(0..15)
    MAX-ACCESS  read-write
    STATUS      current
    DESCRIPTION
        "Represents ECWmax parameter of EDCA."
    ::= { unisDot11StationWmmEdcaEntry 4 }

unisDot11StationWmmTxoplimit OBJECT-TYPE
    SYNTAX      Integer32(0..65535)
    MAX-ACCESS  read-write
    STATUS      current
    DESCRIPTION
        "Represents TXOPLimit parameter of EDCA, the value is in units of 32
         microseconds.
         The TXOP value of 0 indicates that only one MPDU can be
         transmitted."
    ::= { unisDot11StationWmmEdcaEntry 5 }

unisDot11StationWmmCacEnabled OBJECT-TYPE
    SYNTAX      TruthValue
    MAX-ACCESS  read-write
    STATUS      current
    DESCRIPTION
        "Represents the AC to adopt the No ACK policy.  The protocol
         defines two ACK policies: Normal ACK and No ACK.  Only if
         the value of unisDot11StationWmmAC is 'acvo' or 'acvi', Cac
         can be set correctly here."
    ::= { unisDot11StationWmmEdcaEntry 6 }

-- ==================================================================
-- end of unisDot11StationWmmEdcaTable Definition
-- ==================================================================
unisDot11WmmResetGroup OBJECT IDENTIFIER  ::= { unisDot11WmmCfgGroup 4 }

unisDot11WmmResetRadioByAP OBJECT-TYPE
    SYNTAX      Integer32
    MAX-ACCESS  read-write
    STATUS      current
    DESCRIPTION
        "Clear the WMM statistics information of the radio of the
         specified AP or all radios.
         The meaning of this object is the same as unisDot11APElementIndex,
         it represents the index of AP element.  If the value of this object
         is set to 0xFFFFFFFF, WMM statistics information of all radios
         will be cleared.
         The value of this object is always 0 with the get operation."
    ::= { unisDot11WmmResetGroup 1 }

unisDot11WmmResetStationByAP OBJECT-TYPE
    SYNTAX      Integer32
    MAX-ACCESS  read-write
    STATUS      current
    DESCRIPTION
        "Clear the WMM statistics information of the clients associated
         with the specified AP, or of all clients.
         The meaning of this object is the same as unisDot11APElementIndex,
         it represents the index of AP element.  If set with the
         0xFFFFFFFF, it will clear the WMM statistics information of all
         clients.
         The value of this object is always 0 with the get operation."
    ::= { unisDot11WmmResetGroup 2 }

unisDot11RadioWmmEdcaCfg2Table OBJECT-TYPE
    SYNTAX      SEQUENCE OF UnisDot11RadioWmmEdcaCfg2Entry
    MAX-ACCESS  not-accessible
    STATUS      current
    DESCRIPTION
        "The table defines the basic parameters for EDCA configuration of
         radio."
    ::= { unisDot11WmmCfgGroup 5 }

unisDot11RadioWmmEdcaCfg2Entry OBJECT-TYPE
    SYNTAX      UnisDot11RadioWmmEdcaCfg2Entry
    MAX-ACCESS  not-accessible
    STATUS      current
    DESCRIPTION
        "This entry contains the basic information for EDCA configuration of
         radio."
    INDEX
        {
            unisDot11WMMAPSerialID,
            unisDot11WMMRdId,
            unisDot11RdWmmAC
        }
    ::= { unisDot11RadioWmmEdcaCfg2Table 1 }

UnisDot11RadioWmmEdcaCfg2Entry ::= SEQUENCE
    {
        unisDot11WMMAPSerialID    UnisDot11ObjectIDType,
        unisDot11WMMRdId          UnisDot11RadioScopeType,
        unisDot11RdWmmAC          UnisDot11QosAcType,
        unisDot11RdWmmAifsn       Integer32,
        unisDot11RdWmmEcwMin      Integer32,
        unisDot11RdWmmEcwMax      Integer32,
        unisDot11RdWmmTxoplimit   Integer32
    }

unisDot11WMMAPSerialID OBJECT-TYPE
    SYNTAX      UnisDot11ObjectIDType
    MAX-ACCESS  not-accessible
    STATUS      current
    DESCRIPTION
        "Serial ID of the AP."
    ::= { unisDot11RadioWmmEdcaCfg2Entry 1 }

unisDot11WMMRdId OBJECT-TYPE
    SYNTAX      UnisDot11RadioScopeType
    MAX-ACCESS  not-accessible
    STATUS      current
    DESCRIPTION
        "radio ID of the radio."
    ::= { unisDot11RadioWmmEdcaCfg2Entry 2 }


unisDot11RdWmmAC OBJECT-TYPE
    SYNTAX      UnisDot11QosAcType
    MAX-ACCESS  not-accessible
    STATUS      current
    DESCRIPTION
        "Represents the AC level index of EDCA parameters of radio.
         'acbk' : Specifies AC-BK (background traffic).
         'acbe' : Specifies AC-BE (best-effort traffic).
         'acvi' : Specifies AC-VI (video traffic).
         'acvo' : Specifies AC-VO (voice traffic)."
    ::= { unisDot11RadioWmmEdcaCfg2Entry 3 }

unisDot11RdWmmAifsn OBJECT-TYPE
    SYNTAX      Integer32(1..15)
    MAX-ACCESS  read-write
    STATUS      current
    DESCRIPTION
        "Represents AIFSN parameter of EDCA.  The value range of this
         object is limited by the radio chip capability."
    ::= { unisDot11RadioWmmEdcaCfg2Entry 4 }

unisDot11RdWmmEcwMin OBJECT-TYPE
    SYNTAX      Integer32(0..15)
    MAX-ACCESS  read-write
    STATUS      current
    DESCRIPTION
        "Represents ECWmin parameter of EDCA.  The value range of this
         object is limited by the radio chip capability.
         ECWmin parameter of EDCA must be smaller than ECWmax parameter."
    ::= { unisDot11RadioWmmEdcaCfg2Entry 5 }

unisDot11RdWmmEcwMax OBJECT-TYPE
    SYNTAX      Integer32(0..15)
    MAX-ACCESS  read-write
    STATUS      current
    DESCRIPTION
        "Represents ECWmax parameter of EDCA.  The value range of this
         object is limited by the radio chip capability.
         ECWmin parameter of EDCA must be larger than ECWmax parameter."
    ::= { unisDot11RadioWmmEdcaCfg2Entry 6 }

unisDot11RdWmmTxoplimit OBJECT-TYPE
    SYNTAX      Integer32(0..65535)
    MAX-ACCESS  read-write
    STATUS      current
    DESCRIPTION
        "Represents TXOPLimit parameter of EDCA, the value must be
         in the range of 0 to 65535 (in units of 32 microseconds).
         The TXOP value of 0 indicates that only one MPDU can be
         transmitted.  The range of this argument is limited by the
         radio chip capability."
    ::= { unisDot11RadioWmmEdcaCfg2Entry 7 }

END
