-- =========================================================================
-- Copyright (c) 2020 Unisyue Technologies Co., Ltd.  All rights reserved.
--
-- Description:  SPB MIB
-- Reference:  Enterprise MIB
-- Version:V1.00
-- History:
--     initial version 2003-03-06
--     V1.0 6th Nov 2012
-- =========================================================================
UNIS-SPB-MIB DEFINITIONS ::= BEGIN

IMPORTS
    ifIndex
        FROM IF-MIB
    Unsigned32, OBJECT-TYPE, MODULE-IDENTITY, NOTIFICATION-TYPE
        FROM SNMPv2-SMI
    MacAddress
        FROM SNMPv2-TC
    VlanIdOrNone
        FROM Q-BRIDGE-MIB
    unisCommon
        FROM UNIS-OID-MIB
    IEEE8021SpbmSPsourceId
        FROM IEEE8021-SPB-MIB;

unisSpb MODULE-IDENTITY
    LAST-UPDATED "201211220000Z"        -- November 22, 2012 at 00:00 GMT
    ORGANIZATION
        "Unisyue Technologies Co., Ltd."
    CONTACT-INFO
        ""
    DESCRIPTION  "802.1 SPB MIB"
    REVISION  "201211220000Z"        -- November 22, 2012 at 00:00 GMT
    DESCRIPTION
        "This MIB describes objects used for managing Shortest Path Bridging
        (SPB)."
    ::= { unisCommon 128 }


unisSpbObjects OBJECT IDENTIFIER ::= { unisSpb 1 }

unisSpbSysObjects OBJECT IDENTIFIER
    ::= { unisSpbObjects 1 }

unisSpbSysStatus OBJECT-TYPE
    SYNTAX      INTEGER
        {
            enabled(1),
            disabled(2)
        }
    MAX-ACCESS read-write
    STATUS current
    DESCRIPTION
        "To descript the status of Shortest Path Bridging MAC Mode(SPBM) is
        Enabled or Disabled."
    DEFVAL { disabled }
    ::= { unisSpbSysObjects 1 }

unisSpbMulticastBVlanStatus OBJECT-TYPE
    SYNTAX      INTEGER
        {
            enabled(1),
            disabled(2)
        }
    MAX-ACCESS read-write
    STATUS current
    DESCRIPTION
        "To descript the status of SPBM multicast bvlan is Enabled or
        Disabled."
    DEFVAL { disabled }
    ::= { unisSpbSysObjects 2 }

unisSpbConfig OBJECT IDENTIFIER
    ::= { unisSpbObjects 2 }

unisSpbIfTable OBJECT-TYPE
    SYNTAX SEQUENCE OF UnisSpbIfEntry
    MAX-ACCESS not-accessible
    STATUS current
    DESCRIPTION
        "This table describes the interface status of SPBM is Enabled or
        Disabled."
    ::= { unisSpbConfig 1 }

unisSpbIfEntry OBJECT-TYPE
    SYNTAX UnisSpbIfEntry
    MAX-ACCESS not-accessible
    STATUS current
    DESCRIPTION
        "The entry of unisSpbIfEntry."
    INDEX { ifIndex }
    ::= { unisSpbIfTable 1 }

UnisSpbIfEntry ::=
    SEQUENCE
    {
        unisSpbIfStatus         INTEGER
    }

unisSpbIfStatus OBJECT-TYPE
    SYNTAX      INTEGER
        {
            enabled(1),
            disabled(2)
        }
    MAX-ACCESS read-write
    STATUS current
    DESCRIPTION
        "To descript the interface status of SPBM is Enabled or Disabled."
    DEFVAL { disabled }
    ::= { unisSpbIfEntry 1 }

unisSpbSrvTable OBJECT-TYPE
    SYNTAX SEQUENCE OF UnisSpbSrvEntry
    MAX-ACCESS not-accessible
    STATUS current
    DESCRIPTION
        "This table descript the Base VlanID(VID) associated with the service
        and the service multicast duplicate mode."
    ::= { unisSpbConfig 2 }


unisSpbSrvEntry OBJECT-TYPE
    SYNTAX UnisSpbSrvEntry
    MAX-ACCESS not-accessible
    STATUS current
    DESCRIPTION
        "The entry of unisSpbSrvEntry."
    INDEX { unisSpbSrvTableEntryTopIx,
            unisSpbSrvTableEntryIsid }
    ::= { unisSpbSrvTable 1 }

UnisSpbSrvEntry ::=
    SEQUENCE {
        unisSpbSrvTableEntryTopIx   Unsigned32,
        unisSpbSrvTableEntryIsid    Unsigned32,
        unisSpbSrvTableEntryBaseVid VlanIdOrNone,
        unisSpbSrvTableEntryMode    INTEGER
        }

unisSpbSrvTableEntryTopIx OBJECT-TYPE
    SYNTAX Unsigned32
    MAX-ACCESS not-accessible
    STATUS current
    DESCRIPTION
        "Unique identifier of this SPB topology
         This is index is allocated for this ISIS/MT instance.
         It is used as an index to most other SPB tables below and to
         select the exact ISIS instance and which MT instance together."
    ::= { unisSpbSrvEntry 1 }

unisSpbSrvTableEntryIsid OBJECT-TYPE
    SYNTAX    Unsigned32 (255..16777215)
    MAX-ACCESS not-accessible
    STATUS current
    DESCRIPTION
        "An ISID (service) originating/terminating on this bridge."
    ::= { unisSpbSrvEntry 2 }

unisSpbSrvTableEntryBaseVid OBJECT-TYPE
    SYNTAX    VlanIdOrNone
    MAX-ACCESS read-write
    STATUS current
    DESCRIPTION
        "The Base VID associated with this service.  The Base VID determines
         the ECT Algorithm that is associated with this service.  Otherwise
         no Base VID associated with the service, should be set = 0."
    ::= { unisSpbSrvEntry 3 }

unisSpbSrvTableEntryMode OBJECT-TYPE
    SYNTAX    INTEGER
        {
            headEnd(1),
            tandem(2)
        }
    MAX-ACCESS read-write
    STATUS current
    DESCRIPTION
        "Indication of supporting multicast replicate mode
         head-end/tandem."
    DEFVAL { headEnd }
    ::= { unisSpbSrvEntry 4 }

-- ==================================================================
--
-- ======================= trap definition begin ====================
--
-- ==================================================================
unisSpbTrap OBJECT IDENTIFIER ::= {  unisSpbObjects 3  }

unisSpbTraps OBJECT IDENTIFIER ::= { unisSpbTrap 0 }

unisSpbTrapsObjects OBJECT IDENTIFIER ::= { unisSpbTrap 1 }

unisSpbSPSourceConflictTrap NOTIFICATION-TYPE
    OBJECTS
        {
            unisSpbConflictSysID,
            unisSpbConflictSPSourceID
        }
    STATUS      current
    DESCRIPTION
        "This notification will be generated when the SPSourceID is conflict
        with another bridge."
    ::= { unisSpbTraps 1 }

unisSpbBMacConflictTrap NOTIFICATION-TYPE
    OBJECTS
        {
            unisSpbConflictSysID,
            unisSpbConflictBMac
        }
    STATUS      current
    DESCRIPTION
        "This notification will be generated when the BMAC is conflict
        with another bridge."
    ::= { unisSpbTraps 2 }

unisSpbConflictSysID OBJECT-TYPE
    SYNTAX MacAddress
    MAX-ACCESS accessible-for-notify
    STATUS current
    DESCRIPTION
        "The bridge's SPSourceID is conflict with this bridge."
    ::= { unisSpbTrapsObjects 1 }

unisSpbConflictSPSourceID OBJECT-TYPE
    SYNTAX IEEE8021SpbmSPsourceId
    MAX-ACCESS accessible-for-notify
    STATUS current
    DESCRIPTION
        "The Shortest Path Source Identifier which is conflict."
    ::= { unisSpbTrapsObjects 2 }

unisSpbConflictBMac OBJECT-TYPE
    SYNTAX MacAddress
    MAX-ACCESS accessible-for-notify
    STATUS current
    DESCRIPTION
        "The BMAC which is conflict."
    ::= { unisSpbTrapsObjects 3 }

END
