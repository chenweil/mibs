-- =========================================================================
-- Copyright (c) 2020 Unisyue Technologies Co., Ltd.  All rights reserved.
--
-- Description: Multicast Call Detail Record(CDR) MIB
--              In IPTV application, user join in a multicast group to order
--              video programme. Multicast CDR is implemented for record basic
--              information that a user join in a multicast group.
--              The information record will be sent to NMS.
--              This new MIB is used for configured policy to send record and
--              display online user information.
-- Reference:
-- Version: V1.0
-- History:
--   V1.0 Created by Wangxiaodong, 2007.12.15
--        Initial version.
-- =========================================================================
--
-- ==================================================================
--
-- Variables and types be imported
--
-- ==================================================================
UNIS-MCDR-MIB DEFINITIONS ::= BEGIN
IMPORTS

        MODULE-IDENTITY,OBJECT-TYPE,Unsigned32
    FROM SNMPv2-SMI

        TEXTUAL-CONVENTION,DateAndTime
    FROM SNMPv2-TC

        InetAddressType, InetAddress
    FROM INET-ADDRESS-MIB

        ifIndex
    FROM IF-MIB

        VlanId
    FROM Q-BRIDGE-MIB

        unisCommon
    FROM UNIS-OID-MIB;

unisMultCDR MODULE-IDENTITY
    LAST-UPDATED "200712150000Z"
    ORGANIZATION
        "Unisyue Technologies Co., Ltd."
    CONTACT-INFO
        ""
    DESCRIPTION
        "The initial version of this MIB file."
    REVISION "200712150000Z"
    DESCRIPTION
        "The multicast call detail record MIB."
    ::= { unisCommon  86 }

-- ==================================================================
--
-- ======================= definition begin =========================
--
-- ==================================================================

--
-- unisMultCDRCfgObject
--
unisMultCDRCfgObject OBJECT IDENTIFIER ::= { unisMultCDR 1 }

unisMultCDRStatus OBJECT-TYPE
    SYNTAX      INTEGER
        {
            enabled(1),
            disabled(2)
        }
    MAX-ACCESS  read-write
    STATUS      current
    DESCRIPTION
        "Configure to enable or disable multicast CDR function."
    ::= { unisMultCDRCfgObject 1 }

unisMultCDRReportInterval OBJECT-TYPE
    SYNTAX      INTEGER(30..600)
    MAX-ACCESS  read-write
    STATUS      current
    DESCRIPTION
        "Configure the multicast CDR report-interval. Unit: second."
    ::= { unisMultCDRCfgObject 2 }

unisMultCDRCacheLimit OBJECT-TYPE
    SYNTAX      INTEGER(16..1024)
    MAX-ACCESS  read-write
    STATUS      current
    DESCRIPTION
        "Configure the multicast CDR cache-limit."
    ::= { unisMultCDRCfgObject 3 }

unisMultCDRRecordDelay OBJECT-TYPE
    SYNTAX      INTEGER(10..600)
    MAX-ACCESS  read-write
    STATUS      current
    DESCRIPTION
        "Configure the multicast CDR record-delay. Unit: second"
    ::= { unisMultCDRCfgObject 4 }

unisMultCDRRecordSend OBJECT-TYPE
    SYNTAX      INTEGER
        {
            send(1),
            caching(2)
        }
    MAX-ACCESS  read-write
    STATUS      current
    DESCRIPTION
        "Send record at once."
    ::= { unisMultCDRCfgObject 5 }


--
--unisMultUserOnlineInfoTable
--

unisMultUserOnlineInfoTable OBJECT-TYPE
    SYNTAX      SEQUENCE OF UnisMultUserOnlineInfoEntry
    MAX-ACCESS  not-accessible
    STATUS      current
    DESCRIPTION
        "Multicast user online information table."
    ::= { unisMultCDR 2 }

unisMultUserOnlineInfoEntry OBJECT-TYPE
    SYNTAX      UnisMultUserOnlineInfoEntry
    MAX-ACCESS  not-accessible
    STATUS      current
    DESCRIPTION
        "The entry of multicast user online information table."
    INDEX
        {
            ifIndex,
            unisMultUserRecordID
        }
    ::= { unisMultUserOnlineInfoTable 1 }

UnisMultUserOnlineInfoEntry ::= SEQUENCE
    {
        unisMultUserRecordID         Unsigned32,
        unisMultUserSubIfIndex       Unsigned32,
        unisMultUserVlanID           VlanId,
        unisMultUserJoinGAddrType    InetAddressType,
        unisMultUserJoinGAddr        InetAddress,
        unisMultUserJoinSAddrType    InetAddressType,
        unisMultUserJoinSAddr        InetAddress,
        unisMultUserStatus           INTEGER,
        unisMultUserJoinTime         DateAndTime,
        unisMultUserPreviewTimes     Unsigned32,
        unisMultUserPreviewRemain    Unsigned32
    }

unisMultUserRecordID OBJECT-TYPE
    SYNTAX      Unsigned32
    MAX-ACCESS  not-accessible
    STATUS      current
    DESCRIPTION
        "The index of online record."
    ::= { unisMultUserOnlineInfoEntry 1 }

unisMultUserSubIfIndex OBJECT-TYPE
    SYNTAX      Unsigned32
    MAX-ACCESS  read-only
    STATUS      current
    DESCRIPTION
        "The index of sub-interface which is active.
        If the value is zero, unisMultUserSubIfIndex should be ignored."
    ::= { unisMultUserOnlineInfoEntry 2 }

unisMultUserVlanID OBJECT-TYPE
    SYNTAX      VlanId
    MAX-ACCESS  read-only
    STATUS      current
    DESCRIPTION
        "The ID of VLAN in which the user joined the multicast group."
    ::= { unisMultUserOnlineInfoEntry 3 }

unisMultUserJoinGAddrType OBJECT-TYPE
    SYNTAX      InetAddressType
    MAX-ACCESS  read-only
    STATUS      current
    DESCRIPTION
        "Type of the multicast group IP address."
    ::= { unisMultUserOnlineInfoEntry 4 }

unisMultUserJoinGAddr OBJECT-TYPE
    SYNTAX      InetAddress
    MAX-ACCESS  read-only
    STATUS      current
    DESCRIPTION
        "The multicast group address which the user joined."
    ::= { unisMultUserOnlineInfoEntry 5 }

unisMultUserJoinSAddrType OBJECT-TYPE
    SYNTAX      InetAddressType
    MAX-ACCESS  read-only
    STATUS      current
    DESCRIPTION
        "Type of the multicast source IP address."
    ::= { unisMultUserOnlineInfoEntry 6 }

unisMultUserJoinSAddr OBJECT-TYPE
    SYNTAX      InetAddress
    MAX-ACCESS  read-only
    STATUS      current
    DESCRIPTION
        "The multicast source address which the user joined.
        If the value is '0.0.0.0'(IPv4) or '::'(IPv6), unisMultUserJoinSAddr
        should be ignored."
    ::= { unisMultUserOnlineInfoEntry 7 }

unisMultUserStatus OBJECT-TYPE
    SYNTAX      INTEGER
        {
            permit(1),
            preview(2)
        }
    MAX-ACCESS  read-only
    STATUS      current
    DESCRIPTION
        "The current status of user.
        permit - user in permit status.
        preview - user in preview status."
    ::= { unisMultUserOnlineInfoEntry 8 }

unisMultUserJoinTime OBJECT-TYPE
    SYNTAX      DateAndTime
    MAX-ACCESS  read-only
    STATUS      current
    DESCRIPTION
        "The time when the user joined the multicast group."
    ::= { unisMultUserOnlineInfoEntry 9 }

unisMultUserPreviewTimes OBJECT-TYPE
    SYNTAX      Unsigned32
    MAX-ACCESS  read-only
    STATUS      current
    DESCRIPTION
        "The times of multicast preview which the user joined.
        If unisMultUserStatus is not preview, unisMultUserPreviewTimes
        should be ignored."
    ::= { unisMultUserOnlineInfoEntry 10 }

unisMultUserPreviewRemain OBJECT-TYPE
    SYNTAX      Unsigned32
    MAX-ACCESS  read-only
    STATUS      current
    DESCRIPTION
        "The remanent time slice of multicast preview which the user joined.
        If unisMultUserStatus is not preview, unisMultUserPreviewRemain
        should be ignored."
    ::= { unisMultUserOnlineInfoEntry 11 }

END
