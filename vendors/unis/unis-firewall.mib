-- =========================================================================
-- Copyright (c) 2020 Unisyue Technologies Co., Ltd.  All rights reserved.
--
-- Description: The MIB is designed to get Firewall' statistic information.
-- Reference:
-- Version: V1.1
-- History:
--  V1.0 2008-01-17 created by ZhangBo 05309
--       Initial version.
--  V1.1 2012/12/01 Modified by y05947
--       Add unisFWConnRate node.
-- =========================================================================
UNIS-FIREWALL-MIB DEFINITIONS ::= BEGIN

IMPORTS
        unisCommon
    FROM UNIS-OID-MIB
        Unsigned32, Gauge32, OBJECT-TYPE, MODULE-IDENTITY
    FROM SNMPv2-SMI;


unisFireWall MODULE-IDENTITY
    LAST-UPDATED "200801171450Z"
    ORGANIZATION
        "Unisyue Technologies Co., Ltd."
    CONTACT-INFO
        ""
    DESCRIPTION
        "The MIB is designed to manage Firewall products."
    ::= { unisCommon 88 }


--
-- Node definitions
--

unisFirewallobject OBJECT IDENTIFIER ::= { unisFireWall 1 }

unisFirewallSpecs OBJECT IDENTIFIER ::= { unisFirewallobject 1 }

unisFWMaxConnNum OBJECT-TYPE
    SYNTAX      Unsigned32
    MAX-ACCESS  read-only
    STATUS      current
    DESCRIPTION
        "Max connection number of system."
    ::= { unisFirewallSpecs 1 }

unisFirewallGlobalStats OBJECT IDENTIFIER ::= { unisFirewallobject 2 }

unisFWConnNumCurr OBJECT-TYPE
    SYNTAX      Gauge32
    MAX-ACCESS  read-only
    STATUS      current
    DESCRIPTION
        "The number of connections that currently exist."
    ::= { unisFirewallGlobalStats 1 }

unisFWConnRate OBJECT-TYPE
    SYNTAX Gauge32
    MAX-ACCESS read-only
    STATUS current
    DESCRIPTION
        "Connection establishment rate."
    ::= { unisFirewallGlobalStats 2 }

END
