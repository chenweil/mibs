-- =================================================================
-- Copyright (c) 2020 Unisyue Technologies Co., Ltd.  All rights reserved.
--
-- Description: Smart Link MIB
-- Reference:
-- Version: V1.0
-- History:
--   2014-07-23 created by Lei Gongwu
--     Initial version V1.0
-- =================================================================
-- =================================================================
--
-- Import and definition
--
-- =================================================================
UNIS-SMLK-MIB DEFINITIONS ::= BEGIN

IMPORTS
    unisCommon
        FROM UNIS-OID-MIB
    RowStatus, DateAndTime, MacAddress
        FROM SNMPv2-TC
    Integer32, Counter64, OBJECT-TYPE, MODULE-IDENTITY, NOTIFICATION-TYPE
        FROM SNMPv2-SMI
    InterfaceIndex
        FROM IF-MIB;

unisSmlk MODULE-IDENTITY
    LAST-UPDATED
        "201407231503Z"
    ORGANIZATION
        "Unisyue Technologies Co., Ltd."
    CONTACT-INFO
        ""
    DESCRIPTION
        "This MIB defines objects for managing Smart Link.
        Smart Link is a feature developed to address the slow convergence
        issue with STP.
        It provides link redundancy and fast convergence in
        a dual uplink network, allowing the backup link to take over quickly
        when the primary link fails."
    REVISION
        "201407231503Z"
    DESCRIPTION
        "Initial revision of the Smart Link MIB module."
    ::= { unisCommon  147 }

unisSmlkObject OBJECT IDENTIFIER ::= { unisSmlk 1 }

unisSmlkGroupTable OBJECT-TYPE
    SYNTAX      SEQUENCE OF UnisSmlkGroupEntry
    MAX-ACCESS  not-accessible
    STATUS      current
    DESCRIPTION
        "A list of entries of a smart link group."
    ::= { unisSmlkObject 1 }

unisSmlkGroupEntry OBJECT-TYPE
    SYNTAX      UnisSmlkGroupEntry
    MAX-ACCESS  not-accessible
    STATUS      current
    DESCRIPTION
        "A list of parameters that describe a smart link group."
    INDEX
    {
        unisSmlkGroupID
    }
  ::= { unisSmlkGroupTable 1 }

UnisSmlkGroupEntry ::=
    SEQUENCE
    {
        unisSmlkGroupID           Integer32,
        unisSmlkDeviceID          MacAddress,
        unisSmlkPreemptionMode    INTEGER,
        unisSmlkSpeedThreshold    Integer32,
        unisSmlkPreemptionDelay   Integer32,
        unisSmlkControlVlanID     Integer32,
        unisSmlkInstanceListLow   OCTET STRING,
        unisSmlkInstanceListHigh  OCTET STRING,
        unisSmlkGroupRowStatus    RowStatus
    }

unisSmlkGroupID OBJECT-TYPE
    SYNTAX Integer32 (1..256)
    MAX-ACCESS  accessible-for-notify
    STATUS      current
    DESCRIPTION
        "An index that uniquely identifies an entry in the smart link
        group table."
    ::={ unisSmlkGroupEntry 1 }

unisSmlkDeviceID OBJECT-TYPE
    SYNTAX      MacAddress
    MAX-ACCESS  read-only
    STATUS      current
    DESCRIPTION
        "Device ID of a smart link group.
        The device ID is the bridge MAC of the device."
    ::={ unisSmlkGroupEntry 2 }

unisSmlkPreemptionMode OBJECT-TYPE
    SYNTAX      INTEGER
                {
                    none(1),
                    role(2),
                    speed(3)
                }
    MAX-ACCESS  read-create
    STATUS      current
    DESCRIPTION
        "Preemption mode of a smart link group."
    DEFVAL      { 1 }
    ::={ unisSmlkGroupEntry 3 }

unisSmlkSpeedThreshold OBJECT-TYPE
    SYNTAX      Integer32 (0..10000)
    MAX-ACCESS  read-create
    STATUS      current
    DESCRIPTION
        "Speed threshold for a smart link group in speed mode.
        This object is valid only when the value of unisSmlkPreemptionMode
        is 'speed'."
    DEFVAL      { 0 }
    ::={ unisSmlkGroupEntry 4 }

unisSmlkPreemptionDelay OBJECT-TYPE
    SYNTAX      Integer32 (0..300)
    MAX-ACCESS  read-create
    STATUS      current
    DESCRIPTION
        "Preemption delay for a smart link group, in the range of 0 to 300
        seconds."
    DEFVAL      { 1 }
    ::={ unisSmlkGroupEntry 5 }

unisSmlkControlVlanID OBJECT-TYPE
    SYNTAX      Integer32 (1..4094|65535)
    MAX-ACCESS  read-create
    STATUS      current
    DESCRIPTION
        "Index of the control VLAN specified for a smart link group.
        The value 65535 indicates that the control VLAN has not been
        configured."
    DEFVAL      { 1 }
    ::={ unisSmlkGroupEntry 6 }

unisSmlkInstanceListLow OBJECT-TYPE
    SYNTAX      OCTET STRING(SIZE(256))
    MAX-ACCESS  read-create
    STATUS      current
    DESCRIPTION
        "Each octet contained in this value specifies an eight-instance
        group, with the first octet specifying instances 0 through 7,
        the second octet specifying instances 8 through 15, and so on.
        Within each octet, the most significant bit represents the
        highest numbered instance, and the least significant bit represents
        the lowest numbered instance.  Each instance to which the
        protected VLANs of a smart link group are mapped corresponds to a
        bit within the value of this object.  A bit with a value of '1'
        indicates that the VLANs mapped to the instance are protected
        VLANs of the smart link group.  The VLANs mapped to
        the instance are not protected VLANs if the corresponding bit has a
        value of '0'.  The value of this object must be set with
        unisSmlkInstanceListHigh at the same time when a SET
        operation is performed."
    DEFVAL      { "" }
    ::= { unisSmlkGroupEntry 7 }

unisSmlkInstanceListHigh OBJECT-TYPE
    SYNTAX      OCTET STRING(SIZE(256))
    MAX-ACCESS  read-create
    STATUS      current
    DESCRIPTION
        "Each octet contained in this value specifies an eight-instance
        group, with the first octet specifying instances 2048 through
        2055, the second octet specifying instances 2056 through 2063,
        and so on.  Within each octet, the most significant bit represents
        the highest numbered instance, and the least significant bit
        represents the lowest numbered instance.  The most significant bit
        of the last octet is invalid.  Each instance to which the
        protected VLANs of a smart link group are mapped corresponds to a
        bit within the value of this object.  A bit with a value of '1'
        indicates that the VLANs mapped to the instance are protected VLANs
        of the smart link group.  The VLANs mapped to the
        instance are not protected VLANs if the corresponding bit has a
        value of '0'.  The value of this object must be set with
        unisSmlkInstanceListLow at the same time when a SET operation
        is performed."
    DEFVAL      { "" }
    ::= { unisSmlkGroupEntry 8 }

unisSmlkGroupRowStatus OBJECT-TYPE
    SYNTAX      RowStatus
    MAX-ACCESS  read-create
    STATUS      current
    DESCRIPTION
        "This object is responsible for managing creation,
        deletion, and modification of rows.  The rows support active
        status, CreatAndGo, and destroy operations."
    ::={ unisSmlkGroupEntry 9 }

unisSmlkPortTable OBJECT-TYPE
    SYNTAX      SEQUENCE OF UnisSmlkPortEntry
    MAX-ACCESS  not-accessible
    STATUS      current
    DESCRIPTION
        "A list of port entries of a smart link group."
    ::= { unisSmlkObject 2 }

unisSmlkPortEntry OBJECT-TYPE
    SYNTAX      UnisSmlkPortEntry
    MAX-ACCESS  not-accessible
    STATUS      current
    DESCRIPTION
        "A list of parameters that describe a port to be added to a smart
        link group."
    INDEX
    {
        unisSmlkGroupID,
        unisSmlkPortIfIndex
    }
    ::= { unisSmlkPortTable 1 }

UnisSmlkPortEntry ::=
    SEQUENCE
    {
        unisSmlkPortIfIndex      InterfaceIndex,
        unisSmlkPortRole         INTEGER,
        unisSmlkPortStatus       INTEGER,
        unisSmlkFlushCount       Counter64,
        unisSmlkLastFlushTime    DateAndTime,
        unisSmlkPortRowStatus    RowStatus
    }

unisSmlkPortIfIndex OBJECT-TYPE
    SYNTAX      InterfaceIndex
    MAX-ACCESS  accessible-for-notify
    STATUS      current
    DESCRIPTION
        "IfIndex of a port in a smart link group."
    ::={ unisSmlkPortEntry 1 }

unisSmlkPortRole OBJECT-TYPE
    SYNTAX      INTEGER
                {
                    primary(1),
                    secondary(2)
                }
    MAX-ACCESS  read-create
    STATUS      current
    DESCRIPTION
        "Role of a port in a smart link group."
    ::={ unisSmlkPortEntry 2 }

unisSmlkPortStatus OBJECT-TYPE
    SYNTAX      INTEGER
                {
                    down(1),
                    active(2),
                    standby(3)
                }
    MAX-ACCESS  read-only
    STATUS      current
    DESCRIPTION
        "Status of a port in a smart link group."
    ::={ unisSmlkPortEntry 3 }

unisSmlkFlushCount OBJECT-TYPE
    SYNTAX      Counter64
    MAX-ACCESS  read-only
    STATUS      current
    DESCRIPTION
        "Number of transmitted flush messages."
    ::={ unisSmlkPortEntry 4 }

unisSmlkLastFlushTime OBJECT-TYPE
    SYNTAX      DateAndTime
    MAX-ACCESS  read-only
    STATUS      current
    DESCRIPTION
        "Time when the last flush message was transmitted."
    ::= { unisSmlkPortEntry 5 }

unisSmlkPortRowStatus OBJECT-TYPE
    SYNTAX      RowStatus
    MAX-ACCESS  read-create
    STATUS      current
    DESCRIPTION
        "This object is responsible for managing creation,
        deletion, and modification of rows.  The rows support active
        status, CreatAndGo, and destroy operations."
    ::={ unisSmlkPortEntry 6 }

unisSmlkFlushEnableTable OBJECT-TYPE
    SYNTAX      SEQUENCE OF UnisSmlkFlushEnableEntry
    MAX-ACCESS  not-accessible
    STATUS      current
    DESCRIPTION
        "A list of ports on which flush message receiving is enabled."
    ::= { unisSmlkObject 3 }

unisSmlkFlushEnableEntry OBJECT-TYPE
    SYNTAX      UnisSmlkFlushEnableEntry
    MAX-ACCESS  not-accessible
    STATUS      current
    DESCRIPTION
        "A list of parameters that describe a port on which flush message
        receiving is enabled."
    INDEX
    {
          unisSmlkIfIndex
    }
    ::= { unisSmlkFlushEnableTable 1 }

UnisSmlkFlushEnableEntry ::=
    SEQUENCE
    {
        unisSmlkIfIndex               InterfaceIndex,
        unisSmlkControlVlanListLow    OCTET STRING,
        unisSmlkControlVlanListHigh   OCTET STRING
    }

unisSmlkIfIndex OBJECT-TYPE
    SYNTAX      InterfaceIndex
    MAX-ACCESS  not-accessible
    STATUS      current
    DESCRIPTION
        "IfIndex of a port on which flush message receiving is enabled."
    ::={ unisSmlkFlushEnableEntry 1 }

unisSmlkControlVlanListLow OBJECT-TYPE
    SYNTAX      OCTET STRING(SIZE(256))
    MAX-ACCESS  read-write
    STATUS      current
    DESCRIPTION
        "Specifies the control VLANs used for receiving flush messages.
        The VLAN ID range, described by bitmap, is from 1 to
        2048.  The length of bitmap is 256 in bytes.  Each octet
        within this value specifies a set of eight VLANs, with
        the first octet specifying VLANs 1 through 8, the second
        octet specifying VLANs 9 through 16, and so on.  Within each
        octet, the most significant bit represents the highest
        numbered VLAN, and the least significant bit represents
        the lowest numbered VLAN."
    ::= { unisSmlkFlushEnableEntry 2 }

unisSmlkControlVlanListHigh OBJECT-TYPE
    SYNTAX      OCTET STRING(SIZE(256))
    MAX-ACCESS  read-write
    STATUS      current
    DESCRIPTION
        "Specifies the control VLANs used for receiving flush messages.
        The VLAN ID range, described by bitmap, is from 2049 to
        4094.  The length of bitmap is 256 in bytes.  Each octet
        within this value specifies a set of eight VLANs, with
        the first octet specifying VLANs 2049 through 2056, the
        second octet specifying VLANs 2057 through 2064, and so on.
        Within each octet, the most significant bit represents
        the highest numbered VLAN, and the least significant bit
        represents the lowest numbered VLAN."
    ::= { unisSmlkFlushEnableEntry 3 }

unisSmlkTrap            OBJECT IDENTIFIER ::= { unisSmlk 2 }
unisSmlkTrapPrefix      OBJECT IDENTIFIER ::= { unisSmlkTrap 0 }
unisSmlkGroupLinkActive NOTIFICATION-TYPE
    OBJECTS
        {
            unisSmlkGroupID,
            unisSmlkPortIfIndex
        }
    STATUS      current
    DESCRIPTION
        "A trap message is generated when the status of a port
        in a smart link group changes to active."
    ::= { unisSmlkTrapPrefix 1 }

END
