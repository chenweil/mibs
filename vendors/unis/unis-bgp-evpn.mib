-- =============================================================================
-- Copyright (c) 2020 Unisyue Technologies Co., Ltd.  All rights reserved.
--
-- Description: This MIB module contains managed object definitions for
--              Border Gateway Protocol (BGP) Ethernet Virtual Private Network (EVPN).
-- Reference:
-- Version: V1.1
-- History:
--   V1.0 2017-11-20 Initial version Created by AnXiaoFeng
--   V1.1 2018-07-07 Update unisBgpEvpnNbrPrefixTable by shanyangyang
-- =============================================================================
UNIS-BGP-EVPN-MIB DEFINITIONS ::= BEGIN
IMPORTS
    MODULE-IDENTITY, OBJECT-TYPE,
    Integer32, Unsigned32, IpAddress
        FROM SNMPv2-SMI
    TruthValue
        FROM SNMPv2-TC
    unisCommon
        FROM UNIS-OID-MIB;

-- =============================================================================
-- module identity part
-- =============================================================================
unisBgpEvpn MODULE-IDENTITY
    LAST-UPDATED "201807071430Z"
    ORGANIZATION
        "Unisyue Technologies Co., Ltd."
    CONTACT-INFO
        ""
    DESCRIPTION
        "This MIB contains managed object definitions for the
         Border Gateway Protocol (BGP) Ethernet Virtual Private
         Network (EVPN) as defined in : ."
    REVISION
        "201807071430Z"
    DESCRIPTION
        "Change the objects of unisBgpEvpnNbrPrefixTable." 
    REVISION
        "201711291431Z"
    DESCRIPTION
        "modified according to review suggestions."
    REVISION
        "201711041431Z"
    DESCRIPTION
        "Initial version of this MIB."
    ::= { unisCommon 172 }

-- =============================================================================
-- object definition begin
-- =============================================================================
unisBgpEvpnObjects OBJECT IDENTIFIER ::= { unisBgpEvpn 1 }
unisBgpEvpnConf    OBJECT IDENTIFIER ::= { unisBgpEvpnObjects 1 }

-- =============================================================================
-- unisBgpEvpnNbrAddrTable Definition
-- =============================================================================
unisBgpEvpnNbrAddrTable OBJECT-TYPE
    SYNTAX      SEQUENCE OF UnisBgpEvpnNbrAddrEntry
    MAX-ACCESS  not-accessible
    STATUS      current
    DESCRIPTION
        "This table specifies per-interface BGP EVPN neighbor
         addresses for both PEs and CEs."
    ::= { unisBgpEvpnConf 1 }

unisBgpEvpnNbrAddrEntry OBJECT-TYPE
    SYNTAX      UnisBgpEvpnNbrAddrEntry
    MAX-ACCESS  not-accessible
    STATUS      current
    DESCRIPTION
        "An entry in this table is created by an LSR for
         every VRF capable of supporting BGP EVPN.  The
         indexing provides an ordering of BGP prefixes
         per VRF."
    INDEX {
            unisBgpEvpnNbrAddr
          }
    ::= { unisBgpEvpnNbrAddrTable 1 }

UnisBgpEvpnNbrAddrEntry ::= SEQUENCE {
    unisBgpEvpnNbrAddr         IpAddress,
    unisBgpEvpnNbrAsNumber     Unsigned32
}

unisBgpEvpnNbrAddr OBJECT-TYPE
    SYNTAX      IpAddress
    MAX-ACCESS  not-accessible
    STATUS      current
    DESCRIPTION
        "Denotes the BGP neighbor address."
    ::= { unisBgpEvpnNbrAddrEntry 1 }

unisBgpEvpnNbrAsNumber OBJECT-TYPE
    SYNTAX      Unsigned32
    MAX-ACCESS  read-only
    STATUS      current
    DESCRIPTION
        "The Autonomous System that the BGP's neighbor in."
    ::= { unisBgpEvpnNbrAddrEntry 2 }

-- =============================================================================
-- End of unisBgpEvpnNbrAddrTable Definition
-- =============================================================================

-- =============================================================================
-- unisBgpEvpnNbrPrefixTable Definition
-- =============================================================================
unisBgpEvpnNbrPrefixTable OBJECT-TYPE
    SYNTAX      SEQUENCE OF UnisBgpEvpnNbrPrefixEntry
    MAX-ACCESS  not-accessible
    STATUS      current
    DESCRIPTION
        "This table specifies per-VRF vpnv4 multi-protocol
         prefixes supported by BGP EVPN"
    ::= { unisBgpEvpnConf 2 }

unisBgpEvpnNbrPrefixEntry OBJECT-TYPE
    SYNTAX      UnisBgpEvpnNbrPrefixEntry
    MAX-ACCESS  not-accessible
    STATUS      current
    DESCRIPTION
        "An entry in this table is created by an LSR for
         every BGP prefix associated with a VRF supporting a
         BGP EVPN.  The indexing provides an ordering of
         BGP prefixes per VRF."
    INDEX {
            unisBgpEvpnPAtrRD,
            unisBgpEvpnPAtrAddrPrefix,
            unisBgpEvpnPAtrAddrPrefixLen,
            unisBgpEvpnPAtrPeer
          }
    ::= { unisBgpEvpnNbrPrefixTable 1 }

UnisBgpEvpnNbrPrefixEntry ::= SEQUENCE {
    unisBgpEvpnPAtrRD              OCTET STRING,
    unisBgpEvpnPAtrAddrPrefix      OCTET STRING,
    unisBgpEvpnPAtrAddrPrefixLen   Integer32,
    unisBgpEvpnPAtrPeer            IpAddress,
    unisBgpEvpnPAtrRouteType       Unsigned32,
    unisBgpEvpnPAtrOrigin          INTEGER,
    unisBgpEvpnPAtrASPathSegment   OCTET STRING,
    unisBgpEvpnPAtrNextHop         IpAddress,
    unisBgpEvpnPAtrMultiExitDisc   Integer32,
    unisBgpEvpnPAtrLocalPref       Integer32,
    unisBgpEvpnPAtrIGMPFlags       INTEGER,
    unisBgpEvpnPAtrMaxRespTime     Unsigned32,
    unisBgpEvpnPAtrPMSITunnel      OCTET STRING,
    unisBgpEvpnPAtrL2VNI           Unsigned32,
    unisBgpEvpnPAtrL3VNI           Unsigned32,
    unisBgpEvpnPAtrBest            TruthValue,
    unisBgpEvpnPAtrUnknown         OCTET STRING
}

unisBgpEvpnPAtrRD OBJECT-TYPE
    SYNTAX      OCTET STRING (SIZE (3..21))
    MAX-ACCESS  not-accessible
    STATUS      current
    DESCRIPTION
        "The route distinguisher."
    ::= { unisBgpEvpnNbrPrefixEntry 1 }

unisBgpEvpnPAtrAddrPrefix OBJECT-TYPE
    SYNTAX      OCTET STRING (SIZE (1..86))
    MAX-ACCESS  not-accessible
    STATUS      current
    DESCRIPTION
        "The EVPN information in the Network Layer
        Reachability Information field. BGP EVPN
        prefix includes:
        [1][ESI][EthernetTagID]:
           ESI: each Ethernet segment(ES) is identified
           by a unique non-zero identifier called an
           Ethernet Segment Identifier.
           EthernetTagID: This attribute identifies a
           particular broadcast domain in an EVPN instance.
        [2][EthernetTagID][MACLength][MAC][IPAddressLength][IPAddress]
        [3][EthernetTagID][IPAddressLength][IPAddress]
        [4][ESI][IPAddressLength][IPAddress]
        [5][EthernetTagID][IPAddressLength][IPAddress]
        [6][EthernetTagID][MulticastSourceLength]
           [MulticastSourceAddress][MulticastGroupLength]
           [MulticastGroupAddress][OriginatorRouterLength]
           [OriginatorRouterAddress]
        [7][ESI][EthernetTagID][MulticastSourceLength]
           [MulticastSourceAddress][MulticastGroupLength]
           [MulticastGroupAddress][OriginatorRouterLength]
           [OriginatorRouterAddress][LeaveGroupSyn]
           LeaveGroupSyn: This attribute identifies the
           specific (x, G) leave group synchronization
           procedure initiated by the advertising PE,
           which increments the value whenever it
           initiates a procedure.
        [8][ESI][EthernetTagID][MulticastSourceLength]
           [MulticastSourceAddress][MulticastGroupLength]
           [MulticastGroupAddress][OriginatorRouterLength]
           [OriginatorRouterAddress][LeaveGroupSyn]"
    ::= { unisBgpEvpnNbrPrefixEntry 2 }

unisBgpEvpnPAtrAddrPrefixLen OBJECT-TYPE
    SYNTAX      Integer32  (0..300)
    MAX-ACCESS  not-accessible
    STATUS      current
    DESCRIPTION
       "Length in bits of the Network
        Layer Reachability Information field."
    ::= { unisBgpEvpnNbrPrefixEntry 3 }

unisBgpEvpnPAtrPeer OBJECT-TYPE
    SYNTAX      IpAddress
    MAX-ACCESS  not-accessible
    STATUS      current
    DESCRIPTION
        "The IP address of the peer where the path
         information was learned."
    ::= { unisBgpEvpnNbrPrefixEntry 4 }

unisBgpEvpnPAtrRouteType OBJECT-TYPE
    SYNTAX      Unsigned32
    MAX-ACCESS  read-only
    STATUS      current
    DESCRIPTION
        "Defines the following Route Types:
         1 - Ethernet Auto-Discovery (A-D) route
         2 - MAC/IP Advertisement route
         3 - Inclusive Multicast Ethernet Tag route
         4 - Ethernet Segment route
         5 - IP Prefix Route
         6 - Selective Multicast Ethernet Tag Route
         7 - IGMP Join Synch Route
         8 - IGMP Leave Synch Route"
    ::= { unisBgpEvpnNbrPrefixEntry 5 }

unisBgpEvpnPAtrOrigin OBJECT-TYPE
    SYNTAX      INTEGER { igp(1),-- networks are interior
                          egp(2),-- networks learned via EGP
                          incomplete(3) -- undetermined
                        }
    MAX-ACCESS  read-only
    STATUS      current
    DESCRIPTION
        "The ultimate origin of the path
         information."
    ::= { unisBgpEvpnNbrPrefixEntry 6 }

unisBgpEvpnPAtrASPathSegment OBJECT-TYPE
    SYNTAX      OCTET STRING (SIZE (2..255))
    MAX-ACCESS  read-only
    STATUS      current
    DESCRIPTION
        "The sequence of AS path segments.  Each AS
         path segment is represented by a triple
         <type, length, value>.

          The type is a 1-octet field which has two
          possible values:
              1      AS_SET: unordered set of ASs a
                     route in the UPDATE
                     message has traversed
              2      AS_SEQUENCE: ordered set of ASs
                     a route in the UPDATE
                     message has traversed.
                     The length is a 1-octet field containing the
                     number of ASs in the value field.

                     The value field contains one or more AS
                     numbers, each AS is represented in the octet
                     string as a pair of octets according to the
                     following algorithm:
                     first-byte-of-pair = ASNumber / 256;
                     second-byte-of-pair = ASNumber & 255;"
    ::= { unisBgpEvpnNbrPrefixEntry 7 }

unisBgpEvpnPAtrNextHop OBJECT-TYPE
    SYNTAX      IpAddress
    MAX-ACCESS  read-only
    STATUS      current
    DESCRIPTION
        "The address of the router that should be
         used for the destination network.  This address is
         the NEXT_HOP address received in the UPDATE packet."
    ::= { unisBgpEvpnNbrPrefixEntry 8 }

unisBgpEvpnPAtrMultiExitDisc OBJECT-TYPE
    SYNTAX      Integer32 (-1..2147483647)
    MAX-ACCESS  read-only
    STATUS      current
    DESCRIPTION
        "The MED attribute received in the UPDATE packet.
         When the actual value is range from 2147483647 to
         4294967295,the return value will be 2147483647."
    ::= { unisBgpEvpnNbrPrefixEntry 9 }

unisBgpEvpnPAtrLocalPref OBJECT-TYPE
    SYNTAX      Integer32 (-1..2147483647)
    MAX-ACCESS  read-only
    STATUS      current
    DESCRIPTION
        "The local preference attribute received in the UPDATE packet.
         When the actual value is range from 2147483647 to 4294967295,
         the return value will be 2147483647."
    ::= { unisBgpEvpnNbrPrefixEntry 10 }

unisBgpEvpnPAtrIGMPFlags OBJECT-TYPE
    SYNTAX      INTEGER { igmpv1(1),
                          igmpv2(2),
                          igmpv3(3)
                        }
    MAX-ACCESS  read-only
    STATUS      current
    DESCRIPTION
        "This attribute indicates support for IGMP version."
    ::= { unisBgpEvpnNbrPrefixEntry 11 }

unisBgpEvpnPAtrMaxRespTime OBJECT-TYPE
    SYNTAX      Unsigned32
    UNITS       "ms"
    MAX-ACCESS  read-only
    STATUS      current
    DESCRIPTION
        "The Maximum Response Time is the duration of (x, G)
         leave group synchronization procedure."
    ::= { unisBgpEvpnNbrPrefixEntry 12 }

unisBgpEvpnPAtrPMSITunnel OBJECT-TYPE
    SYNTAX      OCTET STRING (SIZE (9..21))
    MAX-ACCESS  read-only
    STATUS      current
    DESCRIPTION
        "This attribute identifies the
         P-tunnel used for sending broadcast."
    ::= { unisBgpEvpnNbrPrefixEntry 13 }

unisBgpEvpnPAtrL2VNI OBJECT-TYPE
    SYNTAX      Unsigned32
    MAX-ACCESS  read-only
    STATUS      current
    DESCRIPTION
         "L2 VXLAN ID."
    ::= { unisBgpEvpnNbrPrefixEntry 14 }

unisBgpEvpnPAtrL3VNI OBJECT-TYPE
    SYNTAX      Unsigned32
    MAX-ACCESS  read-only
    STATUS      current
    DESCRIPTION
         "L3 VXLAN ID."
    ::= { unisBgpEvpnNbrPrefixEntry 15 }

unisBgpEvpnPAtrBest OBJECT-TYPE
    SYNTAX      TruthValue
    MAX-ACCESS  read-only
    STATUS      current
    DESCRIPTION
        "An indication of whether this route
         was chosen as the best BGP4 route for
         this destination."
    ::= { unisBgpEvpnNbrPrefixEntry 16 }

unisBgpEvpnPAtrUnknown OBJECT-TYPE
    SYNTAX      OCTET STRING (SIZE(0..255))
    MAX-ACCESS  read-only
    STATUS      current
    DESCRIPTION
        "One or more path attributes not
         understood by this BGP4 speaker."
    ::= { unisBgpEvpnNbrPrefixEntry 17 }

-- =============================================================================
-- End of unisBgpEvpnNbrPrefixTable Definition
-- =============================================================================
-- End of UNIS-BGP-EVPN-MIB
END
