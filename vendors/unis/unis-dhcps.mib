-- =========================================================================
-- Copyright (c) 2020 Unisyue Technologies Co., Ltd.  All rights reserved.
--
-- Description:  DHCP Server MIB
-- Reference:  Enterprise MIB
-- Version:V1.52
-- History:
--     initial version 2003-03-06
--     V1.0 6th Mar 2004
--  V1.1 Modified by chenhua 2004-08-13
--   Add 0 to the vlaue list of unisDHCPSIPResetFlag for get-opporation
--  V1.2 Modified by chenhua 2004-09-16
--   Modify  the default value of unisDHCPSWriteDataDelay  to 300
--  V1.3 2004-10-12 updated by gaolong
--   Import TEXTUAL-CONVENTION
--  v1.4 Modified by xinhaing 2004-03-03
--   Add a new table  : unisDHCPSIPInUseExTable
--   The satus of the table unisDHCPSIPInUseTable is modified to be deprecated
--   Correct some spelling errors in unisDHCPSIPInUseTable's description
--   Adjust file format
-- v1.5 2006-02-22 Modified by xuyufei
--   Modify the default value of unisDHCPSDetectingServerStatus to disabled
--   Modify the default value of unisDHCPSGlobalPoolClientNetbiosType
--   and unisDHCPSInterfacePoolClientNetbiosType to 0
--   Correct the description of unisDHCPSGlobalPoolOptionHexString,
--   unisDHCPSInterfacePoolOptionHexString, unisDHCPSGlobalPoolNumber,
--   unisDHCPSInterfacePoolNumber
-- v1.51 2006-04-13
--   change value range of unisDHCPSIPInUsePoolName and unisDHCPSIPInUsePoolNameEx
-- v1.52 2011-01-19 Modified by ganchanghua
--   change SYNTAX of unisDHCPSConflictIPDetectTime to OCTET STRING(SIZE(1..20))
-- =========================================================================
UNIS-DHCPS-MIB DEFINITIONS ::= BEGIN
    IMPORTS
        unisRhw
            FROM UNIS-OID-MIB
        ifIndex
            FROM RFC1213-MIB
        OBJECT-GROUP
            FROM SNMPv2-CONF
        IpAddress, Integer32, OBJECT-TYPE, MODULE-IDENTITY
            FROM SNMPv2-SMI
        RowStatus, MacAddress, TEXTUAL-CONVENTION
            FROM SNMPv2-TC;

    unisDHCPServerMib MODULE-IDENTITY
        LAST-UPDATED "200602200000Z"        -- February 20, 2006 at 00:00 GMT
        ORGANIZATION
            "Unisyue Technologies Co., Ltd."
        CONTACT-INFO
            ""
        DESCRIPTION
            "This MIB describes objects used for managing DHCP server."
        ::= { unisRhw 2 }
--
-- Textual Conventions
--

    UnisDhcpSEnabledStatus ::= TEXTUAL-CONVENTION
        STATUS      current
        DESCRIPTION
            "To descript the status of some function is Enabled or
            Disabled."
        SYNTAX      INTEGER
            {
                enabled(1),
                disabled(0)
            }

--
-- Node definitions
--

    unisDHCPServerMibObject OBJECT IDENTIFIER ::= { unisDHCPServerMib 1 }

--  Part 1: For DHCP server global pool
--
-- =================================================================
-- 1st Table of unisDHCPServerMibObject: unisDHCPSGlobalPoolTable
-- =================================================================
    unisDHCPSGlobalPoolTable OBJECT-TYPE
        SYNTAX      SEQUENCE OF UnisDHCPSGlobalPoolEntry
        MAX-ACCESS  not-accessible
        STATUS      current
        DESCRIPTION
            "A table for creating DHCP server global pools."
        ::= { unisDHCPServerMibObject 1 }

    unisDHCPSGlobalPoolEntry OBJECT-TYPE
        SYNTAX      UnisDHCPSGlobalPoolEntry
        MAX-ACCESS  not-accessible
        STATUS      current
        DESCRIPTION
            "An entry containing objects for creating or
            deleting a global pool for the DHCP server."
        INDEX { unisDHCPSGlobalPoolName }
        ::= { unisDHCPSGlobalPoolTable 1 }

    UnisDHCPSGlobalPoolEntry ::=
        SEQUENCE
            {
                unisDHCPSGlobalPoolName         OCTET STRING,
                unisDHCPSGlobalPoolRowStatus    RowStatus
            }

    unisDHCPSGlobalPoolName OBJECT-TYPE
        SYNTAX      OCTET STRING(SIZE(0..255))
        MAX-ACCESS  read-only
        STATUS      current
        DESCRIPTION
            "DHCP server global pool name."
        ::= { unisDHCPSGlobalPoolEntry 1 }

    unisDHCPSGlobalPoolRowStatus OBJECT-TYPE
        SYNTAX      RowStatus
        MAX-ACCESS  read-create
        STATUS      current
        DESCRIPTION
            "RowStatus. Three actions are used: active,
            createAndGo, destroy."
        ::= { unisDHCPSGlobalPoolEntry 2 }

--  =================================================================
-- 2nd Table of unisDHCPServerMibObject: unisDHCPSGlobalPoolConfigTable
-- =================================================================
    unisDHCPSGlobalPoolConfigTable OBJECT-TYPE
        SYNTAX      SEQUENCE OF UnisDHCPSGlobalPoolConfigEntry
        MAX-ACCESS  not-accessible
        STATUS      current
        DESCRIPTION
            "A table containing the configurations of dhcp
            server global pools."
        ::= { unisDHCPServerMibObject 2 }

    unisDHCPSGlobalPoolConfigEntry OBJECT-TYPE
        SYNTAX      UnisDHCPSGlobalPoolConfigEntry
        MAX-ACCESS  not-accessible
        STATUS      current
        DESCRIPTION
            "An entry containing the objects for configuring
            the network ip or host ip etc. to global pools for
            DHCP server."
        INDEX { unisDHCPSGlobalPoolName }
        ::= { unisDHCPSGlobalPoolConfigTable 1 }

    UnisDHCPSGlobalPoolConfigEntry ::=
        SEQUENCE
            {
                unisDHCPSGlobalPoolType              INTEGER,
                unisDHCPSGlobalPoolNetwork           IpAddress,
                unisDHCPSGlobalPoolNetworkMask       IpAddress,
                unisDHCPSGlobalPoolHostIPAddr        IpAddress,
                unisDHCPSGlobalPoolHostMask          IpAddress,
                unisDHCPSGlobalPoolHostHAddr         MacAddress,
                unisDHCPSGlobalPoolConfigUndoFlag    INTEGER
            }

    unisDHCPSGlobalPoolType OBJECT-TYPE
        SYNTAX      INTEGER
            {
                null(0),
                host(1),
                network(2)
            }
        MAX-ACCESS  read-write
        STATUS      current
        DESCRIPTION
            "Type of a DHCP global pool. Any operations of
            this object will be bound with the operations
            of unisDHCPSGlobalPoolNetwork, unisDHCPSGlobalPoolHostIPAddr,
            or unisDHCPSGlobalPoolHostHAddr.
            That means any operation of this object alone will
            be regarded as invalid operation."
        ::= { unisDHCPSGlobalPoolConfigEntry 1 }

    unisDHCPSGlobalPoolNetwork OBJECT-TYPE
        SYNTAX      IpAddress
        MAX-ACCESS  read-write
        STATUS      current
        DESCRIPTION
            "Network ip of a DHCP global pool.
            To delete a configured network ip, please set
            unisDHCPSGlobalPoolConfigUndoFlag to 1."
        ::= { unisDHCPSGlobalPoolConfigEntry 2 }

    unisDHCPSGlobalPoolNetworkMask OBJECT-TYPE
        SYNTAX      IpAddress
        MAX-ACCESS  read-write
        STATUS      current
        DESCRIPTION
            "Net mask of a DHCP global pool(network).
            The SET operation to this object ought to be with
            the SET of unisDHCPSGlobalPoolNetwork together, and
            any SET operation alone to this object will be
            regarded as an invalid operation.
            When a network ip of a DHCP global pool was
            deleted, the net mask would also be deleted
            automatically, and no further operation needed."
        ::= { unisDHCPSGlobalPoolConfigEntry 3 }

    unisDHCPSGlobalPoolHostIPAddr OBJECT-TYPE
        SYNTAX      IpAddress
        MAX-ACCESS  read-write
        STATUS      current
        DESCRIPTION
            "Host ip of a DHCP global pool.
            To delete a configured network ip, please set
            unisDHCPSGlobalPoolConfigUndoFlag to 2."
        ::= { unisDHCPSGlobalPoolConfigEntry 4 }

    unisDHCPSGlobalPoolHostMask OBJECT-TYPE
        SYNTAX      IpAddress
        MAX-ACCESS  read-write
        STATUS      current
        DESCRIPTION
            "Net mask of a DHCP global pool(host)
            The SET operation to this object ought to be with
            the SET of unisDHCPSGlobalPoolHostIPAddr together,
            and any SET operation alone to this object will be
            regarded as an invalid operation.
            When a host ip of a DHCP global pool was
            deleted, the net mask would also be deleted
            automatically, and no further operation needed."
        ::= { unisDHCPSGlobalPoolConfigEntry 5 }

    unisDHCPSGlobalPoolHostHAddr OBJECT-TYPE
        SYNTAX      MacAddress
        MAX-ACCESS  read-write
        STATUS      current
        DESCRIPTION
            "Hardware address of a DHCP global pool(host).
            To delete a configured hardware address, please
            set unisDHCPSGlobalPoolConfigUndoFlag to 3."
        ::= { unisDHCPSGlobalPoolConfigEntry 6 }

    unisDHCPSGlobalPoolConfigUndoFlag OBJECT-TYPE
        SYNTAX      INTEGER
            {
                undonetworkip(1),
                undohostip(2),
                undohosthaddr(3)
            }
        MAX-ACCESS  read-write
        STATUS      current
        DESCRIPTION
            "Flag of undo operation for unisDHCPSGlobalPoolConfigTable."
        ::= { unisDHCPSGlobalPoolConfigEntry 7 }

--  =================================================================
-- 3rd Table of unisDHCPServerMibObject: unisDHCPSGlobalPoolParaTable
-- =================================================================
    unisDHCPSGlobalPoolParaTable OBJECT-TYPE
        SYNTAX      SEQUENCE OF UnisDHCPSGlobalPoolParaEntry
        MAX-ACCESS  not-accessible
        STATUS      current
        DESCRIPTION
            "A table for configuring parameters to DHCP global
            pools."
        ::= { unisDHCPServerMibObject 3 }

    unisDHCPSGlobalPoolParaEntry OBJECT-TYPE
        SYNTAX      UnisDHCPSGlobalPoolParaEntry
        MAX-ACCESS  not-accessible
        STATUS      current
        DESCRIPTION
            "An entry containing the objects for the
            configurations of parameters of DHCP global pools."
        INDEX { unisDHCPSGlobalPoolName }
        ::= { unisDHCPSGlobalPoolParaTable 1 }

    UnisDHCPSGlobalPoolParaEntry ::=
        SEQUENCE
            {
                unisDHCPSGlobalPoolLeaseDay                 INTEGER,
                unisDHCPSGlobalPoolLeaseHour                INTEGER,
                unisDHCPSGlobalPoolLeaseMinute              INTEGER,
                unisDHCPSGlobalPoolLeaseUnlimited           INTEGER,
                unisDHCPSGlobalPoolDomainName               OCTET STRING,
                unisDHCPSGlobalPoolClientGatewayIPString    OCTET STRING,
                unisDHCPSGlobalPoolClientGatewayIPUndo      IpAddress,
                unisDHCPSGlobalPoolClientDNSIPString        OCTET STRING,
                unisDHCPSGlobalPoolClientDNSIPUndo          IpAddress,
                unisDHCPSGlobalPoolClientNetbiosType        INTEGER,
                unisDHCPSGlobalPoolClientNbnsIPString       OCTET STRING,
                unisDHCPSGlobalPoolClientNbnsIPUndo         IpAddress,
                unisDHCPSGlobalPoolParaUndoFlag             INTEGER,
                unisDHCPSGlobalPoolIPInUseReset             INTEGER
            }

    unisDHCPSGlobalPoolLeaseDay OBJECT-TYPE
        SYNTAX      INTEGER(0..365)
        MAX-ACCESS  read-write
        STATUS      current
        DESCRIPTION
            "Number of days of the lease."
        DEFVAL { 1 }
        ::= { unisDHCPSGlobalPoolParaEntry 1 }

    unisDHCPSGlobalPoolLeaseHour OBJECT-TYPE
        SYNTAX      INTEGER(0..23)
        MAX-ACCESS  read-write
        STATUS      current
        DESCRIPTION
            "Number of hours of the lease."
        DEFVAL { 0 }
        ::= { unisDHCPSGlobalPoolParaEntry 2 }

    unisDHCPSGlobalPoolLeaseMinute OBJECT-TYPE
        SYNTAX      INTEGER(0..59)
        MAX-ACCESS  read-write
        STATUS      current
        DESCRIPTION
            "Number of minutes of the lease."
        DEFVAL { 0 }
        ::= { unisDHCPSGlobalPoolParaEntry 3 }

    unisDHCPSGlobalPoolLeaseUnlimited OBJECT-TYPE
        SYNTAX      INTEGER
            {
                invalid(0),
                unlimited(1)
            }
        MAX-ACCESS  read-write
        STATUS      current
        DESCRIPTION
            "A flag denoting if the lease of a pool is
            unlimited."
        ::= { unisDHCPSGlobalPoolParaEntry 4 }

    unisDHCPSGlobalPoolDomainName OBJECT-TYPE
        SYNTAX      OCTET STRING(SIZE(0..255))
        MAX-ACCESS  read-write
        STATUS      current
        DESCRIPTION
            "Domain name for DHCP clients."
        ::= { unisDHCPSGlobalPoolParaEntry 5 }

    unisDHCPSGlobalPoolClientGatewayIPString OBJECT-TYPE
        SYNTAX      OCTET STRING(SIZE(0..129))
        MAX-ACCESS  read-write
        STATUS      current
        DESCRIPTION
            "String of gateway ip addresses for DHCP clients.
            Since mostly 8 ip can be configured for a pool
            totally, a string is defined to get or configure 8 ip
            ip at a time."
        ::= { unisDHCPSGlobalPoolParaEntry 6 }

    unisDHCPSGlobalPoolClientGatewayIPUndo OBJECT-TYPE
        SYNTAX      IpAddress
        MAX-ACCESS  read-write
        STATUS      current
        DESCRIPTION
            "A gateway ip address to delete. This object is
            only for deleting a given ip of gateway router."
        ::= { unisDHCPSGlobalPoolParaEntry 7 }

    unisDHCPSGlobalPoolClientDNSIPString OBJECT-TYPE
        SYNTAX      OCTET STRING(SIZE(0..129))
        MAX-ACCESS  read-write
        STATUS      current
        DESCRIPTION
            "String of DNS server ip addresses for DHCP clients.
            Since mostly 8 ip can be configured for a pool
            totally, a string is defined to get or configure 8
            ip at a time."
        ::= { unisDHCPSGlobalPoolParaEntry 8 }

    unisDHCPSGlobalPoolClientDNSIPUndo OBJECT-TYPE
        SYNTAX      IpAddress
        MAX-ACCESS  read-write
        STATUS      current
        DESCRIPTION
            "A DNS server ip address to delete. This object
            is only for deleting a given ip of DNS server."
        ::= { unisDHCPSGlobalPoolParaEntry 9 }

    unisDHCPSGlobalPoolClientNetbiosType OBJECT-TYPE
        SYNTAX      INTEGER
            {
                null(0),
                bnode(1),
                pnode(2),
                mnode(4),
                hnode(8)
            }
        MAX-ACCESS  read-write
        STATUS      current
        DESCRIPTION
            "NetBios node type for DHCP clients."
        DEFVAL { 0 }
        ::= { unisDHCPSGlobalPoolParaEntry 10 }

    unisDHCPSGlobalPoolClientNbnsIPString OBJECT-TYPE
        SYNTAX      OCTET STRING(SIZE(0..129))
        MAX-ACCESS  read-write
        STATUS      current
        DESCRIPTION
            "String of NetBios server ip addresses for DHCP
            clients. Since mostly 8 ip can be configured for
            a pool totally, so a string is defined to get or
            configure 8 ip at a time."
        ::= { unisDHCPSGlobalPoolParaEntry 11 }

    unisDHCPSGlobalPoolClientNbnsIPUndo OBJECT-TYPE
        SYNTAX      IpAddress
        MAX-ACCESS  read-write
        STATUS      current
        DESCRIPTION
            "A NetBios server ip address to delete. This
            object is only for deleting a given ip of NetBios
            server."
        ::= { unisDHCPSGlobalPoolParaEntry 12 }

    unisDHCPSGlobalPoolParaUndoFlag OBJECT-TYPE
        SYNTAX      INTEGER
            {
                undoDomain(1),
                undoLease(2),
                undoGateway(3),
                undoDns(4),
                undoNbns(5),
                undoNbType(6)
            }
        MAX-ACCESS  read-write
        STATUS      current
        DESCRIPTION
            "Flag of undo-operation for unisDHCPSGlobalPoolParaTable."
        ::= { unisDHCPSGlobalPoolParaEntry 13 }

    unisDHCPSGlobalPoolIPInUseReset OBJECT-TYPE
        SYNTAX      INTEGER
            {
                reset(1)
            }
        MAX-ACCESS  read-write
        STATUS      current
        DESCRIPTION
            "Reset the auto binding ip of the given global
            pool for DHCP server."
        ::= { unisDHCPSGlobalPoolParaEntry 14 }

--  =================================================================
-- 4th Table of unisDHCPServerMibObject: unisDHCPSGlobalPoolOptionTable
-- =================================================================
    unisDHCPSGlobalPoolOptionTable OBJECT-TYPE
        SYNTAX      SEQUENCE OF UnisDHCPSGlobalPoolOptionEntry
        MAX-ACCESS  not-accessible
        STATUS      current
        DESCRIPTION
            "A table for configuring options to DHCP global pools."
        ::= { unisDHCPServerMibObject 4 }

    unisDHCPSGlobalPoolOptionEntry OBJECT-TYPE
        SYNTAX      UnisDHCPSGlobalPoolOptionEntry
        MAX-ACCESS  not-accessible
        STATUS      current
        DESCRIPTION
            "An entry containing the objects for configuring
            options to DHCP global pools."
        INDEX { unisDHCPSGlobalPoolName, unisDHCPSGlobalPoolOptionCode }
        ::= { unisDHCPSGlobalPoolOptionTable 1 }

    UnisDHCPSGlobalPoolOptionEntry ::=
        SEQUENCE
            {
                unisDHCPSGlobalPoolOptionCode         INTEGER,
                unisDHCPSGlobalPoolOptionType         INTEGER,
                unisDHCPSGlobalPoolOptionAscii        OCTET STRING,
                unisDHCPSGlobalPoolOptionHexString    OCTET STRING,
                unisDHCPSGlobalPoolOptionIPString     OCTET STRING,
                unisDHCPSGlobalPoolOptionRowStatus    RowStatus
             }

    unisDHCPSGlobalPoolOptionCode OBJECT-TYPE
        SYNTAX      INTEGER(1..254)
        MAX-ACCESS  read-only
        STATUS      current
        DESCRIPTION
            "Option code."
        ::= { unisDHCPSGlobalPoolOptionEntry 1 }

    unisDHCPSGlobalPoolOptionType OBJECT-TYPE
        SYNTAX      INTEGER
            {
                ascii(1),
                hex(2),
                ip(3)
            }
        MAX-ACCESS  read-create
        STATUS      current
        DESCRIPTION
            "Option type."
        ::= { unisDHCPSGlobalPoolOptionEntry 2 }

    unisDHCPSGlobalPoolOptionAscii OBJECT-TYPE
        SYNTAX      OCTET STRING(SIZE(0..63))
        MAX-ACCESS  read-create
        STATUS      current
        DESCRIPTION
            "Ascii string of an option."
        ::= { unisDHCPSGlobalPoolOptionEntry 3 }

    unisDHCPSGlobalPoolOptionHexString OBJECT-TYPE
        SYNTAX      OCTET STRING(SIZE(0..143))
        MAX-ACCESS  read-create
        STATUS      current
        DESCRIPTION
            "Hex string of an option. 1st to 16th hex strings,
            which are 2 bytes, 4 bytes, 6 bytes or 8 bytes,
            can be configured at most simultaneously.
            That means the format of each string
            must be '12', '1234', '123456' or '12345678'."
        ::= { unisDHCPSGlobalPoolOptionEntry 4 }

    unisDHCPSGlobalPoolOptionIPString OBJECT-TYPE
        SYNTAX      OCTET STRING(SIZE(0..129))
        MAX-ACCESS  read-create
        STATUS      current
        DESCRIPTION
            "Ip string of an option. 1 to 8 ip addresses  can
            be configured at most simultaneously."
        ::= { unisDHCPSGlobalPoolOptionEntry 5 }

    unisDHCPSGlobalPoolOptionRowStatus OBJECT-TYPE
        SYNTAX      RowStatus
        MAX-ACCESS  read-create
        STATUS      current
        DESCRIPTION
            "RowStatus. Three actions are used: active,
            createAndGo, destroy."
        ::= { unisDHCPSGlobalPoolOptionEntry 6 }

--  =================================================================
-- 5th Table of unisDHCPServerMibObject:unisDHCPSGlobalTreeTable
-- =================================================================
    unisDHCPSGlobalTreeTable OBJECT-TYPE
        SYNTAX      SEQUENCE OF UnisDHCPSGlobalTreeEntry
        MAX-ACCESS  not-accessible
        STATUS      current
        DESCRIPTION
            "A table containing the information of the tree of
            DHCP global pools."
        ::= { unisDHCPServerMibObject 5 }

    unisDHCPSGlobalTreeEntry OBJECT-TYPE
        SYNTAX      UnisDHCPSGlobalTreeEntry
        MAX-ACCESS  not-accessible
        STATUS      current
        DESCRIPTION
            "An entry of objects containing the information
            for displaying the tree of DHCP global pools."
        INDEX { unisDHCPSGlobalPoolName }
        ::= { unisDHCPSGlobalTreeTable 1 }

    UnisDHCPSGlobalTreeEntry ::=
        SEQUENCE
            {
                unisDHCPSGlobalTreeParentNodeName        OCTET STRING,
                unisDHCPSGlobalTreeChildNodeName         OCTET STRING,
                unisDHCPSGlobalTreePreSiblingNodeName    OCTET STRING,
                unisDHCPSGlobalTreeSiblingNodeName       OCTET STRING
             }

    unisDHCPSGlobalTreeParentNodeName OBJECT-TYPE
        SYNTAX      OCTET STRING(SIZE(0..255))
        MAX-ACCESS  read-only
        STATUS      current
        DESCRIPTION
            "Pool name of the parent node."
        ::= { unisDHCPSGlobalTreeEntry 1 }

    unisDHCPSGlobalTreeChildNodeName OBJECT-TYPE
        SYNTAX      OCTET STRING(SIZE(0..255))
        MAX-ACCESS  read-only
        STATUS      current
        DESCRIPTION
            "Pool name of the child node."
        ::= { unisDHCPSGlobalTreeEntry 2 }

    unisDHCPSGlobalTreePreSiblingNodeName OBJECT-TYPE
        SYNTAX      OCTET STRING(SIZE(0..255))
        MAX-ACCESS  read-only
        STATUS      current
        DESCRIPTION
            "Pool name of the presibling node."
        ::= { unisDHCPSGlobalTreeEntry 3 }

    unisDHCPSGlobalTreeSiblingNodeName OBJECT-TYPE
        SYNTAX      OCTET STRING(SIZE(0..255))
        MAX-ACCESS  read-only
        STATUS      current
        DESCRIPTION
            "Pool name of the sibling node."
        ::= { unisDHCPSGlobalTreeEntry 4 }

--  Part 2: For DHCP server interface pool
--
-- =================================================================
-- 6th Table of unisDHCPServerMibObject: unisDHCPSInterfacePoolParaTable
-- =================================================================
    unisDHCPSInterfacePoolParaTable OBJECT-TYPE
        SYNTAX      SEQUENCE OF UnisDHCPSInterfacePoolParaEntry
        MAX-ACCESS  not-accessible
        STATUS      current
        DESCRIPTION
            "A table for configuring parameters to DHCP interface
            pools."
        ::= { unisDHCPServerMibObject 6 }

    unisDHCPSInterfacePoolParaEntry OBJECT-TYPE
        SYNTAX      UnisDHCPSInterfacePoolParaEntry
        MAX-ACCESS  not-accessible
        STATUS      current
        DESCRIPTION
            "An entry of objects for configuring parameters
            to DHCP interface pools.
            The index of this entry is the ifIndex of ethernet."
        INDEX { ifIndex }
        ::= { unisDHCPSInterfacePoolParaTable 1 }

    UnisDHCPSInterfacePoolParaEntry ::=
        SEQUENCE
            {
                unisDHCPSInterfacePoolLeaseDay              INTEGER,
                unisDHCPSInterfacePoolLeaseHour             INTEGER,
                unisDHCPSInterfacePoolLeaseMinute           INTEGER,
                unisDHCPSInterfacePoolLeaseUnlimited        INTEGER,
                unisDHCPSInterfacePoolDomainName            OCTET STRING,
                unisDHCPSInterfacePoolClientDNSIPString     OCTET STRING,
                unisDHCPSInterfacePoolClientDNSIPUndo       IpAddress,
                unisDHCPSInterfacePoolClientNetbiosType     INTEGER,
                unisDHCPSInterfacePoolClientNbnsIPString    OCTET STRING,
                unisDHCPSInterfacePoolClientNbnsIPUndo      IpAddress,
                unisDHCPSInterfacePoolParaUndoFlag          INTEGER,
                unisDHCPSInterfacePoolIPInUseReset          INTEGER
    }

    unisDHCPSInterfacePoolLeaseDay OBJECT-TYPE
        SYNTAX      INTEGER(0..365)
        MAX-ACCESS  read-write
        STATUS      current
        DESCRIPTION
            "Number of days of the lease."
        DEFVAL { 1 }
        ::= { unisDHCPSInterfacePoolParaEntry 1 }

    unisDHCPSInterfacePoolLeaseHour OBJECT-TYPE
        SYNTAX      INTEGER(0..23)
        MAX-ACCESS  read-write
        STATUS      current
        DESCRIPTION
            "Number of hours of the lease."
        DEFVAL { 0 }
        ::= { unisDHCPSInterfacePoolParaEntry 2 }

    unisDHCPSInterfacePoolLeaseMinute OBJECT-TYPE
        SYNTAX      INTEGER(0..59)
        MAX-ACCESS  read-write
        STATUS      current
        DESCRIPTION
            "Number of minutes of the lease."
        DEFVAL { 0 }
        ::= { unisDHCPSInterfacePoolParaEntry 3 }

    unisDHCPSInterfacePoolLeaseUnlimited OBJECT-TYPE
        SYNTAX      INTEGER
            {
                invalid(0),
                unlimited(1)
            }
        MAX-ACCESS  read-write
        STATUS      current
        DESCRIPTION
            "A flag denoting if the lease of a pool is
            unlimited."
        ::= { unisDHCPSInterfacePoolParaEntry 4 }

    unisDHCPSInterfacePoolDomainName OBJECT-TYPE
        SYNTAX      OCTET STRING(SIZE(0..255))
        MAX-ACCESS  read-write
        STATUS      current
        DESCRIPTION
            "Domain name for DHCP clients."
        ::= { unisDHCPSInterfacePoolParaEntry 5 }

    unisDHCPSInterfacePoolClientDNSIPString OBJECT-TYPE
        SYNTAX      OCTET STRING(SIZE(0..129))
        MAX-ACCESS  read-write
        STATUS      current
        DESCRIPTION
            "String of DNS server ip addresses for DHCP clients.
            Since mostly 8 ip can be configured for a pool
            totally, a string is defined to get or configure 8
            ip at a time."
        ::= { unisDHCPSInterfacePoolParaEntry 6 }

    unisDHCPSInterfacePoolClientDNSIPUndo OBJECT-TYPE
        SYNTAX      IpAddress
        MAX-ACCESS  read-write
        STATUS      current
        DESCRIPTION
            "A DNS server ip address to delete. This object
            is only for deleting a given ip of DNS server."
        ::= { unisDHCPSInterfacePoolParaEntry 7 }

    unisDHCPSInterfacePoolClientNetbiosType OBJECT-TYPE
        SYNTAX      INTEGER
            {
                 null(0),
                 bnode(1),
                 pnode(2),
                 mnode(4),
                 hnode(8)
            }
        MAX-ACCESS  read-write
        STATUS      current
        DESCRIPTION
            "NetBios node type for DHCP clients."
        DEFVAL { 0 }
        ::= { unisDHCPSInterfacePoolParaEntry 8 }

    unisDHCPSInterfacePoolClientNbnsIPString OBJECT-TYPE
        SYNTAX      OCTET STRING(SIZE(0..129))
        MAX-ACCESS  read-write
        STATUS      current
        DESCRIPTION
            "String of NetBios server ip addresses for DHCP
            clients. Since mostly 8 ip can be configured for
            a pool totally, so a string is defined to get or
            configure 8 ip at a time."
        ::= { unisDHCPSInterfacePoolParaEntry 9 }

    unisDHCPSInterfacePoolClientNbnsIPUndo OBJECT-TYPE
        SYNTAX      IpAddress
        MAX-ACCESS  read-write
        STATUS      current
        DESCRIPTION
            "A NetBios server ip address to delete. This
            object is only for deleting a given ip of NetBios
            server."
        ::= { unisDHCPSInterfacePoolParaEntry 10 }

    unisDHCPSInterfacePoolParaUndoFlag OBJECT-TYPE
        SYNTAX      INTEGER
            {
                undoDomain(1),
                undoLease(2),
                undoDns(4),
                undoNbns(5),
                undoNbType(6)
            }
        MAX-ACCESS  read-write
        STATUS      current
        DESCRIPTION
            "Flag of undo-operation for
            unisDHCPSInterfacePoolParaTable."
        ::= { unisDHCPSInterfacePoolParaEntry 11 }

    unisDHCPSInterfacePoolIPInUseReset OBJECT-TYPE
        SYNTAX      INTEGER
            {
                reset(1)
            }
        MAX-ACCESS  read-write
        STATUS      current
        DESCRIPTION
            "Reset the auto binding ip of the given interface
            pool for DHCP server."
        ::= { unisDHCPSInterfacePoolParaEntry 12 }

--  =====================================================================
-- 7th Table of unisDHCPServerMibObject: unisDHCPSInterfacePoolOptionTable
-- =====================================================================
    unisDHCPSInterfacePoolOptionTable OBJECT-TYPE
        SYNTAX      SEQUENCE OF UnisDHCPSInterfacePoolOptionEntry
        MAX-ACCESS  not-accessible
        STATUS      current
        DESCRIPTION
            "A table for configuring options to DHCP interface pools."
        ::= { unisDHCPServerMibObject 7 }

    unisDHCPSInterfacePoolOptionEntry OBJECT-TYPE
        SYNTAX      UnisDHCPSInterfacePoolOptionEntry
        MAX-ACCESS  not-accessible
        STATUS      current
        DESCRIPTION
            "An entry of objects for configuring options
            to DHCP interface pools.
            The index of this entry is the ifIndex of ethernet."
        INDEX { ifIndex, unisDHCPSInterfacePoolOptionCode }
        ::= { unisDHCPSInterfacePoolOptionTable 1 }

    UnisDHCPSInterfacePoolOptionEntry ::=
        SEQUENCE
            {
                unisDHCPSInterfacePoolOptionCode         INTEGER,
                unisDHCPSInterfacePoolOptionType         INTEGER,
                unisDHCPSInterfacePoolOptionAscii        OCTET STRING,
                unisDHCPSInterfacePoolOptionHexString    OCTET STRING,
                unisDHCPSInterfacePoolOptionIPString     OCTET STRING,
                unisDHCPSInterfacePoolOptionRowStatus    RowStatus
             }

    unisDHCPSInterfacePoolOptionCode OBJECT-TYPE
        SYNTAX      INTEGER(1..254)
        MAX-ACCESS  read-only
        STATUS      current
        DESCRIPTION
            "Option Code."
        ::= { unisDHCPSInterfacePoolOptionEntry 1 }

    unisDHCPSInterfacePoolOptionType OBJECT-TYPE
        SYNTAX      INTEGER
            {
                ascii(1),
                hex(2),
                ip(3)
            }
        MAX-ACCESS  read-create
        STATUS      current
        DESCRIPTION
            "Option type."
        ::= { unisDHCPSInterfacePoolOptionEntry 2 }

    unisDHCPSInterfacePoolOptionAscii OBJECT-TYPE
        SYNTAX      OCTET STRING(SIZE(0..63))
        MAX-ACCESS  read-create
        STATUS      current
        DESCRIPTION
            "Ascii string of an option."
        ::= { unisDHCPSInterfacePoolOptionEntry 3 }

    unisDHCPSInterfacePoolOptionHexString OBJECT-TYPE
        SYNTAX      OCTET STRING(SIZE(0..143))
        MAX-ACCESS  read-create
        STATUS      current
        DESCRIPTION
            "Hex string of an option. 1st to 16th hex strings,
            which are 2 bytes, 4 bytes, 6 bytes or 8 bytes,
            can be configured at most simultaneously.
            That means the format of each string
            must be '12', '1234', '123456' or '12345678'."
        ::= { unisDHCPSInterfacePoolOptionEntry 4 }

    unisDHCPSInterfacePoolOptionIPString OBJECT-TYPE
        SYNTAX      OCTET STRING(SIZE(0..129))
        MAX-ACCESS  read-create
        STATUS      current
        DESCRIPTION
            "Ip string of an option. 1 to 8 ip addresses  can
            be configured at most simultaneously."
        ::= { unisDHCPSInterfacePoolOptionEntry 5 }

    unisDHCPSInterfacePoolOptionRowStatus OBJECT-TYPE
        SYNTAX      RowStatus
        MAX-ACCESS  read-create
        STATUS      current
        DESCRIPTION
            "RowStatus. Three actions are used: active,
            createAndGo, destroy."
        ::= { unisDHCPSInterfacePoolOptionEntry 6 }

--  =========================================================================
-- 8th Table of unisDHCPServerMibObject: unisDHCPSInterfacePoolStaticBindTable
-- =========================================================================
    unisDHCPSInterfacePoolStaticBindTable OBJECT-TYPE
        SYNTAX      SEQUENCE OF UnisDHCPSInterfacePoolStaticBindEntry
        MAX-ACCESS  not-accessible
        STATUS      current
        DESCRIPTION
            "A table for configuring static binding to DHCP
            interface pools."
        ::= { unisDHCPServerMibObject 8 }

    unisDHCPSInterfacePoolStaticBindEntry OBJECT-TYPE
        SYNTAX      UnisDHCPSInterfacePoolStaticBindEntry
        MAX-ACCESS  not-accessible
        STATUS      current
        DESCRIPTION
            "An entry of objects for configuring static
            binding to DHCP interface pools.
            The index of this entry is the ifIndex of ethernet."
        INDEX { ifIndex, unisDHCPSInterfacePoolStaticBindIP }
        ::= { unisDHCPSInterfacePoolStaticBindTable 1 }

    UnisDHCPSInterfacePoolStaticBindEntry ::=
        SEQUENCE
            {
                unisDHCPSInterfacePoolStaticBindIP           IpAddress,
                unisDHCPSInterfacePoolStaticBindMac          MacAddress,
                unisDHCPSInterfacePoolStaticBindRowStatus    RowStatus
            }

    unisDHCPSInterfacePoolStaticBindIP OBJECT-TYPE
        SYNTAX      IpAddress
        MAX-ACCESS  read-only
        STATUS      current
        DESCRIPTION
            "Ip address in static binding for DHCP
            interface pools."
        ::= { unisDHCPSInterfacePoolStaticBindEntry 1 }

    unisDHCPSInterfacePoolStaticBindMac OBJECT-TYPE
        SYNTAX      MacAddress
        MAX-ACCESS  read-create
        STATUS      current
        DESCRIPTION
            "Hardware address in static binding for DHCP
            interface pools."
        ::= { unisDHCPSInterfacePoolStaticBindEntry 2 }

    unisDHCPSInterfacePoolStaticBindRowStatus OBJECT-TYPE
        SYNTAX      RowStatus
        MAX-ACCESS  read-create
        STATUS      current
        DESCRIPTION
            "RowStatus. Three actions are used: active,
            createAndGo, destroy."
        ::= { unisDHCPSInterfacePoolStaticBindEntry 3 }

--  Part 3: For DHCP server
--
-- =================================================================
-- 9th Table of unisDHCPServerMibObject: unisDHCPSIPInUseTable
-- =================================================================
    unisDHCPSIPInUseTable OBJECT-TYPE
        SYNTAX      SEQUENCE OF UnisDHCPSIPInUseEntry
        MAX-ACCESS  not-accessible
        STATUS      deprecated
        DESCRIPTION
            "A table for displaying the information of ip in use
            for DHCP server pools."
        ::= { unisDHCPServerMibObject 9 }

    unisDHCPSIPInUseEntry OBJECT-TYPE
        SYNTAX      UnisDHCPSIPInUseEntry
        MAX-ACCESS  not-accessible
        STATUS      deprecated
        DESCRIPTION
            "An entry of objects for displaying information
            of ip in use for DHCP server pools."
        INDEX { unisDHCPSIPInUseHAddr }
        ::= { unisDHCPSIPInUseTable 1 }

    UnisDHCPSIPInUseEntry ::=
        SEQUENCE
            {
                unisDHCPSIPInUseHAddr        MacAddress,
                unisDHCPSIPInUseIP           IpAddress,
                unisDHCPSIPInUseEndLease     OCTET STRING,
                unisDHCPSIPInUseType         INTEGER,
                unisDHCPSIPInUsePoolName     OCTET STRING,
                unisDHCPSIPInUseInterface    INTEGER,
                unisDHCPSIPInUseVlan         INTEGER,
                unisDHCPSIPInUseAtmpvc       INTEGER
            }

    unisDHCPSIPInUseHAddr OBJECT-TYPE
        SYNTAX      MacAddress
        MAX-ACCESS  read-only
        STATUS      deprecated
        DESCRIPTION
            "Hardware address."
        ::= { unisDHCPSIPInUseEntry 1 }

    unisDHCPSIPInUseIP OBJECT-TYPE
        SYNTAX      IpAddress
        MAX-ACCESS  read-only
        STATUS      deprecated
        DESCRIPTION
            "Ip address in use."
        ::= { unisDHCPSIPInUseEntry 2 }

    unisDHCPSIPInUseEndLease OBJECT-TYPE
        SYNTAX      OCTET STRING(SIZE(1..20))
        MAX-ACCESS  read-only
        STATUS      deprecated
        DESCRIPTION
            "End time of lease.
            The structure of the OCTET STRING is
            month/day/year hour:munite:second --
            MM/DD/YYYY hh:mm:ss. "
        ::= { unisDHCPSIPInUseEntry 3 }

    unisDHCPSIPInUseType OBJECT-TYPE
        SYNTAX      INTEGER
            {
                manual(1),
                auto(2),
                release(3)
            }
        MAX-ACCESS  read-only
        STATUS      deprecated
        DESCRIPTION
            "Type of binding."
        ::= { unisDHCPSIPInUseEntry 4 }

    unisDHCPSIPInUsePoolName OBJECT-TYPE
        SYNTAX      OCTET STRING(SIZE(1..255))
        MAX-ACCESS  read-only
        STATUS      deprecated
        DESCRIPTION
            "Name of the DHCP server pool the ip belongs to."
        ::= { unisDHCPSIPInUseEntry 5 }

    unisDHCPSIPInUseInterface OBJECT-TYPE
        SYNTAX      INTEGER
        MAX-ACCESS  read-only
        STATUS      deprecated
        DESCRIPTION
            "Interface index information."
        ::= { unisDHCPSIPInUseEntry 6 }

    unisDHCPSIPInUseVlan OBJECT-TYPE
        SYNTAX      INTEGER(1..4094)
        MAX-ACCESS  read-only
        STATUS      deprecated
        DESCRIPTION
            "Vlan information."
        ::= { unisDHCPSIPInUseEntry 7 }

    unisDHCPSIPInUseAtmpvc OBJECT-TYPE
        SYNTAX      INTEGER
        MAX-ACCESS  read-only
        STATUS      deprecated
        DESCRIPTION
            "Pvc information."
        ::= { unisDHCPSIPInUseEntry 8 }

--  =================================================================
-- 10th Table of unisDHCPServerMibObject: unisDHCPSForbiddenIPTable
-- =================================================================
    unisDHCPSForbiddenIPTable OBJECT-TYPE
        SYNTAX      SEQUENCE OF UnisDHCPSForbiddenIPEntry
        MAX-ACCESS  not-accessible
        STATUS      current
        DESCRIPTION
            "A table for configuring forbidden ip to DHCP server."
        ::= { unisDHCPServerMibObject 10 }

    unisDHCPSForbiddenIPEntry OBJECT-TYPE
        SYNTAX      UnisDHCPSForbiddenIPEntry
        MAX-ACCESS  not-accessible
        STATUS      current
        DESCRIPTION
            "An entry for configuring forbidden ip to DHCP
            server."
        INDEX { unisDHCPSForbiddenIPStart, unisDHCPSForbiddenIPEnd }
        ::= { unisDHCPSForbiddenIPTable 1 }

    UnisDHCPSForbiddenIPEntry ::=
        SEQUENCE
            {
                unisDHCPSForbiddenIPStart        IpAddress,
                unisDHCPSForbiddenIPEnd          IpAddress,
                unisDHCPSForbiddenIPRowStatus    RowStatus
            }

    unisDHCPSForbiddenIPStart OBJECT-TYPE
        SYNTAX      IpAddress
        MAX-ACCESS  read-only
        STATUS      current
        DESCRIPTION
            "Start ip of forbidden ip."
        ::= { unisDHCPSForbiddenIPEntry 1 }

    unisDHCPSForbiddenIPEnd OBJECT-TYPE
        SYNTAX      IpAddress
        MAX-ACCESS  read-only
        STATUS      current
        DESCRIPTION
            "End ip of forbidden ip."
        ::= { unisDHCPSForbiddenIPEntry 2 }

    unisDHCPSForbiddenIPRowStatus OBJECT-TYPE
        SYNTAX      RowStatus
        MAX-ACCESS  read-create
        STATUS      current
        DESCRIPTION
            "RowStatus. Three actions are used: active,
            createAndGo, destroy."
        ::= { unisDHCPSForbiddenIPEntry 3 }

--  =================================================================
-- 11th Table of unisDHCPServerMibObject: unisDHCPSConflictIPTable
-- =================================================================
    unisDHCPSConflictIPTable OBJECT-TYPE
        SYNTAX      SEQUENCE OF UnisDHCPSConflictIPEntry
        MAX-ACCESS  not-accessible
        STATUS      current
        DESCRIPTION
            "A table for displaying the information of conflict
            ip for DHCP server."
        ::= { unisDHCPServerMibObject 11 }

    unisDHCPSConflictIPEntry OBJECT-TYPE
        SYNTAX      UnisDHCPSConflictIPEntry
        MAX-ACCESS  not-accessible
        STATUS      current
        DESCRIPTION
            "An entry for displaying the information of
            conflict ip for DHCP server."
        INDEX { unisDHCPSConflictIP }
        ::= { unisDHCPSConflictIPTable 1 }

    UnisDHCPSConflictIPEntry ::=
        SEQUENCE
            {
                unisDHCPSConflictIP              IpAddress,
                unisDHCPSConflictIPType          INTEGER,
                unisDHCPSConflictIPDetectTime    OCTET STRING
            }

    unisDHCPSConflictIP OBJECT-TYPE
        SYNTAX      IpAddress
        MAX-ACCESS  read-only
        STATUS      current
        DESCRIPTION
            "Conflict ip."
        ::= { unisDHCPSConflictIPEntry 1 }

    unisDHCPSConflictIPType OBJECT-TYPE
        SYNTAX      INTEGER
            {
                ping(1),
                arp(2)
            }
        MAX-ACCESS  read-only
        STATUS      current
        DESCRIPTION
            "Type of the detection of conflict ip."
        ::= { unisDHCPSConflictIPEntry 2 }

    unisDHCPSConflictIPDetectTime OBJECT-TYPE
        SYNTAX      OCTET STRING(SIZE(1..20))
        MAX-ACCESS  read-only
        STATUS      current
        DESCRIPTION
            "Time when the conflict is detected.
            The structure of the OCTET STRING is
            month/day/year hour:munite:second --
            MM/DD/YYYY hh:mm:ss."
        ::= { unisDHCPSConflictIPEntry 3 }

--  Part 4: Non-table object
--
    unisDHCPSServiceStatus OBJECT-TYPE
        SYNTAX      UnisDhcpSEnabledStatus
        MAX-ACCESS  read-write
        STATUS      current
        DESCRIPTION
            "The status of DHCP service."
        DEFVAL { enabled }
        ::= { unisDHCPServerMibObject 12 }

    unisDHCPSDetectingServerStatus OBJECT-TYPE
        SYNTAX      UnisDhcpSEnabledStatus
        MAX-ACCESS  read-write
        STATUS      current
        DESCRIPTION
            "The status of DHCP servers detecting function."
        DEFVAL { disabled }
        ::= { unisDHCPServerMibObject 13 }

    unisDHCPSPingNum OBJECT-TYPE
        SYNTAX      INTEGER(0..10)
        MAX-ACCESS  read-write
        STATUS      current
        DESCRIPTION
            "The number of ping packets sent out."
        DEFVAL { 2 }
        ::= { unisDHCPServerMibObject 14 }

    unisDHCPSPingTimeout OBJECT-TYPE
        SYNTAX      INTEGER(0..10000)
        MAX-ACCESS  read-write
        STATUS      current
        DESCRIPTION
            "The delay for the reply of a ping packet.
            Unit: millisecond."
        DEFVAL { 500 }
        ::= { unisDHCPServerMibObject 15 }

    unisDHCPSWriteDataStatus OBJECT-TYPE
        SYNTAX      UnisDhcpSEnabledStatus
        MAX-ACCESS  read-write
        STATUS      current
        DESCRIPTION
            "The status of the function writing data to the
            harddisk."
        DEFVAL { disabled }
        ::= { unisDHCPServerMibObject 16 }

    unisDHCPSWriteDataDirection OBJECT-TYPE
        SYNTAX      OCTET STRING(SIZE(1..255))
        MAX-ACCESS  read-only
        STATUS      current
        DESCRIPTION
            "The direction of writing data to a harddisk."
        ::= { unisDHCPServerMibObject 17 }

    unisDHCPSWriteDataDelay OBJECT-TYPE
        SYNTAX      INTEGER(300..86400)
        MAX-ACCESS  read-write
        STATUS      current
        DESCRIPTION
            "The allowable delay of writing data to the
            harddisk. Unit: second."
        DEFVAL { 300 }
        ::= { unisDHCPServerMibObject 18 }

    unisDHCPSWriteDataRecover OBJECT-TYPE
        SYNTAX      UnisDhcpSEnabledStatus
        MAX-ACCESS  read-write
        STATUS      current
        DESCRIPTION
            "The flag used to recover DHCP data with the data on
            the harddisk."
        ::= { unisDHCPServerMibObject 19 }

    unisDHCPSIPInUseResetIP OBJECT-TYPE
        SYNTAX      IpAddress
        MAX-ACCESS  read-write
        STATUS      current
        DESCRIPTION
            "An ip in use that will be cleared. 0 returned for SET
            operation."
        ::= { unisDHCPServerMibObject 20 }

    unisDHCPSConflictIPResetIP OBJECT-TYPE
        SYNTAX      IpAddress
        MAX-ACCESS  read-write
        STATUS      current
        DESCRIPTION
            "A conflict ip that will be cleared. 0 returned for
            SET operation."
        ::= { unisDHCPServerMibObject 21 }

    unisDHCPSIPResetFlag OBJECT-TYPE
        SYNTAX      INTEGER
            {
                invalid(0),
                ipInUse(1),
                conflictIp(2)
            }
        MAX-ACCESS  read-write
        STATUS      current
        DESCRIPTION
            "A flag that descript the reset operation."
        ::= { unisDHCPServerMibObject 22 }

    unisDHCPSGlobalPoolNumber OBJECT-TYPE
        SYNTAX      Integer32
        MAX-ACCESS  read-only
        STATUS      current
        DESCRIPTION
            "The total number of DHCP server global-pools."
        ::= { unisDHCPServerMibObject 23 }

    unisDHCPSGlobalPoolAutoBindingNum OBJECT-TYPE
        SYNTAX      Integer32
        MAX-ACCESS  read-only
        STATUS      current
        DESCRIPTION
            "The total number of auto binding ip in DHCP server global-pools."
        ::= { unisDHCPServerMibObject 24 }

    unisDHCPSGlobalPoolManualBindingNum OBJECT-TYPE
        SYNTAX      Integer32
        MAX-ACCESS  read-only
        STATUS      current
        DESCRIPTION
            "The total number of manual binding ip in DHCP
            server global-pools."
        ::= { unisDHCPServerMibObject 25 }

    unisDHCPSGlobalPoolExpiredBindingNum OBJECT-TYPE
        SYNTAX      Integer32
        MAX-ACCESS  read-only
        STATUS      current
        DESCRIPTION
            "The total number of expired binding ip in DHCP
            server global-pools."
        ::= { unisDHCPServerMibObject 26 }

    unisDHCPSInterfacePoolNumber OBJECT-TYPE
        SYNTAX      Integer32
        MAX-ACCESS  read-only
        STATUS      current
        DESCRIPTION
            "The total number of DHCP server interface-pools."
        ::= { unisDHCPServerMibObject 27 }

    unisDHCPSInterfacePoolAutoBindingNum OBJECT-TYPE
        SYNTAX      Integer32
        MAX-ACCESS  read-only
        STATUS      current
        DESCRIPTION
            "The total number of auto binding ip in DHCP server
            interface-pools."
        ::= { unisDHCPServerMibObject 28 }

    unisDHCPSInterfacePoolManualBindingNum OBJECT-TYPE
        SYNTAX      Integer32
        MAX-ACCESS  read-only
        STATUS      current
        DESCRIPTION
            "The total number of manual binding ip in DHCP server
            interface-pools."
        ::= { unisDHCPServerMibObject 29 }

    unisDHCPSInterfacePoolExpiredBindingNum OBJECT-TYPE
        SYNTAX      Integer32
        MAX-ACCESS  read-only
        STATUS      current
        DESCRIPTION
            "The total number of expired binding ip in DHCP server
            interface-pools."
        ::= { unisDHCPServerMibObject 30 }

    unisDHCPSBadPktNum OBJECT-TYPE
        SYNTAX      Integer32
        MAX-ACCESS  read-only
        STATUS      current
        DESCRIPTION
            "The total number of the bad packets received."
        ::= { unisDHCPServerMibObject 31 }

    unisDHCPSBootRequestPktNum OBJECT-TYPE
        SYNTAX      Integer32
        MAX-ACCESS  read-only
        STATUS      current
        DESCRIPTION
            "The total number of the packets received by DHCP
            Server from DHCP clients."
        ::= { unisDHCPServerMibObject 32 }

    unisDHCPSDiscoverPktNum OBJECT-TYPE
        SYNTAX      Integer32
        MAX-ACCESS  read-only
        STATUS      current
        DESCRIPTION
            "The total number of the DHCP Discover packets
            received from the DHCP clients."
        ::= { unisDHCPServerMibObject 33 }

    unisDHCPSRequestPktNum OBJECT-TYPE
        SYNTAX      Integer32
        MAX-ACCESS  read-only
        STATUS      current
        DESCRIPTION
            "The total number of the DHCP Request packets
            received from the DHCP clients."
        ::= { unisDHCPServerMibObject 34 }

    unisDHCPSDeclinePktNum OBJECT-TYPE
        SYNTAX      Integer32
        MAX-ACCESS  read-only
        STATUS      current
        DESCRIPTION
            "The total number of the DHCP Decline packets
            received from the DHCP clients."
        ::= { unisDHCPServerMibObject 35 }

    unisDHCPSReleasePktNum OBJECT-TYPE
        SYNTAX      Integer32
        MAX-ACCESS  read-only
        STATUS      current
        DESCRIPTION
            "The total number of the DHCP Release packets
            received from the DHCP clients."
        ::= { unisDHCPServerMibObject 36 }

    unisDHCPSInformPktNum OBJECT-TYPE
        SYNTAX      Integer32
        MAX-ACCESS  read-only
        STATUS      current
        DESCRIPTION
            "The total number of the DHCP Inform packets
            received from the DHCP clients."
        ::= { unisDHCPServerMibObject 37 }

    unisDHCPSBootReplyPktNum OBJECT-TYPE
        SYNTAX      Integer32
        MAX-ACCESS  read-only
        STATUS      current
        DESCRIPTION
            "The total number of the packets sent by DHCP server
            to DHCP clients."
        ::= { unisDHCPServerMibObject 38 }

    unisDHCPSOfferPktNum OBJECT-TYPE
        SYNTAX      Integer32
        MAX-ACCESS  read-only
        STATUS      current
        DESCRIPTION
            "The total number of the DHCP Offer packets
            sent by the DHCP server."
        ::= { unisDHCPServerMibObject 39 }

    unisDHCPSAckPktNum OBJECT-TYPE
        SYNTAX      Integer32
        MAX-ACCESS  read-only
        STATUS      current
        DESCRIPTION
            "The total number of the DHCP Ack packets
            sent by the DHCP server."
        ::= { unisDHCPServerMibObject 40 }

    unisDHCPSNakPktNum OBJECT-TYPE
        SYNTAX      Integer32
        MAX-ACCESS  read-only
        STATUS      current
        DESCRIPTION
            "The total number of the DHCP Nak packets
            sent by the DHCP server."
        ::= { unisDHCPServerMibObject 41 }

    unisDHCPSStatisticsReset OBJECT-TYPE
        SYNTAX      INTEGER
            {
                reset(1)
            }
        MAX-ACCESS  read-write
        STATUS      current
        DESCRIPTION
            "Reset the above statistic information of packets
            received and sent by the DHCP server."
        ::= { unisDHCPServerMibObject 42 }

-- =================================================================
-- 43th Table of unisDHCPServerMibObject: unisDHCPSIPInUseTableEx
-- =================================================================
    unisDHCPSIPInUseExTable OBJECT-TYPE
        SYNTAX SEQUENCE OF UnisDHCPSIPInUseExEntry
        MAX-ACCESS not-accessible
        STATUS current
        DESCRIPTION
            "A table for displaying the information of ip in use
            for DHCP Server pools. "
        ::= { unisDHCPServerMibObject 43 }

    unisDHCPSIPInUseExEntry OBJECT-TYPE
        SYNTAX      UnisDHCPSIPInUseExEntry
        MAX-ACCESS  not-accessible
        STATUS      current
        DESCRIPTION
            "An entry of objects for displaying information
            of ip in use for DHCP server pools."
        INDEX { unisDHCPSIPInUseHAddrEx, unisDHCPSIPInUseVlanIdEx }
        ::= { unisDHCPSIPInUseExTable 1 }

    UnisDHCPSIPInUseExEntry ::=
        SEQUENCE
            {
                unisDHCPSIPInUseHAddrEx               MacAddress,
                unisDHCPSIPInUseVlanIdEx              INTEGER,
                unisDHCPSIPInUseIPEx                  IpAddress,
                unisDHCPSIPInUseEndLeaseEx            OCTET STRING,
                unisDHCPSIPInUseTypeEx                INTEGER,
                unisDHCPSIPInUsePoolNameEx            OCTET STRING,
                unisDHCPSIPInUseIfIndexEx             INTEGER,
                unisDHCPSIPInUseServerPortVlanIdEx    INTEGER,
                unisDHCPSIPInUseAtmpvcEx              INTEGER
            }

    unisDHCPSIPInUseHAddrEx OBJECT-TYPE
        SYNTAX      MacAddress
        MAX-ACCESS  accessible-for-notify
        STATUS      current
        DESCRIPTION
            "Hardware address."
        ::= { unisDHCPSIPInUseExEntry 1 }

    unisDHCPSIPInUseVlanIdEx OBJECT-TYPE
        SYNTAX      INTEGER(1..4094|60000)
        MAX-ACCESS  accessible-for-notify
        STATUS      current
        DESCRIPTION
            "User's vlanID.
            60000 means that a client doesn't have vlanID or have an
            invalid vlanID."
        ::= { unisDHCPSIPInUseExEntry 2 }

    unisDHCPSIPInUseIPEx OBJECT-TYPE
        SYNTAX      IpAddress
        MAX-ACCESS  read-only
        STATUS      current
        DESCRIPTION
            "Ip address in use."
        ::= { unisDHCPSIPInUseExEntry 3 }

    unisDHCPSIPInUseEndLeaseEx OBJECT-TYPE
        SYNTAX      OCTET STRING(SIZE(1..20))
        MAX-ACCESS  read-only
        STATUS      current
        DESCRIPTION
            "End time of lease.
            The structure of the OCTET STRING is
            month/day/year hour:munite:second --
            MM/DD/YYYY hh:mm:ss."
        ::= { unisDHCPSIPInUseExEntry 4 }

    unisDHCPSIPInUseTypeEx OBJECT-TYPE
        SYNTAX      INTEGER
            {
                manual(1),
                auto(2),
                release(3)
            }
        MAX-ACCESS  read-only
        STATUS      current
        DESCRIPTION
            "Type of binding."
        ::= { unisDHCPSIPInUseExEntry 5 }

    unisDHCPSIPInUsePoolNameEx OBJECT-TYPE
        SYNTAX      OCTET STRING(SIZE(1..255))
        MAX-ACCESS  read-only
        STATUS      current
        DESCRIPTION
            "Name of the DHCP server pool the ip belongs to."
        ::= { unisDHCPSIPInUseExEntry 6 }

    unisDHCPSIPInUseIfIndexEx OBJECT-TYPE
        SYNTAX      INTEGER
        MAX-ACCESS  read-only
        STATUS      current
        DESCRIPTION
            "Interface index information."
        ::= { unisDHCPSIPInUseExEntry 7 }

    unisDHCPSIPInUseServerPortVlanIdEx OBJECT-TYPE
        SYNTAX      INTEGER(1..4094)
        MAX-ACCESS  read-only
        STATUS      current
        DESCRIPTION
            "Vlan information of port on server through
             which the client user accesses server."
        ::= { unisDHCPSIPInUseExEntry 8 }

    unisDHCPSIPInUseAtmpvcEx OBJECT-TYPE
        SYNTAX      INTEGER
        MAX-ACCESS  read-only
        STATUS      current
        DESCRIPTION
            "Pvc information."
        ::= { unisDHCPSIPInUseExEntry 9 }

--  Conformance information
--
    unisDHCPServerMIBConformance OBJECT IDENTIFIER ::= { unisDHCPServerMib 2 }

    unisDHCPServerMIBCompliances OBJECT IDENTIFIER ::= { unisDHCPServerMIBConformance 1 }

    unisDHCPServerMIBGroups OBJECT IDENTIFIER ::= { unisDHCPServerMIBConformance 2 }

--  Units of conformance
--
    unisDHCPServerMIBGroup OBJECT-GROUP
        OBJECTS { unisDHCPSGlobalPoolName, unisDHCPSGlobalPoolRowStatus, unisDHCPSGlobalPoolType, unisDHCPSGlobalPoolNetwork, unisDHCPSGlobalPoolNetworkMask,
            unisDHCPSGlobalPoolHostIPAddr, unisDHCPSGlobalPoolHostMask, unisDHCPSGlobalPoolHostHAddr, unisDHCPSGlobalPoolConfigUndoFlag, unisDHCPSGlobalPoolLeaseDay,
            unisDHCPSGlobalPoolLeaseHour, unisDHCPSGlobalPoolLeaseMinute, unisDHCPSGlobalPoolLeaseUnlimited, unisDHCPSGlobalPoolDomainName, unisDHCPSGlobalPoolClientGatewayIPString,
            unisDHCPSGlobalPoolClientGatewayIPUndo, unisDHCPSGlobalPoolClientDNSIPString, unisDHCPSGlobalPoolClientDNSIPUndo, unisDHCPSGlobalPoolClientNetbiosType, unisDHCPSGlobalPoolClientNbnsIPString,
            unisDHCPSGlobalPoolClientNbnsIPUndo, unisDHCPSGlobalPoolParaUndoFlag, unisDHCPSGlobalPoolIPInUseReset, unisDHCPSGlobalPoolOptionCode, unisDHCPSGlobalPoolOptionType,
            unisDHCPSGlobalPoolOptionAscii, unisDHCPSGlobalPoolOptionHexString, unisDHCPSGlobalPoolOptionIPString, unisDHCPSGlobalPoolOptionRowStatus, unisDHCPSGlobalTreeParentNodeName,
            unisDHCPSGlobalTreeChildNodeName, unisDHCPSGlobalTreePreSiblingNodeName, unisDHCPSGlobalTreeSiblingNodeName, unisDHCPSInterfacePoolLeaseDay, unisDHCPSInterfacePoolLeaseHour,
            unisDHCPSInterfacePoolLeaseMinute, unisDHCPSInterfacePoolLeaseUnlimited, unisDHCPSInterfacePoolDomainName, unisDHCPSInterfacePoolClientDNSIPString, unisDHCPSInterfacePoolClientDNSIPUndo,
            unisDHCPSInterfacePoolClientNetbiosType, unisDHCPSInterfacePoolClientNbnsIPString, unisDHCPSInterfacePoolClientNbnsIPUndo, unisDHCPSInterfacePoolParaUndoFlag, unisDHCPSInterfacePoolIPInUseReset,
            unisDHCPSInterfacePoolOptionCode, unisDHCPSInterfacePoolOptionType, unisDHCPSInterfacePoolOptionAscii, unisDHCPSInterfacePoolOptionHexString, unisDHCPSInterfacePoolOptionIPString,
            unisDHCPSInterfacePoolOptionRowStatus, unisDHCPSInterfacePoolStaticBindIP, unisDHCPSInterfacePoolStaticBindMac, unisDHCPSInterfacePoolStaticBindRowStatus, unisDHCPSIPInUseHAddr,
            unisDHCPSIPInUseIP, unisDHCPSIPInUseEndLease, unisDHCPSIPInUseType, unisDHCPSIPInUsePoolName, unisDHCPSIPInUseInterface,
            unisDHCPSIPInUseVlan, unisDHCPSIPInUseAtmpvc, unisDHCPSForbiddenIPStart, unisDHCPSForbiddenIPEnd, unisDHCPSForbiddenIPRowStatus,
            unisDHCPSConflictIP, unisDHCPSConflictIPType, unisDHCPSConflictIPDetectTime, unisDHCPSServiceStatus, unisDHCPSDetectingServerStatus,
            unisDHCPSPingNum, unisDHCPSPingTimeout, unisDHCPSWriteDataStatus, unisDHCPSWriteDataDirection, unisDHCPSWriteDataDelay,
            unisDHCPSWriteDataRecover, unisDHCPSIPInUseResetIP, unisDHCPSConflictIPResetIP, unisDHCPSIPResetFlag, unisDHCPSGlobalPoolNumber,
            unisDHCPSGlobalPoolAutoBindingNum, unisDHCPSGlobalPoolManualBindingNum, unisDHCPSGlobalPoolExpiredBindingNum, unisDHCPSInterfacePoolNumber, unisDHCPSInterfacePoolAutoBindingNum,
            unisDHCPSInterfacePoolManualBindingNum, unisDHCPSInterfacePoolExpiredBindingNum, unisDHCPSBadPktNum, unisDHCPSBootRequestPktNum, unisDHCPSDiscoverPktNum,
            unisDHCPSRequestPktNum, unisDHCPSDeclinePktNum, unisDHCPSReleasePktNum, unisDHCPSInformPktNum, unisDHCPSBootReplyPktNum,
            unisDHCPSOfferPktNum, unisDHCPSAckPktNum, unisDHCPSNakPktNum, unisDHCPSStatisticsReset,unisDHCPSIPInUseHAddrEx,unisDHCPSIPInUseVlanIdEx,
            unisDHCPSIPInUseIPEx, unisDHCPSIPInUseEndLeaseEx,unisDHCPSIPInUseTypeEx, unisDHCPSIPInUsePoolNameEx, unisDHCPSIPInUseIfIndexEx,
            unisDHCPSIPInUseServerPortVlanIdEx, unisDHCPSIPInUseAtmpvcEx }
        STATUS      current
        DESCRIPTION
            "The basic collection of objects providing management of
            DHCP server."
        ::= { unisDHCPServerMIBGroups 1 }


    END
