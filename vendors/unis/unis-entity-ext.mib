-- =================================================================
-- Copyright (c) 2020 Unisyue Technologies Co., Ltd.  All rights reserved.
--
-- Description: description of entity extend properties.
-- Reference:
-- History V3.2
-- V1.0 Created by weixinzhe, Thursday, April 22, 2004 at 18:26:02
-- V1.1 modified by yelinhui, add unisEntityExtMacAddress
-- V1.2 modified by panxidong, add unisEntityExtErrorStatus
-- V1.3 2004-10-12 updated by gaolong
--      Remove BITS from IMPORTS
-- V1.4 2005-02-25 modified by longyin
--      Add error status stackPortBlocked(22) and stackPortFailed(23)
--      for unisEntityExtErrorStatus
-- V1.5 2006-05-16 modified by wangsihai
--      Add error status sensorError(81) in unisEntityExtErrorStatus
-- V1.6 2006-07-03 modified by lifengguang
--      Add unisEntityExtManuTable
-- V1.7 2007-09-21 modified by lifengguang
--      Add notification object unisEntityExtSFPAlarmOn and unisEntityExtSFPAlarmOff
--      Add unisEntityExtPowerTable
-- V1.8 2007-11-19 modified by jinyi
--      Add unisEntityExtCpuMaxUsage
-- V1.9 2008-02-27 modified by lifengguang
--      Add Trap nodes: unisEntityExtSFPPhony
-- V2.0 2008-07-11 modified by lisong
--      Add unisProcessTable
--      Add notification object unisEntityInsert and unisEntityRemove
-- V2.1 2008-07-14 modified by lifengguang
--      Add error status hardwareFaulty(91) in unisEntityExtErrorStatus
--      Add Trap nodes: unisEntityExtForcedPowerOff and unisEntityExtForcedPowerOn
--      Add Trap nodes: unisEntityExtFaultAlarmOn and unisEntityExtFaultAlarmOff
-- V2.2 2008-10-24 modified by lifengguang
--      Add nodes unisEntityExtLowerTemperatureThreshold and
--      unisEntityExtShutdownTemperatureThreshold in unisEntityExtStateTable
--      Add trap nodes unisEntityExtResourceLack and unisEntityExtResourceEnough
--      in unisEntityExtTrapsPrefix
--      Add trap nodes unisEntityExtTemperatureLower, unisEntityExtTemperatureTooUp
--      and unisEntityExtTemperatureNormal in unisEntityExtTrapsPrefix
-- V2.3 2009-04-07 Added trap nodes unisEntityExternalAlarmOccur and
--      unisEntityExternalAlarmRecover
-- v2.4 2009-05-05 Added unisEntityExtCpuAvgUsage, unisEntityExtMemAvgUsage,
--      unisEntityExtPhyMemSize, unisEntityExtMemType, unisEntityExtPhyCpuFrequency,
--      unisEntityExtFirstUsedDate,
--      unisEntityExtCpuUsageThresholdRecover, unisEntityExtMemUsageThresholdRecover
-- V2.5 2010-08-09
--      Added unisEntityExtShutdownLowerTemperatureThreshold,
--      unisEntityExtCriticalLowerTemperatureThreshold,
--      unisEntityExtCritLowerTempThresholdNotification and
--      unisEntityExtTemperatureTooLow by zhanglei 06807.
--      Added unisEntityExtMemAllocatedFailed, unisEntityExtECCParityAlarm,
--      unisEntityExtTrapDescription, unisEntityExtECCParityAlarmStatus
--      by zhangqingjun 02357.
--      Modified description of unisEntityExtPhyMemSize by haoyan 06611.
-- V2.6 2010-12-06
--      Added unisEntityExtFanDirectionNotPreferred, unisEntityExtFanDirectionNotAccord
--      by lifengguang 03035.
-- V2.7 2011-04-06
--      Added unisEntityExtSFPInvalid, unisEntityExtSFPInvalidNow and
--      unisEntityExtSFPInvalidInDays by songhao 02718.
--      Changed SYNTAX of unisEntityExtMemSize and unisEntityExtPhyMemSize
--      from Integer32 to Unsigned32 by songhao 02718.
-- V2.8 2011-08-30
--      Added unisEntityExtCpuUsageRecoverThreshold;
--      Added unisEntityExtCpuUsageRecoverThreshold to unisEntityExtCpuUsageThresholdNotfication and
--      unisEntityExtCpuUsageThresholdRecover by shuaixiaojuan 04117.
--      Added unisEntityExtFirstTrapTime by duyanbing 04404.
-- V2.9 2013-04-27
--      Added unisEntityExtMemSizeRev by fangliwen 08502.
--      Added trap nodes unisEntityExtMemUsageThresholdOverTrap and
--      unisEntityExtMemUsageThresholdRecoverTrap by fangliwen 08502.
-- V3.0 2013-12-16
--      Added unisEntityExtCpuUsageIn1Minute and unisEntityExtCpuUsageIn5Minutes
--      by fangliwen 08502.
-- V3.1 2014-01-24
--      Added unisEntityExtVoltageObjects by fangliwen 08502.
--      Added trap nodes unisEntityExtVoltageNormal, unisEntityExtVoltageTooLow,
--      unisEntityExtVoltageLower, unisEntityExtVoltageHigher and
--      unisEntityExtVoltageTooHigh by fangliwen 08502.
-- V3.2 2015-01-12
--      Added trap nodes unisEntityExtSFPAlarmOnEx, unisEntityExtSFPAlarmOffEx by fangliwen 08502.
-- =================================================================
UNIS-ENTITY-EXT-MIB DEFINITIONS ::= BEGIN

    IMPORTS
        unisCommon
            FROM UNIS-OID-MIB
        OBJECT-GROUP, MODULE-COMPLIANCE, NOTIFICATION-GROUP
            FROM SNMPv2-CONF
        OBJECT-TYPE, MODULE-IDENTITY, NOTIFICATION-TYPE, Integer32,
        Unsigned32, Gauge32, TimeTicks
            FROM SNMPv2-SMI
        TEXTUAL-CONVENTION, MacAddress, DateAndTime, DisplayString
            FROM SNMPv2-TC
        SnmpAdminString
            FROM SNMP-FRAMEWORK-MIB
        entPhysicalIndex, entPhysicalName, entPhysicalDescr
            FROM ENTITY-MIB
        CounterBasedGauge64
            FROM HCNUM-TC;

    unisEntityExtend MODULE-IDENTITY
        LAST-UPDATED "201501120000Z"
        ORGANIZATION
            "Unisyue Technologies Co., Ltd."
        CONTACT-INFO
            ""
        DESCRIPTION
            "The private MIB file includes the general extent
            information of the device."
        ::= { unisCommon 6 }

    UnisAdminState  ::=  TEXTUAL-CONVENTION
        STATUS            current
        DESCRIPTION
            "The administrative state for this object, and it is possible to
            set the state when needed.
            A value of locked means the resource is administratively prohibited
            from use. A value of shuttingDown means that usage is
            administratively limited to current instances of use.
            A value of unlocked means the resource is not administratively
            prohibited from use."
        REFERENCE
            "ITU Recommendation X.731, 'Information Technology - Open
            Systems Interconnection - System Management: State
            Management Function', 1992"
        SYNTAX  INTEGER
        {
            notSupported(1),
            locked(2),
            shuttingDown(3),
            unlocked(4)
        }

    UnisOperState  ::=  TEXTUAL-CONVENTION
        STATUS            current
        DESCRIPTION
            " Represents the possible values of operational states.
            A value of disabled means the resource is totally
            inoperable. A value of enabled means the resource
            is partially or fully operable."
        REFERENCE
            "ITU Recommendation X.731, 'Information Technology - Open
            Systems Interconnection - System Management: State
            Management Function', 1992"
        SYNTAX  INTEGER
        {
            notSupported (1),
            disabled(2),
            enabled(3),
            dangerous(4)
        }
    UnisAlarmStatus  ::=  TEXTUAL-CONVENTION
        STATUS            current
        DESCRIPTION
            "Represents the possible values of alarm status.
            When no bits of this attribute are set, then none of the
            status conditions described below are present. When the
            value of under repair is set, the resource is currently
            being repaired.

            When the value of critical is set, one or more critical
            alarms are active against the resource. When the value of
            major is set, one or more major alarms are active against
            the resource. When the value of minor is set, one or more
            minor alarms are active against the resource. When the
            value of warning is set, one or more warning alarms are
            active against the resource. When the value of
            indeterminate is set, one or more  alarms of indeterminate
            severity are active against the resource.
            When the value of alarm outstanding is set, one or more
            alarms is active against the resource. The fault may or may
            not be disabling."
            REFERENCE
            "ITU Recommendation X.731, 'Information Technology - Open
            Systems Interconnection - System Management: State
            Management Function', 1992"
        SYNTAX           BITS
        {
            notSupported (0),
            underRepair(1),
            critical(2),
            major(3),
            minor(4),
            alarmOutstanding(5),
            warning (6), -- Not defined in X.731
            indeterminate (7) -- Not defined in X.731
        }


    UnisStandbyStatus  ::=  TEXTUAL-CONVENTION
        STATUS            current
        DESCRIPTION
                " Represents the possible values of standby status.

                  A value of hotStandby means the resource is not providing
                  service, but is will be immediately able to take over the
                  role of the resource to be backed-up, without the need for
                  initialization activity, and will contain the same
                  information as the resource to be backed up. A value of
                  coldStandy means that the resource is to back-up another
                  resource, but will not be immediately able to take over
                  the role of a resource to be backed up, and will require
                  some initialization activity. A value of providingService
                  means the resource is providing service."
        REFERENCE
            "ITU Recommendation X.731, 'Information Technology - Open
            Systems Interconnection - System Management: State
            Management Function', 1992"
        SYNTAX            INTEGER
        {
            notSupported (1),
            hotStandby(2),
            coldStandby(3),
            providingService(4)
        }


    unisEntityExtObjects OBJECT IDENTIFIER ::= { unisEntityExtend 1 }


--  MIB contains four groups

    unisEntityExtState OBJECT IDENTIFIER ::= { unisEntityExtObjects 1 }

    unisEntityExtStateTable OBJECT-TYPE
        SYNTAX SEQUENCE OF UnisEntityExtStateEntry
        MAX-ACCESS not-accessible
        STATUS current
        DESCRIPTION
            "This table contains one row per physical entity, There is
            always at least one row for an 'overall' physical entity.
            The information in each row may be not include all the object
            in this table, because of the entity need not some of the
            information here."
        ::= { unisEntityExtState 1 }

    unisEntityExtStateEntry OBJECT-TYPE
        SYNTAX UnisEntityExtStateEntry
        MAX-ACCESS not-accessible
        STATUS current
        DESCRIPTION
            "The information about a particular physical entity."
        INDEX { unisEntityExtPhysicalIndex }
        ::= { unisEntityExtStateTable 1 }

    UnisEntityExtStateEntry ::= SEQUENCE {
        unisEntityExtPhysicalIndex
            Integer32,
        unisEntityExtAdminStatus
            UnisAdminState,
        unisEntityExtOperStatus
            UnisOperState,
        unisEntityExtStandbyStatus
            UnisStandbyStatus,
        unisEntityExtAlarmLight
            UnisAlarmStatus,
        unisEntityExtCpuUsage
            Integer32,
        unisEntityExtCpuUsageThreshold
            Integer32,
        unisEntityExtMemUsage
            Integer32,
        unisEntityExtMemUsageThreshold
            Integer32,
        unisEntityExtMemSize
            Unsigned32,
        unisEntityExtUpTime
            Integer32,
        unisEntityExtTemperature
            Integer32,
        unisEntityExtTemperatureThreshold
            Integer32,
        unisEntityExtVoltage
            Integer32,
        unisEntityExtVoltageLowThreshold
            Integer32,
        unisEntityExtVoltageHighThreshold
            Integer32,
        unisEntityExtCriticalTemperatureThreshold
            Integer32,
        unisEntityExtMacAddress
            MacAddress,
        unisEntityExtErrorStatus
            INTEGER,
        unisEntityExtCpuMaxUsage
            Integer32,
        unisEntityExtLowerTemperatureThreshold
            Integer32,
        unisEntityExtShutdownTemperatureThreshold
            Integer32,
        unisEntityExtPhyMemSize
            Unsigned32,
        unisEntityExtPhyCpuFrequency
            Integer32,
        unisEntityExtFirstUsedDate
            DateAndTime,
        unisEntityExtCpuAvgUsage
            Integer32,
        unisEntityExtMemAvgUsage
            Integer32,
        unisEntityExtMemType
            OCTET STRING,
        unisEntityExtCriticalLowerTemperatureThreshold
            Integer32,
        unisEntityExtShutdownLowerTemperatureThreshold
            Integer32,
        unisEntityExtCpuUsageRecoverThreshold
            Integer32,
        unisEntityExtMemSizeRev
            CounterBasedGauge64,
        unisEntityExtCpuUsageIn1Minute
            Integer32,
        unisEntityExtCpuUsageIn5Minutes
            Integer32
     }

    unisEntityExtPhysicalIndex OBJECT-TYPE
        SYNTAX Integer32
        MAX-ACCESS accessible-for-notify
        STATUS current
        DESCRIPTION
            "The index of unisEntityExtStateTable.
            This index is identical to entPhysicalIndex in ENTITY-MIB"
        ::= { unisEntityExtStateEntry 1 }

    unisEntityExtAdminStatus OBJECT-TYPE
        SYNTAX UnisAdminState
        MAX-ACCESS read-write
        STATUS current
        DESCRIPTION
            "The administrative state for this object."
        ::= { unisEntityExtStateEntry 2 }

    unisEntityExtOperStatus OBJECT-TYPE
        SYNTAX UnisOperState
        MAX-ACCESS read-only
        STATUS current
        DESCRIPTION
            "The operate state for this object."
        ::= { unisEntityExtStateEntry 3 }

    unisEntityExtStandbyStatus OBJECT-TYPE
        SYNTAX UnisStandbyStatus
        MAX-ACCESS read-only
        STATUS current
        DESCRIPTION
            "This object is used for monitoring standby status.
            Not all entities support this object."
        ::= { unisEntityExtStateEntry 4 }

    unisEntityExtAlarmLight OBJECT-TYPE
        SYNTAX UnisAlarmStatus
        MAX-ACCESS read-only
        STATUS current
        DESCRIPTION
            "The alarm status for this entity. It does not include
            the severity of alarms raised on child components. In
            this condition, there will be a alarm light on the entity,
            the object should have the same status with it."
        ::= { unisEntityExtStateEntry 5 }

    unisEntityExtCpuUsage OBJECT-TYPE
        SYNTAX Integer32 (0..100)
        MAX-ACCESS read-only
        STATUS current
        DESCRIPTION
            "The CPU usage for this entity. Generally, the overall
            CPU usage on the entity is calculated, independent of
            the number of CPUs on the entity."
        ::= { unisEntityExtStateEntry 6 }

    unisEntityExtCpuUsageThreshold OBJECT-TYPE
        SYNTAX Integer32 (0..100)
        MAX-ACCESS read-write
        STATUS current
        DESCRIPTION
            "The threshold for the CPU usage. When the CPU usage exceeds
            the threshold, a notification will be sent."
        ::= { unisEntityExtStateEntry 7 }

    unisEntityExtMemUsage OBJECT-TYPE
        SYNTAX Integer32 (0..100)
        MAX-ACCESS read-only
        STATUS current
        DESCRIPTION
            "The memory usage for the entity. This object indicates what
            percent of memory are used."
        ::= { unisEntityExtStateEntry 8 }

    unisEntityExtMemUsageThreshold OBJECT-TYPE
        SYNTAX Integer32 (0..100)
        MAX-ACCESS read-write
        STATUS current
        DESCRIPTION
            "The threshold for the Memory usage, When the memory usage
            exceeds the threshold, a notification will be sent."
        ::= { unisEntityExtStateEntry 9 }

    unisEntityExtMemSize OBJECT-TYPE
        SYNTAX Unsigned32
        UNITS "bytes"
        MAX-ACCESS read-only
        STATUS current
        DESCRIPTION
            "The size of memory for the entity.

            If the amount of memory exceeds 4,294,967,295 bytes,
            the value remains 4,294,967,295 bytes."
        ::= { unisEntityExtStateEntry 10 }

    unisEntityExtUpTime OBJECT-TYPE
        SYNTAX Integer32
        UNITS "seconds"
        MAX-ACCESS read-only
        STATUS current
        DESCRIPTION
            "The uptime for the entity. The meaning of uptime is
            when the entity is up, and the value of the object
            will add 1 seconds while the entity is running."
        ::= { unisEntityExtStateEntry 11 }

    unisEntityExtTemperature OBJECT-TYPE
        SYNTAX Integer32
        MAX-ACCESS read-only
        STATUS current
        DESCRIPTION
            "The temperature for the entity."
        ::= { unisEntityExtStateEntry 12 }

    unisEntityExtTemperatureThreshold OBJECT-TYPE
        SYNTAX Integer32
        MAX-ACCESS read-write
        STATUS current
        DESCRIPTION
            "The threshold for the temperature. When the temperature
            exceeds the threshold, a notification will be sent."
        ::= { unisEntityExtStateEntry 13 }

    unisEntityExtVoltage OBJECT-TYPE
        SYNTAX Integer32
        MAX-ACCESS read-only
        STATUS current
        DESCRIPTION
            "The voltage for the entity."
        ::= { unisEntityExtStateEntry 14 }

    unisEntityExtVoltageLowThreshold OBJECT-TYPE
        SYNTAX Integer32
        MAX-ACCESS read-write
        STATUS current
        DESCRIPTION
            "The low-threshold for the voltage.
            When voltage is lower than low-threshold, a notification will be
            sent."
        ::= { unisEntityExtStateEntry 15 }

    unisEntityExtVoltageHighThreshold OBJECT-TYPE
        SYNTAX Integer32
        MAX-ACCESS read-write
        STATUS current
        DESCRIPTION
            "The high-threshold for the voltage.
            When voltage greater than high-threshold, a notification will be
            sent."
        ::= { unisEntityExtStateEntry 16 }

    unisEntityExtCriticalTemperatureThreshold OBJECT-TYPE
        SYNTAX Integer32
        MAX-ACCESS read-write
        STATUS current
        DESCRIPTION
            " The threshold for the critical Temperature. When temperature
            exceeds the critical temperature, a notification will be sent."
        ::= { unisEntityExtStateEntry 17 }

    unisEntityExtMacAddress OBJECT-TYPE
        SYNTAX MacAddress
        MAX-ACCESS read-only
        STATUS current
        DESCRIPTION
            "MAC Address of the entity."
        ::= { unisEntityExtStateEntry 18 }

    unisEntityExtErrorStatus OBJECT-TYPE
        SYNTAX INTEGER
            {
            notSupported(1),
            normal(2),
            postFailure(3),
            entityAbsent(4),
            poeError(11),
            stackError(21),
            stackPortBlocked(22),
            stackPortFailed(23),
            sfpRecvError(31),
            sfpSendError(32),
            sfpBothError(33),
            fanError (41),
            psuError(51),
            rpsError(61),
            moduleFaulty(71),
            sensorError(81),
            hardwareFaulty(91)
            }
        MAX-ACCESS read-only
        STATUS current
        DESCRIPTION
            "Indicate the error state of this entity object. Now it only
            supports Port, general power supply, RPS power supply and
            board/Subcard. It may have one of these values.
            The following four values  can be used for all kinds of entities.

            notSupported(1) means this entity cannot support this function.
            normal(2) means the statement of this entity is normal. for ports,
            it doesn't differentiate 10M/s, 100M/s, 1000M/s, duplex and
            half-duplex. For fan, power supply and board-Subcard, it means
            their states are normal.
            postFailure(3)  means the entity fails to POST.
            entityAbsent(4) means the entity is absent now.


            The following values is depended on the entity.

            For Port entities, it may have the following  values. If its POST
            is failure,
            then the value of the instance will be postFailure(3), otherwise
            the value will be normal(2).

            If enable power supply over Ethernet on this port is failure,
            the value of this instance will be poeError(11), otherwise it will
            be normal(2).

            For stack port, if it connects to another stack port normally, and
            these two units merge into one stack, then the value of this
            instance will be normal(2).
            If something wrong occurs and the unit cannot merge into stack,
            the value of this instance will be stackPortFailed(23).  If the
            stack port forms resilient daisy chain with another stack port
            on the other unit, the value of this instance will be
            stackPortBlocked(22).


            For SFP ports, if it fail to receive, the value of this instance
            will be sfpRecvError(31), if it fail to send, the value is
            sfpSendError(32), if it fail to send and receive, the value is
            sfpBothError(33), otherwise it will be normal(2).

            fanError(41) means that the fan stops working.

            psuError(51) means that the Power Supply Unit is in the state of
            fault.

            rpsError(61) means the RPS is in the state of fault.

            moduleFaulty(71) means the Module is in the state of fault.

            sensorError(81) means the sensor is in the state of fault.

            hardwareFaulty(91) means the hardware of specified entity is in the state of fault.

            NMS must be compatible with the states which may be added
            in the future."
        ::= { unisEntityExtStateEntry 19 }

    unisEntityExtCpuMaxUsage OBJECT-TYPE
        SYNTAX Integer32(0..100)
        MAX-ACCESS read-only
        STATUS current
        DESCRIPTION
            "The maximal CPU usage for the entity in the period of time."
        ::= { unisEntityExtStateEntry 20 }

    unisEntityExtLowerTemperatureThreshold OBJECT-TYPE
        SYNTAX Integer32
        MAX-ACCESS read-write
        STATUS current
        DESCRIPTION
            "The threshold for the lower Temperature. When temperature runs
            under the threshold, a notification will be sent."
        ::= { unisEntityExtStateEntry 21 }

    unisEntityExtShutdownTemperatureThreshold OBJECT-TYPE
        SYNTAX Integer32
        MAX-ACCESS read-write
        STATUS current
        DESCRIPTION
            "The threshold for the shutdown Temperature. When temperature
            exceeds the threshold, a notification will be sent and the entity
            will be shutdown."
        ::= { unisEntityExtStateEntry 22 }

    unisEntityExtPhyMemSize OBJECT-TYPE
        SYNTAX Unsigned32
        MAX-ACCESS read-only
        STATUS current
        DESCRIPTION
            "The memory size of entity. This is the physical attribute of entity."
        ::= { unisEntityExtStateEntry 23 }

    unisEntityExtPhyCpuFrequency OBJECT-TYPE
        SYNTAX Integer32
        MAX-ACCESS read-only
        STATUS current
        DESCRIPTION
            "The CPU frequency of entity. Unit of measure is MHZ."
        ::= { unisEntityExtStateEntry 24 }

    unisEntityExtFirstUsedDate OBJECT-TYPE
        SYNTAX DateAndTime (SIZE(8))
        MAX-ACCESS read-only
        STATUS current
        DESCRIPTION
            "The first used date of the entity."
        ::= { unisEntityExtStateEntry 25 }

    unisEntityExtCpuAvgUsage OBJECT-TYPE
        SYNTAX Integer32(0..100)
        MAX-ACCESS read-only
        STATUS current
        DESCRIPTION
            "The average CPU usage for the entity in a period of time."
        ::= { unisEntityExtStateEntry 26 }

    unisEntityExtMemAvgUsage OBJECT-TYPE
        SYNTAX Integer32(0..100)
        MAX-ACCESS read-only
        STATUS current
        DESCRIPTION
            "The average memory usage for the entity in a period of time."
        ::= { unisEntityExtStateEntry 27 }

    unisEntityExtMemType OBJECT-TYPE
        SYNTAX OCTET STRING(SIZE (0..64))
        MAX-ACCESS read-only
        STATUS current
        DESCRIPTION
            "The memory type of entity."
        ::= { unisEntityExtStateEntry 28 }

    unisEntityExtCriticalLowerTemperatureThreshold OBJECT-TYPE
        SYNTAX Integer32
        MAX-ACCESS read-write
        STATUS current
        DESCRIPTION
            "The threshold for the critical Temperature.  When temperature
            exceeds the critical lower temperature, a notification will be sent."
        ::= { unisEntityExtStateEntry 29 }

    unisEntityExtShutdownLowerTemperatureThreshold OBJECT-TYPE
        SYNTAX Integer32
        MAX-ACCESS read-write
        STATUS current
        DESCRIPTION
            "The threshold for the shutdown Temperature.  When temperature
            exceeds the lower threshold, a notification will be sent and the entity
            will be shutdown."
        ::= { unisEntityExtStateEntry 30 }

    unisEntityExtCpuUsageRecoverThreshold OBJECT-TYPE
        SYNTAX Integer32 (0..100)
        MAX-ACCESS read-write
        STATUS current
        DESCRIPTION
            "The recover threshold for the CPU usage.  When the CPU usage falls down to
            the threshold, a notification is sent.  The unisEntityExtCpuUsageRecoverThreshold
            must be less than or equal to the unisEntityExtCpuUsageThreshold."
        DEFVAL      { 100 }
        ::= { unisEntityExtStateEntry 31 }

    unisEntityExtMemSizeRev OBJECT-TYPE
        SYNTAX CounterBasedGauge64
        UNITS "bytes"
        MAX-ACCESS read-only
        STATUS current
        DESCRIPTION
            "Size of memory space for the entity.

            This node is used to replace unisEntityExtMemSize."
        ::= { unisEntityExtStateEntry 32 }

    unisEntityExtCpuUsageIn1Minute OBJECT-TYPE
        SYNTAX Integer32 (0..100)
        MAX-ACCESS read-only
        STATUS current
        DESCRIPTION
            "The CPU usage in last one minute for this entity.
            Generally, the overall CPU usage on the entity is
            calculated, independent of the number of CPUs on
            the entity."
        ::= { unisEntityExtStateEntry 33 }

    unisEntityExtCpuUsageIn5Minutes OBJECT-TYPE
        SYNTAX Integer32 (0..100)
        MAX-ACCESS read-only
        STATUS current
        DESCRIPTION
            "The CPU usage in last five minutes for this entity.
            Generally, the overall CPU usage on the entity is
            calculated, independent of the number of CPUs on
            the entity."
        ::= { unisEntityExtStateEntry 34 }

    unisEntityExtManu OBJECT IDENTIFIER ::= { unisEntityExtObjects 2 }

    unisEntityExtManuTable OBJECT-TYPE
        SYNTAX SEQUENCE OF UnisEntityExtManuEntry
        MAX-ACCESS not-accessible
        STATUS current
        DESCRIPTION
            "The table about device manufacture information."
        ::= { unisEntityExtManu 1 }

    unisEntityExtManuEntry OBJECT-TYPE
        SYNTAX UnisEntityExtManuEntry
        MAX-ACCESS not-accessible
        STATUS current
        DESCRIPTION
            "The device manufacture information about a particular physical
            entity."
        INDEX { unisEntityExtManuPhysicalIndex }
        ::= { unisEntityExtManuTable 1 }

    UnisEntityExtManuEntry ::= SEQUENCE {
        unisEntityExtManuPhysicalIndex
            Integer32,
        unisEntityExtManuSerialNum
            SnmpAdminString,
        unisEntityExtManuBuildInfo
            SnmpAdminString,
        unisEntityExtManuBOM
            SnmpAdminString,
        unisEntityExtMacAddressCount
            Unsigned32
     }

    unisEntityExtManuPhysicalIndex OBJECT-TYPE
        SYNTAX Integer32 (1..2147483647)
        MAX-ACCESS accessible-for-notify
        STATUS current
        DESCRIPTION
            "The index of unisEntityExtManuTable.
            This index is identical to entPhysicalIndex in ENTITY-MIB."
        ::= { unisEntityExtManuEntry 1 }

    unisEntityExtManuSerialNum OBJECT-TYPE
        SYNTAX SnmpAdminString
        MAX-ACCESS read-only
        STATUS current
        DESCRIPTION
            "Manufacture serial number.
            The manufacture serial number of the entity such as chassis,
            module, and so on.  It is got from the device when manufacturing.
            For low level box-device, the manufacture serial number is the
            device-number of System Control Board(SCB for short), it is written
            into the SCB directly; for middle level or high level frame-device,
            the manufacture serial number is the device-numbers of SCB and
            Service Board, because the SCB, Service Board and chassis are
            separate to sale and the device-number of chassis cannot be
            written into board."
        ::= { unisEntityExtManuEntry 2 }

    unisEntityExtManuBuildInfo OBJECT-TYPE
        SYNTAX SnmpAdminString
        MAX-ACCESS read-only
        STATUS current
        DESCRIPTION
            "Device version information.
            The device version information of the entity such as chassis,
            module, and so on.  It consists of software version information
            and hardware version information."
        ::= { unisEntityExtManuEntry 3 }

    unisEntityExtManuBOM OBJECT-TYPE
        SYNTAX SnmpAdminString
        MAX-ACCESS read-only
        STATUS current
        DESCRIPTION
            "Device BOM code.
            The device BOM code of the entity such as chassis, module, and so
            on.  It is the component code of ERP system, which can be
            disassembled from device-number."
        ::= { unisEntityExtManuEntry 4 }

    unisEntityExtMacAddressCount OBJECT-TYPE
        SYNTAX Unsigned32
        MAX-ACCESS read-only
        STATUS current
        DESCRIPTION
            "MAC address count.
            The count of MAC addresses of the entity, such as chassis, module,
            or port, and so on."
        ::= { unisEntityExtManuEntry 5 }

    unisEntityExtPower OBJECT IDENTIFIER ::= { unisEntityExtObjects 3 }

    unisEntityExtPowerTable OBJECT-TYPE
        SYNTAX SEQUENCE OF UnisEntityExtPowerEntry
        MAX-ACCESS not-accessible
        STATUS current
        DESCRIPTION
            "This table describes the power information of all the physical
            entity on the device, such as the fans, the subcards, the boards,
            etc."
        ::= { unisEntityExtPower 1 }

    unisEntityExtPowerEntry OBJECT-TYPE
        SYNTAX UnisEntityExtPowerEntry
        MAX-ACCESS not-accessible
        STATUS current
        DESCRIPTION
            "The entity power information about a particular physical entity."
        INDEX { unisEntityExtPowerPhysicalIndex }
        ::= { unisEntityExtPowerTable 1 }

    UnisEntityExtPowerEntry ::= SEQUENCE {
        unisEntityExtPowerPhysicalIndex
            Integer32,
        unisEntityExtNominalPower
            Gauge32,
        unisEntityExtCurrentPower
            Gauge32,
        unisEntityExtAveragePower
            Integer32,
        unisEntityExtPeakPower
            Integer32
     }

    unisEntityExtPowerPhysicalIndex OBJECT-TYPE
        SYNTAX Integer32 (1..2147483647)
        MAX-ACCESS accessible-for-notify
        STATUS current
        DESCRIPTION
            "The index of unisEntityExtPowerTable.
            This index is identical to entPhysicalIndex in ENTITY-MIB."
        ::= { unisEntityExtPowerEntry 1 }

    unisEntityExtNominalPower OBJECT-TYPE
        SYNTAX Gauge32
        MAX-ACCESS read-only
        STATUS current
        DESCRIPTION
            "The nominal power of the entity expressed in milliWatts."
        ::= { unisEntityExtPowerEntry 2 }

    unisEntityExtCurrentPower OBJECT-TYPE
        SYNTAX Gauge32
        MAX-ACCESS read-only
        STATUS current
        DESCRIPTION
            "The measured usage power of the entity expressed in milliWatts."
        ::= { unisEntityExtPowerEntry 3 }

    unisEntityExtAveragePower OBJECT-TYPE
        SYNTAX Integer32
        MAX-ACCESS read-write
        STATUS current
        DESCRIPTION
            "The average power consumed by the entity expressed in milliWatts.
            Writing a value of zero to this object resets its value to zero.
            Writing any other value to this object has no effect on its value
            and an error is returned."
        ::= { unisEntityExtPowerEntry 4 }

    unisEntityExtPeakPower OBJECT-TYPE
        SYNTAX Integer32
        MAX-ACCESS read-write
        STATUS current
        DESCRIPTION
            "The peak power consumed by the entity expressed in milliWatts.
            Writing a value of zero to this object resets its value to zero.
            Writing any other value to this object has no effect on its value
            and an error is returned."
        ::= { unisEntityExtPowerEntry 5 }

-- Process Table
    unisProcessObjects OBJECT IDENTIFIER ::= { unisEntityExtObjects 4 }

    unisProcessTable OBJECT-TYPE
        SYNTAX SEQUENCE OF UnisProcessEntry
        MAX-ACCESS not-accessible
        STATUS current
        DESCRIPTION
            "The Table describes the information about a particular process,
            namely a task."
        ::= { unisProcessObjects 1 }

    unisProcessEntry OBJECT-TYPE
        SYNTAX UnisProcessEntry
        MAX-ACCESS not-accessible
        STATUS current
        DESCRIPTION
            "The information about a particular process, namely a task."
        INDEX { unisProcessID }
        ::= { unisProcessTable 1 }

    UnisProcessEntry ::= SEQUENCE {
        unisProcessID          Unsigned32,
        unisProcessName        DisplayString,
        unisProcessUtil5Min    Unsigned32
     }

    unisProcessID OBJECT-TYPE
        SYNTAX          Unsigned32
        MAX-ACCESS      read-only
        STATUS          current
        DESCRIPTION
            "This object indicates the identifier of process, namely task ID
            in system."
    ::= { unisProcessEntry 1 }

    unisProcessName OBJECT-TYPE
        SYNTAX          DisplayString(SIZE(1..32))
        MAX-ACCESS      read-only
        STATUS          current
        DESCRIPTION
            "This object indicates the process name."
    ::= { unisProcessEntry 2 }

    unisProcessUtil5Min OBJECT-TYPE
        SYNTAX          Unsigned32(0..100)
        MAX-ACCESS      read-only
        STATUS          current
        DESCRIPTION
            "This object provides a general idea of how busy a process caused
            the processor to be over a 5 minute period.  The ratio is calculated
            by the overall CPU usage caused by the process."
    ::= { unisProcessEntry 3 }

    unisEntityExtVoltageObjects OBJECT IDENTIFIER ::= { unisEntityExtObjects 5 }

    unisEntityExtVoltageTable OBJECT-TYPE
        SYNTAX SEQUENCE OF UnisEntityExtVoltageEntry
        MAX-ACCESS not-accessible
        STATUS current
        DESCRIPTION
            "The table describes the voltage information of the voltage sensor
            entities on the device."
        ::= { unisEntityExtVoltageObjects 1 }

    unisEntityExtVoltageEntry OBJECT-TYPE
        SYNTAX UnisEntityExtVoltageEntry
        MAX-ACCESS not-accessible
        STATUS current
        DESCRIPTION
            "The voltage information of the voltage sensor entity."
        INDEX { unisEntityExtPhysicalIndex }
        ::= { unisEntityExtVoltageTable 1 }

    UnisEntityExtVoltageEntry ::= SEQUENCE {
        unisEntityExtCurrentVoltage
            Integer32,
        unisEntityExtNominalVoltage
            Integer32,
        unisEntityExtVoltageState
            INTEGER,
        unisEntityExtVoltageMajorLowThreshold
            Integer32,
        unisEntityExtVoltageFatalLowThreshold
            Integer32,
        unisEntityExtVoltageMajorHighThreshold
            Integer32,
        unisEntityExtVoltageFatalHighThreshold
            Integer32
     }

    unisEntityExtCurrentVoltage OBJECT-TYPE
        SYNTAX          Integer32
        MAX-ACCESS      read-only
        STATUS          current
        DESCRIPTION
            "The current voltage in millivolts of the voltage
            sensor entity."
    ::= { unisEntityExtVoltageEntry 1 }

    unisEntityExtNominalVoltage OBJECT-TYPE
        SYNTAX          Integer32
        MAX-ACCESS      read-only
        STATUS          current
        DESCRIPTION
            "The nominal voltage in millivolts of the voltage
            sensor entity."
    ::= { unisEntityExtVoltageEntry 2 }

    unisEntityExtVoltageState OBJECT-TYPE
        SYNTAX          INTEGER
        {
             normal   (0),
             low      (1),
             tooLow  (2),
             high     (3),
             tooHigh (4)
        }
        MAX-ACCESS      read-only
        STATUS          current
        DESCRIPTION
            "The voltage state of the voltage sensor entity."
    ::= { unisEntityExtVoltageEntry 3 }

    unisEntityExtVoltageMajorLowThreshold OBJECT-TYPE
        SYNTAX          Integer32
        MAX-ACCESS      read-only
        STATUS          current
        DESCRIPTION
            "The low threshold for the voltage sensor entity.

            When the voltage is lower than the threshold, a notification
            will be sent."
    ::= { unisEntityExtVoltageEntry 4 }

    unisEntityExtVoltageFatalLowThreshold OBJECT-TYPE
        SYNTAX          Integer32
        MAX-ACCESS      read-only
        STATUS          current
        DESCRIPTION
            "The fatal low voltage threshold for the voltage sensor entity.

            When the voltage is lower than the threshold, a notification
            will be sent."
    ::= { unisEntityExtVoltageEntry 5 }

    unisEntityExtVoltageMajorHighThreshold OBJECT-TYPE
        SYNTAX          Integer32
        MAX-ACCESS      read-only
        STATUS          current
        DESCRIPTION
            "The high threshold for the voltage sensor entity.

            When the voltage is higher than the threshold, a notification
            will be sent."
    ::= { unisEntityExtVoltageEntry 6 }

    unisEntityExtVoltageFatalHighThreshold OBJECT-TYPE
        SYNTAX          Integer32
        MAX-ACCESS      read-only
        STATUS          current
        DESCRIPTION
            "The fatal high threshold for the voltage sensor entity.

            When the voltage is higher than the threshold, a notification
            will be sent."
    ::= { unisEntityExtVoltageEntry 7 }

-- End

    unisEntityExtTraps OBJECT IDENTIFIER ::= { unisEntityExtend 2 }

    unisEntityExtTrapsPrefix OBJECT IDENTIFIER ::= { unisEntityExtTraps 0 }
    unisEntityExtTrapsInfor OBJECT IDENTIFIER ::= { unisEntityExtTraps 1 }

    unisEntityExtTemperatureThresholdNotification NOTIFICATION-TYPE
        OBJECTS {
            unisEntityExtPhysicalIndex,
            unisEntityExtTemperature,
            unisEntityExtTemperatureThreshold,
            unisEntityExtAdminStatus,
            unisEntityExtAlarmLight
            }
        STATUS current
        DESCRIPTION
            "The unisEntityExtTemperatureThresholdNotification
            indicates the temperature exceeded the threshold.
            In this condition, user should check the status and the
            environment of the entity, sometimes it happens because
            of the failure of air-condition."
        ::= { unisEntityExtTrapsPrefix 1 }

    unisEntityExtVoltageLowThresholdNotification NOTIFICATION-TYPE
        OBJECTS {
            unisEntityExtPhysicalIndex,
            unisEntityExtVoltage,
            unisEntityExtVoltageLowThreshold,
            unisEntityExtAdminStatus,
            unisEntityExtAlarmLight
            }
        STATUS current
        DESCRIPTION
            "The unisEntityExtVoltageLowThresholdNotification indicates
            the voltage is lower than the threshold.

            If the voltage is lower too much than the entity needs,
            the entity will halt."
        ::= { unisEntityExtTrapsPrefix 2 }

    unisEntityExtVoltageHighThresholdNotification NOTIFICATION-TYPE
        OBJECTS {
            unisEntityExtPhysicalIndex,
            unisEntityExtVoltage,
            unisEntityExtVoltageHighThreshold,
            unisEntityExtAdminStatus,
            unisEntityExtAlarmLight
            }
        STATUS current
        DESCRIPTION
            "The unisEntityExtVoltageHighThresholdNotification indicates
            the voltage is higher than the threshold.

            If the voltage is higher too much than the entity needs,
            The entity may be damaged by the high voltage."
        ::= { unisEntityExtTrapsPrefix 3 }

    unisEntityExtCpuUsageThresholdNotfication NOTIFICATION-TYPE
        OBJECTS {
            unisEntityExtPhysicalIndex,
            unisEntityExtCpuUsage,
            unisEntityExtCpuUsageThreshold,
            unisEntityExtAdminStatus,
            unisEntityExtAlarmLight,
            unisEntityExtCpuUsageRecoverThreshold,
            unisEntityExtFirstTrapTime
            }
        STATUS current
        DESCRIPTION
            "The unisEntityExtCpuUsageThresholdNotfication indicates
            the entity is overloaded."
        ::= { unisEntityExtTrapsPrefix 4 }

    unisEntityExtMemUsageThresholdNotification NOTIFICATION-TYPE
        OBJECTS {
            unisEntityExtPhysicalIndex,
            unisEntityExtMemUsage,
            unisEntityExtMemUsageThreshold,
            unisEntityExtMemSize,
            unisEntityExtAdminStatus,
            unisEntityExtAlarmLight,
            unisEntityExtFirstTrapTime
            }
        STATUS current
        DESCRIPTION
            "The unisEntityExtMemUsageThresholdNotification indicates
            the entity is overloaded."
        ::= { unisEntityExtTrapsPrefix 5 }

    unisEntityExtOperEnabled NOTIFICATION-TYPE
        OBJECTS {
            unisEntityExtPhysicalIndex,
            unisEntityExtAdminStatus,
            unisEntityExtAlarmLight
            }
        STATUS current
        DESCRIPTION
            "The trap indicates the entity is operable at present."
        ::= { unisEntityExtTrapsPrefix 6 }

    unisEntityExtOperDisabled NOTIFICATION-TYPE
        OBJECTS {
            unisEntityExtPhysicalIndex,
            unisEntityExtAdminStatus,
            unisEntityExtAlarmLight
            }
        STATUS current
        DESCRIPTION
            "The trap indicates the entity is not operable at present."
        ::= { unisEntityExtTrapsPrefix 7 }

    unisEntityExtCriticalTemperatureThresholdNotification NOTIFICATION-TYPE
        OBJECTS {
            unisEntityExtPhysicalIndex,
            unisEntityExtTemperature,
            unisEntityExtCriticalTemperatureThreshold,
            unisEntityExtAdminStatus,
            unisEntityExtAlarmLight
            }
        STATUS current
        DESCRIPTION
            "The unisEntityExtCriticalTemperatureThresholdNotification
            indicates the temperature exceeds the critical temperature.
            In this condition, user should check the status and the
            environment of the entity, sometimes it happens because
            of the failure of air-condition."
        ::= { unisEntityExtTrapsPrefix 8 }

    unisEntityExtSFPAlarmOn NOTIFICATION-TYPE
        OBJECTS {
            unisEntityExtPhysicalIndex,
            unisEntityExtErrorStatus,
            unisEntityExtAdminStatus,
            unisEntityExtAlarmLight
            }
        STATUS current
        DESCRIPTION
            "The trap is generated when the SFP module fails
            or runs abnormally for some particular reason."
        ::= { unisEntityExtTrapsPrefix 9 }

    unisEntityExtSFPAlarmOff NOTIFICATION-TYPE
        OBJECTS {
            unisEntityExtPhysicalIndex,
            unisEntityExtErrorStatus,
            unisEntityExtAdminStatus,
            unisEntityExtAlarmLight
            }
        STATUS current
        DESCRIPTION
            "The trap is generated when the SFP module restores to
            normal status."
        ::= { unisEntityExtTrapsPrefix 10 }

    unisEntityExtSFPPhony NOTIFICATION-TYPE
        OBJECTS {
            unisEntityExtPhysicalIndex,
            entPhysicalName,
            unisEntityExtAdminStatus,
            unisEntityExtAlarmLight
            }
        STATUS current
        DESCRIPTION
            "This module is NOT sold by authorized manufacturer.
            The normal function of the device or assume the maintenance
            responsibility thereof will NOT be guaranteed.
            The trap is generated periodically after a phony module has been
            found."
        ::= { unisEntityExtTrapsPrefix 11 }

    unisEntityInsert NOTIFICATION-TYPE
        OBJECTS { entPhysicalDescr, unisEntityExtAdminStatus, unisEntityExtOperStatus }
        STATUS current
        DESCRIPTION
            "The trap is generated when a removable entity inserting to
            device."
        ::= { unisEntityExtTrapsPrefix 12 }

    unisEntityRemove NOTIFICATION-TYPE
        OBJECTS { entPhysicalDescr, unisEntityExtAdminStatus, unisEntityExtOperStatus }
        STATUS current
        DESCRIPTION
            "The trap is generated when a removable entity removing from
            device."
        ::= { unisEntityExtTrapsPrefix 13 }

    unisEntityExtForcedPowerOff NOTIFICATION-TYPE
        OBJECTS {
            unisEntityExtPhysicalIndex,
            entPhysicalName,
            unisEntityExtAdminStatus,
            unisEntityExtAlarmLight
            }
        STATUS current
        DESCRIPTION
            "The trap indicates the entity is forced to power off."
        ::= { unisEntityExtTrapsPrefix 14 }

    unisEntityExtForcedPowerOn NOTIFICATION-TYPE
        OBJECTS {
            unisEntityExtPhysicalIndex,
            entPhysicalName,
            unisEntityExtAdminStatus,
            unisEntityExtAlarmLight
            }
        STATUS current
        DESCRIPTION
            "The trap indicates the entity is forced to power on."
        ::= { unisEntityExtTrapsPrefix 15 }

    unisEntityExtFaultAlarmOn NOTIFICATION-TYPE
        OBJECTS {
            unisEntityExtPhysicalIndex,
            entPhysicalName,
            unisEntityExtErrorStatus,
            unisEntityExtAdminStatus,
            unisEntityExtAlarmLight
            }
        STATUS current
        DESCRIPTION
            "The trap indicates a fault occurs on the specified entity."
        ::= { unisEntityExtTrapsPrefix 16 }

    unisEntityExtFaultAlarmOff NOTIFICATION-TYPE
        OBJECTS {
            unisEntityExtPhysicalIndex,
            entPhysicalName,
            unisEntityExtErrorStatus,
            unisEntityExtAdminStatus,
            unisEntityExtAlarmLight
            }
        STATUS current
        DESCRIPTION
            "The trap indicates a fault disappears on the specified entity."
        ::= { unisEntityExtTrapsPrefix 17 }

    unisEntityExtResourceLack NOTIFICATION-TYPE
        OBJECTS {
            unisEntityExtPhysicalIndex,
            entPhysicalName
            }
        STATUS current
        DESCRIPTION
            "The trap indicates that a kind of resource is not enough on the
            specified entity."
        ::= { unisEntityExtTrapsPrefix 18 }

    unisEntityExtResourceEnough NOTIFICATION-TYPE
        OBJECTS {
            unisEntityExtPhysicalIndex,
            entPhysicalName
            }
        STATUS current
        DESCRIPTION
            "The trap indicates that the entity recovers from the status of no
            enough resource."
        ::= { unisEntityExtTrapsPrefix 19 }

    unisEntityExtTemperatureLower NOTIFICATION-TYPE
        OBJECTS {
            unisEntityExtPhysicalIndex,
            entPhysicalName,
            unisEntityExtTemperature,
            unisEntityExtLowerTemperatureThreshold,
            unisEntityExtAdminStatus
            }
        STATUS current
        DESCRIPTION
            "The trap indicates the temperature of a specified entity is under
            the lower threshold. In this condition, user should check the
            status and the environment of the entity, sometimes it goes wrong
            for some reason."
        ::= { unisEntityExtTrapsPrefix 20 }

    unisEntityExtTemperatureTooUp NOTIFICATION-TYPE
        OBJECTS {
            unisEntityExtPhysicalIndex,
            entPhysicalName,
            unisEntityExtTemperature,
            unisEntityExtShutdownTemperatureThreshold,
            unisEntityExtAdminStatus
            }
        STATUS current
        DESCRIPTION
            "The trap indicates the temperature of a specified entity exceeded
            the shutdown threshold. In this condition, user should check the
            status and the environment of the entity, sometimes it goes wrong
            for some reason."
        ::= { unisEntityExtTrapsPrefix 21 }

    unisEntityExtTemperatureNormal NOTIFICATION-TYPE
        OBJECTS {
            unisEntityExtPhysicalIndex,
            entPhysicalName,
            unisEntityExtTemperature,
            unisEntityExtLowerTemperatureThreshold,
            unisEntityExtTemperatureThreshold,
            unisEntityExtAdminStatus
            }
        STATUS current
        DESCRIPTION
            "The trap indicates the temperature of a specified entity recover
            from abnormal status."
        ::= { unisEntityExtTrapsPrefix 22 }

    unisEntityExternalAlarmOccur NOTIFICATION-TYPE
        OBJECTS {
            unisEntityExtPhysicalIndex,
            entPhysicalName
            }
        STATUS current
        DESCRIPTION
            "The trap is generated when the monitored device connected to the
             specified entity fails."
        ::= { unisEntityExtTrapsPrefix 23 }

    unisEntityExternalAlarmRecover NOTIFICATION-TYPE
        OBJECTS {
            unisEntityExtPhysicalIndex,
            entPhysicalName
            }
        STATUS current
        DESCRIPTION
            "The trap is generated when the failed device connected to the
             specified entity returns to normal."
        ::= { unisEntityExtTrapsPrefix 24 }

    unisEntityExtCpuUsageThresholdRecover NOTIFICATION-TYPE
        OBJECTS {
            unisEntityExtPhysicalIndex,
            unisEntityExtCpuUsage,
            unisEntityExtCpuUsageThreshold,
            unisEntityExtAdminStatus,
            unisEntityExtAlarmLight,
            unisEntityExtCpuUsageRecoverThreshold,
            unisEntityExtFirstTrapTime
            }
        STATUS current
        DESCRIPTION
            "The trap indicates the CPU usage descends the threshold."
        ::= { unisEntityExtTrapsPrefix 25 }

    unisEntityExtMemUsageThresholdRecover NOTIFICATION-TYPE
        OBJECTS {
            unisEntityExtPhysicalIndex,
            unisEntityExtMemUsage,
            unisEntityExtMemUsageThreshold,
            unisEntityExtMemSize,
            unisEntityExtAdminStatus,
            unisEntityExtAlarmLight,
            unisEntityExtFirstTrapTime
            }
        STATUS current
        DESCRIPTION
            "The trap indicates the memory usage descends the threshold."
        ::= { unisEntityExtTrapsPrefix 26 }

    unisEntityExtMemAllocatedFailed NOTIFICATION-TYPE
        OBJECTS {
            unisEntityExtPhysicalIndex,
            unisEntityExtTrapDescription
            }
        STATUS current
        DESCRIPTION
            "The trap indicates the memory allocated failed."
        ::= { unisEntityExtTrapsPrefix 27 }

    unisEntityExtECCParityAlarm NOTIFICATION-TYPE
        OBJECTS {
            unisEntityExtPhysicalIndex,
            unisEntityExtECCParityAlarmStatus,
            unisEntityExtTrapDescription
            }
        STATUS current
        DESCRIPTION
            "The trap indicates the ECC(Error Correction Code) parity error alarm."
        ::= { unisEntityExtTrapsPrefix 28 }

    unisEntityExtCritLowerTempThresholdNotification NOTIFICATION-TYPE
        OBJECTS {
            unisEntityExtPhysicalIndex,
            entPhysicalName,
            unisEntityExtTemperature,
            unisEntityExtCriticalLowerTemperatureThreshold
            }
        STATUS current
        DESCRIPTION
            "The unisEntityExtCritLowerTempThresholdNotification
            indicates the temperature is lower than the threshold.

            If the temperature is lower too much than the entity needs,
            the entity will halt."
        ::= { unisEntityExtTrapsPrefix 29 }

    unisEntityExtTemperatureTooLow NOTIFICATION-TYPE
        OBJECTS {
            unisEntityExtPhysicalIndex,
            entPhysicalName,
            unisEntityExtTemperature,
            unisEntityExtShutdownLowerTemperatureThreshold
            }
        STATUS current
        DESCRIPTION
            "The unisEntityExtTemperatureTooLow indicates the temperature
            is lower than the threshold.

            If the temperature is lower too much than the entity needs,
            the entity halts now."
        ::= { unisEntityExtTrapsPrefix 30 }

    unisEntityExtFanDirectionNotPreferred NOTIFICATION-TYPE
        OBJECTS {
            unisEntityExtPhysicalIndex,
            entPhysicalName
            }
        STATUS current
        DESCRIPTION
            "This trap indicates the specified fan's direction does not
            accord with preferred. The two parameters indicate the entity
            index and physical name of fan."
        ::= { unisEntityExtTrapsPrefix 31 }

    unisEntityExtFanDirectionNotAccord NOTIFICATION-TYPE
        OBJECTS {
            unisEntityExtPhysicalIndex,
            entPhysicalName
            }
        STATUS current
        DESCRIPTION
            "This trap indicates the direction of fans does not accord
            with each other. The two parameters indicate the parent
            entity of the fans."
        ::= { unisEntityExtTrapsPrefix 32 }

    unisEntityExtSFPInvalid NOTIFICATION-TYPE
        OBJECTS {
            unisEntityExtPhysicalIndex,
            entPhysicalName,
            unisEntityExtSFPInvalidInDays
            }
        STATUS current
        DESCRIPTION
            "The transceiver module is not compatible with the interface card.
            The authorized manufacturer therefore shall NOT guarantee
            the normal function of the transceiver.
            The transceiver module will be invalidated in days.
            Please replace it with a compatible one as soon as possible.
            The trap is generated periodically after a phony transceiver module
            has been found."
        ::= { unisEntityExtTrapsPrefix 33 }

    unisEntityExtSFPInvalidNow NOTIFICATION-TYPE
        OBJECTS {
            unisEntityExtPhysicalIndex,
            entPhysicalName
            }
        STATUS current
        DESCRIPTION
            "This transceiver module is not compatible with the interface card.
            The authorized manufacturer therefore shall NOT guarantee
            the normal function of the transceiver.
            The trap is generated after a phony transceiver module
            has been found."
        ::= { unisEntityExtTrapsPrefix 34 }

    unisEntityExtMemUsageThresholdOverTrap NOTIFICATION-TYPE
        OBJECTS {
            unisEntityExtPhysicalIndex,
            unisEntityExtMemUsage,
            unisEntityExtMemUsageThreshold,
            unisEntityExtMemSizeRev,
            unisEntityExtAdminStatus,
            unisEntityExtAlarmLight
            }
        STATUS current
        DESCRIPTION
            "This trap indicates that the memory usage of the entity is
            overloaded.

            This trap is used to replace
            unisEntityExtMemUsageThresholdNotification."
        ::= { unisEntityExtTrapsPrefix 35 }

    unisEntityExtMemUsageThresholdRecoverTrap NOTIFICATION-TYPE
        OBJECTS {
            unisEntityExtPhysicalIndex,
            unisEntityExtMemUsage,
            unisEntityExtMemUsageThreshold,
            unisEntityExtMemSizeRev,
            unisEntityExtAdminStatus,
            unisEntityExtAlarmLight
            }
        STATUS current
        DESCRIPTION
            "This trap indicates that the memory usage decreased below
            the threshold.

            This trap is used to replace
            unisEntityExtMemUsageThresholdRecover."
        ::= { unisEntityExtTrapsPrefix 36 }

    unisEntityExtVoltageNormal NOTIFICATION-TYPE
        OBJECTS {
            unisEntityExtPhysicalIndex,
            unisEntityExtCurrentVoltage,
            unisEntityExtNominalVoltage,
            unisEntityExtVoltageMajorLowThreshold,
            unisEntityExtVoltageMajorHighThreshold
            }
        STATUS current
        DESCRIPTION
            "This trap indicates that the voltage recovers to normal."
        ::= { unisEntityExtTrapsPrefix 37 }

    unisEntityExtVoltageLower NOTIFICATION-TYPE
        OBJECTS {
            unisEntityExtPhysicalIndex,
            unisEntityExtCurrentVoltage,
            unisEntityExtNominalVoltage,
            unisEntityExtVoltageMajorLowThreshold
            }
        STATUS current
        DESCRIPTION
            "This trap indicates that the voltage is lower than the
            low threshold."
        ::= { unisEntityExtTrapsPrefix 38 }

    unisEntityExtVoltageTooLow NOTIFICATION-TYPE
        OBJECTS {
            unisEntityExtPhysicalIndex,
            unisEntityExtCurrentVoltage,
            unisEntityExtNominalVoltage,
            unisEntityExtVoltageFatalLowThreshold
            }
        STATUS current
        DESCRIPTION
            "This trap indicates that the voltage is lower than the
            fatal low threshold."
        ::= { unisEntityExtTrapsPrefix 39 }

    unisEntityExtVoltageHigher NOTIFICATION-TYPE
        OBJECTS {
            unisEntityExtPhysicalIndex,
            unisEntityExtCurrentVoltage,
            unisEntityExtNominalVoltage,
            unisEntityExtVoltageMajorHighThreshold
            }
        STATUS current
        DESCRIPTION
            "This trap indicates that the voltage is higher than the
            high threshold."
        ::= { unisEntityExtTrapsPrefix 40 }

    unisEntityExtVoltageTooHigh NOTIFICATION-TYPE
        OBJECTS {
            unisEntityExtPhysicalIndex,
            unisEntityExtCurrentVoltage,
            unisEntityExtNominalVoltage,
            unisEntityExtVoltageFatalHighThreshold
            }
        STATUS current
        DESCRIPTION
            "This trap indicates that the voltage is higher than the
            fatal high threshold."
        ::= { unisEntityExtTrapsPrefix 41 }

    unisEntityExtSFPAlarmOnEx NOTIFICATION-TYPE
        OBJECTS {
            unisEntityExtPhysicalIndex,
            entPhysicalName,
            unisEntityExtAdminStatus,
            unisEntityExtAlarmLight,
            unisEntityExtErrorStatus
            }
        STATUS current
        DESCRIPTION
            "The trap is generated when the SFP module fails
            or runs abnormally for some particular reason.
            This trap is used to replace unisEntityExtSFPAlarmOn."
        ::= { unisEntityExtTrapsPrefix 42 }

    unisEntityExtSFPAlarmOffEx NOTIFICATION-TYPE
        OBJECTS {
            unisEntityExtPhysicalIndex,
            entPhysicalName,
            unisEntityExtAdminStatus,
            unisEntityExtAlarmLight,
            unisEntityExtErrorStatus
            }
        STATUS current
        DESCRIPTION
            "The trap is generated when the SFP module is restored to
            normal status.
            This trap is used to replace unisEntityExtSFPAlarmOff."
        ::= { unisEntityExtTrapsPrefix 43 }

    unisEntityExtTrapDescription OBJECT-TYPE
        SYNTAX      SnmpAdminString (SIZE (0..255))
        MAX-ACCESS  accessible-for-notify
        STATUS      current
        DESCRIPTION
            "The information of trap."
        ::= { unisEntityExtTrapsInfor 1 }

    unisEntityExtECCParityAlarmStatus OBJECT-TYPE
        SYNTAX  INTEGER {
                         other(1),
                         l1cache(2),       -- cpu l1 data cache err
                         l2cache(3),       -- cpu l2 data cache err
                         sdram(4),         -- sdram err for cpu
                         mac(5),           -- mac err
                         tcam(6),          -- tcam err
                         ingressbuffer(7), -- IB err
                         egressbuffer(8),  -- EB err
                         lpm(9),           -- lpm err
                         controlmemory(10) -- controlmemory err
                        }
        MAX-ACCESS  accessible-for-notify
        STATUS      current
        DESCRIPTION
               "ECC parity error."
        ::= { unisEntityExtTrapsInfor 2 }

    unisEntityExtSFPInvalidInDays OBJECT-TYPE
        SYNTAX      Integer32
        MAX-ACCESS  accessible-for-notify
        STATUS      current
        DESCRIPTION
            "The days when the transceiver module is still valid,
            but after those days, it will be invalidated."
        ::= { unisEntityExtTrapsInfor 3 }

    unisEntityExtFirstTrapTime OBJECT-TYPE
        SYNTAX      TimeTicks
        MAX-ACCESS  accessible-for-notify
        STATUS      current
        DESCRIPTION
            "Represents the first trap time."
        ::= { unisEntityExtTrapsInfor 4 }

--  Conformance and Compliance
    unisEntityExtConformance OBJECT IDENTIFIER ::= { unisEntityExtend 3 }

    unisEntityExtCompliances OBJECT IDENTIFIER ::= { unisEntityExtConformance 1 }

--  this module
    unisEntityExtCompliance MODULE-COMPLIANCE
        STATUS current
        DESCRIPTION
            "The compliance statement for systems supporting this MIB."
        MODULE -- this module
            MANDATORY-GROUPS { unisEntityExtGroup, unisEntityExtNotificationGroup,
                               unisEntityExtManuGroup, unisEntityExtPowerGroup }
            OBJECT unisEntityExtAdminStatus
                MIN-ACCESS read-only
                DESCRIPTION
                    "Write access is not required."
            OBJECT unisEntityExtCpuUsageThreshold
                MIN-ACCESS read-only
                DESCRIPTION
                    "Write access is not required."
            OBJECT unisEntityExtMemUsageThreshold
                MIN-ACCESS read-only
                DESCRIPTION
                    "Write access is not required."
            OBJECT unisEntityExtTemperatureThreshold
                MIN-ACCESS read-only
                DESCRIPTION
                    "Write access is not required."
            OBJECT unisEntityExtVoltageLowThreshold
                MIN-ACCESS read-only
                DESCRIPTION
                    "Write access is not required."
            OBJECT unisEntityExtVoltageHighThreshold
                MIN-ACCESS read-only
                DESCRIPTION
                    "Write access is not required."
        ::= { unisEntityExtCompliances 1 }

    unisEntityExtGroups OBJECT IDENTIFIER ::= { unisEntityExtConformance 2 }

    unisEntityExtGroup OBJECT-GROUP
        OBJECTS {
            unisEntityExtPhysicalIndex,
            unisEntityExtAdminStatus,
            unisEntityExtOperStatus,
            unisEntityExtStandbyStatus,
            unisEntityExtAlarmLight,
            unisEntityExtCpuUsage,
            unisEntityExtCpuUsageThreshold,
            unisEntityExtMemUsage,
            unisEntityExtMemUsageThreshold,
            unisEntityExtMemSize,
            unisEntityExtUpTime,
            unisEntityExtTemperature,
            unisEntityExtTemperatureThreshold,
            unisEntityExtVoltage,
            unisEntityExtVoltageLowThreshold,
            unisEntityExtVoltageHighThreshold,
            unisEntityExtCriticalTemperatureThreshold,
            unisEntityExtMacAddress,
            unisEntityExtErrorStatus,
            unisEntityExtCpuMaxUsage,
            unisEntityExtLowerTemperatureThreshold,
            unisEntityExtShutdownTemperatureThreshold,
            unisEntityExtPhyMemSize,
            unisEntityExtPhyCpuFrequency,
            unisEntityExtFirstUsedDate,
            unisEntityExtCpuAvgUsage,
            unisEntityExtMemAvgUsage,
            unisEntityExtMemType,
            unisEntityExtCriticalLowerTemperatureThreshold,
            unisEntityExtShutdownLowerTemperatureThreshold,
            unisEntityExtCpuUsageRecoverThreshold,
            unisEntityExtMemSizeRev,
            unisEntityExtCpuUsageIn1Minute,
            unisEntityExtCpuUsageIn5Minutes
            }
        STATUS current
        DESCRIPTION
            "Entity Extend group."
        ::= { unisEntityExtGroups 1 }

    unisEntityExtNotificationGroup NOTIFICATION-GROUP
        NOTIFICATIONS { unisEntityExtTemperatureThresholdNotification,
                unisEntityExtVoltageLowThresholdNotification,
                unisEntityExtVoltageHighThresholdNotification,
                unisEntityExtCpuUsageThresholdNotfication,
                unisEntityExtMemUsageThresholdNotification,
                unisEntityExtOperEnabled,
                unisEntityExtOperDisabled,
                unisEntityExtCriticalTemperatureThresholdNotification,
                unisEntityExtSFPAlarmOn,
                unisEntityExtSFPAlarmOff,
                unisEntityExtSFPPhony,
                unisEntityInsert,
                unisEntityRemove,
                unisEntityExtForcedPowerOff,
                unisEntityExtForcedPowerOn,
                unisEntityExtFaultAlarmOn,
                unisEntityExtFaultAlarmOff,
                unisEntityExtResourceLack,
                unisEntityExtResourceEnough,
                unisEntityExtTemperatureLower,
                unisEntityExtTemperatureTooUp,
                unisEntityExtTemperatureNormal,
                unisEntityExternalAlarmOccur,
                unisEntityExternalAlarmRecover,
                unisEntityExtCpuUsageThresholdRecover,
                unisEntityExtMemUsageThresholdRecover,
                unisEntityExtMemAllocatedFailed,
                unisEntityExtECCParityAlarm,
                unisEntityExtCritLowerTempThresholdNotification,
                unisEntityExtTemperatureTooLow,
                unisEntityExtFanDirectionNotPreferred,
                unisEntityExtFanDirectionNotAccord,
                unisEntityExtSFPInvalid,
                unisEntityExtSFPInvalidNow,
                unisEntityExtMemUsageThresholdOverTrap,
                unisEntityExtMemUsageThresholdRecoverTrap,
                unisEntityExtVoltageNormal,
                unisEntityExtVoltageTooLow,
                unisEntityExtVoltageLower,
                unisEntityExtVoltageHigher,
                unisEntityExtVoltageTooHigh,
                unisEntityExtSFPAlarmOnEx,
                unisEntityExtSFPAlarmOffEx
                }
        STATUS current
        DESCRIPTION
            "Entity Extend Notification group."
            ::= { unisEntityExtGroups 2 }

    unisEntityExtManuGroup OBJECT-GROUP
        OBJECTS {
            unisEntityExtManuPhysicalIndex,
            unisEntityExtManuSerialNum,
            unisEntityExtManuBuildInfo,
            unisEntityExtManuBOM,
            unisEntityExtMacAddressCount
            }
        STATUS current
        DESCRIPTION
            "Standard Device Manufacture Information group."
        ::= { unisEntityExtGroups 3 }

    unisEntityExtPowerGroup OBJECT-GROUP
        OBJECTS {
            unisEntityExtPowerPhysicalIndex,
            unisEntityExtNominalPower,
            unisEntityExtCurrentPower,
            unisEntityExtAveragePower,
            unisEntityExtPeakPower
            }
        STATUS current
        DESCRIPTION
            "Standard Entity Power Information group."
        ::= { unisEntityExtGroups 4 }

    END
