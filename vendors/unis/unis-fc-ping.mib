-- =====================================================================
-- Copyright (c) 2020 Unisyue Technologies Co., Ltd.  All rights reserved.
--
-- Description:
--      This MIB module is for the management of the Fibre Channel
--      Ping functionality.
-- Reference:
-- Version: V1.0
-- History:
--      V1.0 Initial version created by liuyanchao 2013-03-15
-- =====================================================================
UNIS-FC-PING-MIB DEFINITIONS ::= BEGIN

IMPORTS
    MODULE-IDENTITY, OBJECT-TYPE, NOTIFICATION-TYPE, Unsigned32, Integer32
        FROM SNMPv2-SMI
    RowStatus, TruthValue
        FROM SNMPv2-TC
    UnisFcVsanIndex, UnisFcAddressType, UnisFcAddress,
    UnisFcStartOper
        FROM UNIS-FC-TC-MIB
    unisSan
        FROM UNIS-VSAN-MIB;


unisFcPing  MODULE-IDENTITY
    LAST-UPDATED "201303150000Z"
    ORGANIZATION
        "Unisyue Technologies Co., Ltd."
    CONTACT-INFO
        ""
    DESCRIPTION
        "This MIB module is for the management of the Fibre Channel
         Ping functionality."
    REVISION "201303150000Z"
    DESCRIPTION
        "Initial version of this MIB module."
    ::= { unisSan 5 }

unisFcPingObjects             OBJECT IDENTIFIER
    ::= { unisFcPing 1 }
unisFcPingConfigurations      OBJECT IDENTIFIER
    ::= { unisFcPingObjects 1 }
unisFcPingStatistics          OBJECT IDENTIFIER
    ::= { unisFcPingObjects 2 }
unisFcPingNotifications       OBJECT IDENTIFIER
    ::= { unisFcPingObjects 3 }
unisFcPingNotifyPrefix        OBJECT IDENTIFIER
    ::= { unisFcPingNotifications 0 }

-- FC Ping table

unisFcPingTable OBJECT-TYPE
    SYNTAX        SEQUENCE OF UnisFcPingEntry
    MAX-ACCESS    not-accessible
    STATUS        current
    DESCRIPTION
        "A table of FC ping entries containing a group of
         FC ping requests that need to be executed at the
         agent."
    ::= { unisFcPingConfigurations 1 }

unisFcPingEntry OBJECT-TYPE
    SYNTAX        UnisFcPingEntry
    MAX-ACCESS    not-accessible
    STATUS        current
    DESCRIPTION
        "A FC ping request entry that need to be executed
         at the agent."
    INDEX         { unisFcPingIndex }
    ::= { unisFcPingTable 1 }

UnisFcPingEntry ::= SEQUENCE {
    unisFcPingIndex              Unsigned32,
    unisFcPingVsan               UnisFcVsanIndex,
    unisFcPingAddressType        UnisFcAddressType,
    unisFcPingAddress            UnisFcAddress,
    unisFcPingPacketCount        Unsigned32,
    unisFcPingPayloadSize        Unsigned32,
    unisFcPingTimeout            Unsigned32,
    unisFcPingDelay              Unsigned32,
    unisFcPingAgeInterval        Unsigned32,
    unisFcPingAdminStatus        UnisFcStartOper,
    unisFcPingOperStatus         INTEGER,
    unisFcPingTrapOnCompletion   TruthValue,
    unisFcPingRowStatus          RowStatus
}

unisFcPingIndex OBJECT-TYPE
    SYNTAX        Unsigned32 (1..65535)
    MAX-ACCESS    accessible-for-notify
    STATUS        current
    DESCRIPTION
        "The index of the current FC ping entry.  This object
         identifies a FC ping request entry uniquely in a
         specified VSAN (Virtual Storage Area Network)."
    ::= { unisFcPingEntry 1 }

unisFcPingVsan OBJECT-TYPE
    SYNTAX        UnisFcVsanIndex
    MAX-ACCESS    read-create
    STATUS        current
    DESCRIPTION
        "The VSAN on which the FC ping request will be
         performed.  If the corresponding instance value of
         unisFcPingOperStatus is 'inProgress', the object
         cannot be modified."
    ::= { unisFcPingEntry 2 }

unisFcPingAddressType OBJECT-TYPE
    SYNTAX        UnisFcAddressType
    MAX-ACCESS    read-create
    STATUS        current
    DESCRIPTION
        "The type of the corresponding instance of
         unisFcPingAddress object."
    DEFVAL        { fcid }
    ::= { unisFcPingEntry 3 }

unisFcPingAddress OBJECT-TYPE
    SYNTAX        UnisFcAddress
    MAX-ACCESS    read-create
    STATUS        current
    DESCRIPTION
        "The address to which the route will be pinged.

         This object will contain an 8 octet long WWN(World Wide Name),
         if the value of the associated instance of unisFcPingAddressType
         object is 'wwn'.

         This object will contain a 3 octet long Fibre Channel Address ID,
         if the value of the associated instance of unisFcPingAddressType
         object is 'fcid'."
    ::= { unisFcPingEntry 4 }

unisFcPingPacketCount OBJECT-TYPE
    SYNTAX      Unsigned32 (1..2147483647)
    MAX-ACCESS  read-create
    STATUS      current
    DESCRIPTION
        "The number of FC ping packets to be sent to the
         target in this sequence."
    DEFVAL        { 5 }
    ::= { unisFcPingEntry 5 }

unisFcPingPayloadSize OBJECT-TYPE
    SYNTAX      Unsigned32
    MAX-ACCESS  read-only
    STATUS      current
    DESCRIPTION
        "This object specifies the size of the FC ping packet
         payload to be sent to the target in this sequence."
    ::= { unisFcPingEntry 6 }

unisFcPingTimeout OBJECT-TYPE
    SYNTAX        Unsigned32 (1..10)
    UNITS         "seconds"
    MAX-ACCESS    read-create
    STATUS        current
    DESCRIPTION
        "The value of timeout for this FC ping request."
    DEFVAL        { 5 }
    ::= { unisFcPingEntry 7 }

unisFcPingDelay OBJECT-TYPE
    SYNTAX      Unsigned32
    UNITS       "seconds"
    MAX-ACCESS  read-only
    STATUS      current
    DESCRIPTION
        "The minimum amount of time to wait before sending
         the next packet in a sequence, after receiving a
         response or declaring a timeout for a previously
         transmitted packet."
    ::= { unisFcPingEntry 8 }

unisFcPingAgeInterval OBJECT-TYPE
    SYNTAX        Unsigned32 (500..900)
    UNITS         "seconds"
    MAX-ACCESS    read-create
    STATUS        current
    DESCRIPTION
        "The interval time after a FC ping test completes
         before the entry is aged out."
    DEFVAL        { 500 }
    ::= { unisFcPingEntry 9 }

unisFcPingAdminStatus OBJECT-TYPE
    SYNTAX        UnisFcStartOper
    MAX-ACCESS    read-create
    STATUS        current
    DESCRIPTION
        "The administrative status of each unisFcPingEntry.

         The object has two values:
         enable     -  Activate the entry.
         disable    -  Deactivate the entry.

         When the FC ping entry is executing, this object cannot be
         modified.  If this object is read at such a time, a value of
         'enable' will be returned.  When the test finishes, the value
         of this object will be set to 'disable'."
    DEFVAL        { disable }
    ::= { unisFcPingEntry 10 }

unisFcPingOperStatus OBJECT-TYPE
    SYNTAX        INTEGER {
      inProgress(1),     -- FC ping in progress
      complete(2),       -- FC ping complete
      disabled(3),       -- FC ping disabled
      failed(4)          -- FC ping failed
      }
    MAX-ACCESS    read-only
    STATUS        current
    DESCRIPTION
        "This object indicates the operational status
         of this unisFcPingEntry.

         The value specifications are listed as follows:
         inProgress     - FC ping is in progress.
         complete       - FC ping is complete.
         disabled       - FC ping is disabled.
         failed         - FC ping has failed due to resource limitations."
    ::= { unisFcPingEntry 11 }

unisFcPingTrapOnCompletion OBJECT-TYPE
    SYNTAX        TruthValue
    MAX-ACCESS    read-create
    STATUS        current
    DESCRIPTION
        "This object indicates that if unisFcPingCompletionNotify
         notification should be generated or not when the corresponding
         ping sequence completes."
    DEFVAL        { false }
    ::= { unisFcPingEntry 12 }

unisFcPingRowStatus OBJECT-TYPE
    SYNTAX        RowStatus
    MAX-ACCESS    read-create
    STATUS        current
    DESCRIPTION
        "The status of this conceptual row."
    ::= { unisFcPingEntry 13 }

-- FC Ping Statistics Table

unisFcPingStatTable OBJECT-TYPE
    SYNTAX        SEQUENCE OF UnisFcPingStatEntry
    MAX-ACCESS    not-accessible
    STATUS        current
    DESCRIPTION
        "A table of FC ping statistics.
         This table notes the FC ping statistics of a FC ping test
         associated with an entry in the unisFcPingTable."
    ::= { unisFcPingStatistics 1 }

unisFcPingStatEntry OBJECT-TYPE
    SYNTAX        UnisFcPingStatEntry
    MAX-ACCESS    not-accessible
    STATUS        current
    DESCRIPTION
        "A FC ping statistics entry.

         An entry will be created automatically in this table when the
         unisFcPingRowStatus of a ping request in the unisFcPingTable
         is set to 'active'.

         The entry in this table will have the same indices as the entry
         that in the unisFcPingTable.

         An entry in this table will be deleted when the corresponding
         entry in the unisFcPingTable is deleted."
    INDEX         { unisFcPingIndex }
    ::= { unisFcPingStatTable 1 }

UnisFcPingStatEntry ::= SEQUENCE {
    unisFcPingReqPackets      Unsigned32,
    unisFcPingResPackets      Unsigned32,
    unisFcPingMinTime         Integer32,
    unisFcPingAverageTime     Integer32,
    unisFcPingMaxTime         Integer32,
    unisFcPingTimeoutNum      Unsigned32
}

unisFcPingReqPackets OBJECT-TYPE
    SYNTAX        Unsigned32
    MAX-ACCESS    read-only
    STATUS        current
    DESCRIPTION
        "The number of FC ping packets request in this sequence."
    ::= { unisFcPingStatEntry 1 }

unisFcPingResPackets OBJECT-TYPE
    SYNTAX        Unsigned32
    MAX-ACCESS    read-only
    STATUS        current
    DESCRIPTION
        "The number of FC ping packets response in this sequence."
    ::= { unisFcPingStatEntry 2 }

unisFcPingMinTime OBJECT-TYPE
    SYNTAX        Integer32
    UNITS         "microseconds"
    MAX-ACCESS    read-only
    STATUS        current
    DESCRIPTION
        "The minimum round trip time of all the packets that
         have been sent in this sequence."
    ::= { unisFcPingStatEntry 3 }

unisFcPingAverageTime OBJECT-TYPE
    SYNTAX        Integer32
    UNITS         "microseconds"
    MAX-ACCESS    read-only
    STATUS        current
    DESCRIPTION
        "The average round trip time of all the packets that
         have been sent in this sequence."
    ::= { unisFcPingStatEntry 4 }

unisFcPingMaxTime OBJECT-TYPE
    SYNTAX        Integer32
    UNITS         "microseconds"
    MAX-ACCESS    read-only
    STATUS        current
    DESCRIPTION
        "The maximum round trip time of all the packets that
         have been sent in this sequence."
    ::= { unisFcPingStatEntry 5 }


unisFcPingTimeoutNum OBJECT-TYPE
    SYNTAX        Unsigned32
    MAX-ACCESS    read-only
    STATUS        current
    DESCRIPTION
        "The number of timeouts encountered in this sequence."
    ::= { unisFcPingStatEntry 6 }

-- Notifications

unisFcPingCompletionNotify NOTIFICATION-TYPE
    OBJECTS       { unisFcPingIndex,
                    unisFcPingVsan,
                    unisFcPingAddressType,
                    unisFcPingAddress,
                    unisFcPingReqPackets,
                    unisFcPingResPackets}
    STATUS        current
    DESCRIPTION
        "When a FC ping test is finished and the instance of
         unisFcPingTrapOnCompletion associated with the test
         is set to 'true', this notification occurred."
    ::= { unisFcPingNotifyPrefix 1 }

END
