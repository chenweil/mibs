-- =============================================================================
-- Copyright (c) 2020 Unisyue Technologies Co., Ltd.  All rights reserved.
--
-- Description: The MIB for VSI (Virtual Switch Instance).
-- Reference:
-- Version: V1.7
-- History:
--   V1.0 2009-08-08 Initial version Created by Zhonghua Gao
--   V1.1 2012-11-21 Modified by yanneng, added unisVsiSpbIsid,
--               Value 'default(0)' is added for data type 'unisVsiMode'
--   V1.2 2013-04-27 Modified by raoxiaobing, Value 'minmpxp(6), martiniAndMinmpxp(7)
--               and kompellaAndMinmpxp(8)' is added for data type 'unisVsiMode'
--   V1.3 2013-09-11 Modified by yanneng, added unisVsiPwBindTable table.
--   V1.4 2013-11-22 Modified by yanneng, added unisVsiL2vpnStatus,
--               unisVsiVxlanID, unisVsiArpSuppression, unisVsiFlooding,
--               unisVsiLocalMacCount, unisVsiFloodMacTable, unisVsiLocalMacTable
--   V1.5 2014-03-22 Modified by wangrui, added unisVsiInterfaceID, unisVsiStatistics,
--               unisVsiPerfTable, unisVsiIfTable
--        2014-04-12 Modified by yanneng, added unisVsiNvgreID
--   V1.6 2015-05-19 Modified by fuzhihua, modified unisVsiXconnectEvcSrvInstId
--   V1.7 2016-10-29 Modified by liuqingye, added value 'vxlan(9)' for
--               data type 'unisVsiMode'
-- =============================================================================
UNIS-VSI-MIB DEFINITIONS ::= BEGIN
IMPORTS
        RowStatus, TruthValue, MacAddress
    FROM SNMPv2-TC
        MODULE-IDENTITY,
        OBJECT-TYPE,
        Integer32,
        Counter64,
        Unsigned32
    FROM SNMPv2-SMI
        InterfaceIndex
    FROM IF-MIB
        unisCommon
    FROM UNIS-OID-MIB;

-- =============================================================================
-- module identity part
-- =============================================================================
unisVsi MODULE-IDENTITY
    LAST-UPDATED
        "201610291650Z"        -- Oct 29, 2016 at 16:50 GMT
    ORGANIZATION
        "Unisyue Technologies Co., Ltd."
    CONTACT-INFO
        ""
    DESCRIPTION
        "The MIB for VSI (Virtual Switch Instance)."
    REVISION
        "201610291650Z"   -- Oct 29, 2016 at 16:50 GMT
    DESCRIPTION
        "Added value 'vxlan(9)' for data type 'unisVsiMode' version."
    REVISION
        "201505261555Z"   -- May 26, 2015 at 15:55 GMT
    DESCRIPTION
        "Modified unisVsiXconnectEvcSrvInstId version."
    REVISION
        "200908081000Z"   -- Aug 08, 2009 at 10:00 GMT
    DESCRIPTION
        "Initial version."
    ::= { unisCommon 105 }

-- =============================================================================
-- object definition begin
-- =============================================================================

unisVsiObjects      OBJECT IDENTIFIER ::= { unisVsi 1 }

unisVsiScalarGroup OBJECT IDENTIFIER ::= { unisVsiObjects 1 }

unisVsiNextAvailableVsiIndex    OBJECT-TYPE
    SYNTAX      Unsigned32
    MAX-ACCESS  read-only
    STATUS      current
    DESCRIPTION
        "Next available VSI entry index for creating VSI.  Its value ranges
        from 0x1 to 0xFFFFFFFF.  The invalid value 0xFFFFFFFF indicates that
        no VSI entry can be created."
    ::= { unisVsiScalarGroup 1 }

unisVsiL2vpnStatus    OBJECT-TYPE
    SYNTAX      TruthValue
    MAX-ACCESS  read-write
    STATUS      current
    DESCRIPTION
        "The global configuration of L2VPN."
    ::= { unisVsiScalarGroup 2 }

-- =============================================================================
-- unisVsiTable Definition
-- =============================================================================
unisVsiTable  OBJECT-TYPE
    SYNTAX      SEQUENCE OF UnisVsiEntry
    MAX-ACCESS  not-accessible
    STATUS      current
    DESCRIPTION
        "A table for configuring VSI parameters."
    ::= { unisVsiObjects 2 }

unisVsiEntry  OBJECT-TYPE
    SYNTAX      UnisVsiEntry
    MAX-ACCESS  not-accessible
    STATUS      current
    DESCRIPTION
        "An entry for configuring VSI parameters."
    INDEX
    {
        unisVsiIndex
    }
    ::= { unisVsiTable 1 }

UnisVsiEntry ::=
    SEQUENCE
    {
        unisVsiIndex             Unsigned32,
        unisVsiName              OCTET STRING,
        unisVsiMode              INTEGER,
        unisMinmIsid             Integer32,
        unisVsiId                Unsigned32,
        unisVsiTransMode         INTEGER,
        unisVsiEnableHubSpoke    INTEGER,
        unisVsiAdminState        INTEGER,
        unisVsiRowStatus         RowStatus,
        unisVsiSpbIsid           Integer32,
        unisVsiVxlanID           Unsigned32,
        unisVsiArpSuppression    TruthValue,
        unisVsiFlooding          TruthValue,
        unisVsiLocalMacCount     Unsigned32,
        unisVsiInterfaceID       Unsigned32,
        unisVsiStatistics        TruthValue,
        unisVsiNvgreID           Unsigned32
    }

unisVsiIndex    OBJECT-TYPE
    SYNTAX      Unsigned32
    MAX-ACCESS  not-accessible
    STATUS      current
    DESCRIPTION
        "Index of VSI.  Its value ranges from 0x1 to 0xFFFFFFFE."
    ::= { unisVsiEntry 1 }

unisVsiName    OBJECT-TYPE
    SYNTAX      OCTET STRING(SIZE(1..31))
    MAX-ACCESS  read-create
    STATUS      current
    DESCRIPTION
        "Name of VSI.  Max string length of VSI name is 31."
    ::= { unisVsiEntry 2 }

unisVsiMode    OBJECT-TYPE
    SYNTAX      INTEGER
    {
        default(0),
        martini(1),
        minm(2),
        martiniAndMinm(3),
        kompella(4),
        kompellaAndMinm(5),
        minmpxp(6),
        martiniAndMinmpxp(7),
        kompellaAndMinmpxp(8),
        vxlan(9)
    }
    MAX-ACCESS  read-create
    STATUS      current
    DESCRIPTION
        "Mode of VSI.  Martini mode indicated this VSI supports VPLS service
         signalled using LDP.  Kompella indicated this VSI supports VPLS
         service signalled using BGP.  Minm indicated this VSI supports
         MAC-in-MAC service.
         Default indicated this VSI supports all services."

    ::= { unisVsiEntry 3 }

unisMinmIsid    OBJECT-TYPE
    SYNTAX      Integer32
    MAX-ACCESS  read-create
    STATUS      current
    DESCRIPTION
        "The PBB I-SID of VSI in minm or martiniAndMinm mode.  It
        must be different for every VSI.  Its value ranges from 0x1 to
        0xFFFFFF.  In other VSI modes, its value is invalid value 0x0."
    ::= { unisVsiEntry 4 }

unisVsiId    OBJECT-TYPE
    SYNTAX      Unsigned32
    MAX-ACCESS  read-create
    STATUS      current
    DESCRIPTION
        "Identifier of VSI in martini or martiniAndMinm mode, by default,
        it's the PW ID of this VSI.  Its value ranges from 1 to 4294967295.
        In other VSI modes, its value is invalid value 0."
    ::= { unisVsiEntry 5 }

unisVsiTransMode    OBJECT-TYPE
    SYNTAX      INTEGER
    {
        vlan(1),
        ethernet(2)
    }
    MAX-ACCESS  read-create
    STATUS      current
    DESCRIPTION
        "Transit Mode of VSI."
    ::= { unisVsiEntry 6 }

unisVsiEnableHubSpoke    OBJECT-TYPE
    SYNTAX      INTEGER
    {
        disable(1),
        enable(2)
    }
    MAX-ACCESS  read-create
    STATUS      current
    DESCRIPTION
        "Config HubSpoke property of this VSI."
    ::= { unisVsiEntry 7 }

unisVsiAdminState   OBJECT-TYPE
    SYNTAX      INTEGER
    {
        adminUp(1),
        adminDown(2)
    }
    MAX-ACCESS  read-create
    STATUS      current
    DESCRIPTION
        "Set VSI admin state as adminUp or adminDown."
    ::= { unisVsiEntry 8 }

unisVsiRowStatus     OBJECT-TYPE
    SYNTAX      RowStatus
    MAX-ACCESS  read-create
    STATUS      current
    DESCRIPTION
        "Operation status of this table entry."
    ::= { unisVsiEntry 9 }

unisVsiSpbIsid    OBJECT-TYPE
    SYNTAX      Integer32
    MAX-ACCESS  read-create
    STATUS      current
    DESCRIPTION
        "The SPB I-SID of VSI in minm or martiniAndMinm mode.  It
        must be different for every VSI.  Its value ranges from 0xFF to
        0xFFFFFF.  In other VSI modes, its value is invalid value 0x0."
    ::= { unisVsiEntry 10 }

unisVsiVxlanID    OBJECT-TYPE
    SYNTAX      Unsigned32
    MAX-ACCESS  read-only
    STATUS      current
    DESCRIPTION
        "VXLAN ID, in the range of 0x0 to 0xFFFFFF.  Value 0xFFFFFFFF means
        this VSI does not enable VXLAN service."
    ::= { unisVsiEntry 11 }

unisVsiArpSuppression    OBJECT-TYPE
    SYNTAX      TruthValue
    MAX-ACCESS  read-create
    STATUS      current
    DESCRIPTION
        "The capability of ARP suppression."
    DEFVAL { false }
    ::= { unisVsiEntry 12 }

unisVsiFlooding    OBJECT-TYPE
    SYNTAX      TruthValue
    MAX-ACCESS  read-create
    STATUS      current
    DESCRIPTION
        "The capability of MAC(Media Access Control) flooding."
    DEFVAL { true }
    ::= { unisVsiEntry 13 }

unisVsiLocalMacCount    OBJECT-TYPE
    SYNTAX      Unsigned32
    MAX-ACCESS  read-only
    STATUS      current
    DESCRIPTION
        "The number of VSI local MAC addresses."
    ::= { unisVsiEntry 14 }

unisVsiInterfaceID    OBJECT-TYPE
    SYNTAX      Unsigned32
    MAX-ACCESS  read-create
    STATUS      current
    DESCRIPTION
        "VSI interface ID.  A value of 0xFFFFFFFF indicates that no gateway
        interface has been assigned to the VSI."
    ::= { unisVsiEntry 15 }

unisVsiStatistics    OBJECT-TYPE
    SYNTAX      TruthValue
    MAX-ACCESS  read-create
    STATUS      current
    DESCRIPTION
        "The enable status of VSI traffic flow statistics."
    DEFVAL { false }
    ::= { unisVsiEntry 16 }

unisVsiNvgreID    OBJECT-TYPE
    SYNTAX      Unsigned32
    MAX-ACCESS  read-only
    STATUS      current
    DESCRIPTION
        "NVGRE ID, in the range of 4096 to 16777214.  Value 4294967295 means
        this VSI does not enable NVGRE service."
    ::= { unisVsiEntry 17 }

-- =============================================================================
-- End of unisVsiTable Definition
-- =============================================================================

-- =============================================================================
-- unisVsiXconnectTable Definition
-- =============================================================================
unisVsiXconnectTable  OBJECT-TYPE
    SYNTAX      SEQUENCE OF UnisVsiXconnectEntry
    MAX-ACCESS  not-accessible
    STATUS      current
    DESCRIPTION
        "A table for configuring xconnect parameters."
    ::= { unisVsiObjects 3 }

unisVsiXconnectEntry  OBJECT-TYPE
    SYNTAX      UnisVsiXconnectEntry
    MAX-ACCESS  not-accessible
    STATUS      current
    DESCRIPTION
        "An entry for configuring xconnect parameters.  Each entry means
        connecting a service instance of a interface to a VSI."
    INDEX
    {
        unisVsiXconnectIfIndex,
        unisVsiXconnectEvcSrvInstId
    }
    ::= { unisVsiXconnectTable 1 }

UnisVsiXconnectEntry ::=
    SEQUENCE
    {
        unisVsiXconnectIfIndex      Unsigned32,
        unisVsiXconnectEvcSrvInstId Unsigned32,
        unisVsiXconnectVsiName      OCTET STRING,
        unisVsiXconnectAccessMode   INTEGER,
        unisVsiXconnectHubSpoke     INTEGER,
        unisVsiXconnectRowStatus    RowStatus
    }
unisVsiXconnectIfIndex    OBJECT-TYPE
    SYNTAX      Unsigned32
    MAX-ACCESS  not-accessible
    STATUS      current
    DESCRIPTION
        "Index of the interface associated with the VSI."
    ::= { unisVsiXconnectEntry 1 }

unisVsiXconnectEvcSrvInstId    OBJECT-TYPE
    SYNTAX      Unsigned32
    MAX-ACCESS  not-accessible
    STATUS      current
    DESCRIPTION
        "Index of the service instance associated with the VSI.  The value is always 0 when the
         interface isn't a layer 2 Ethernet interface."
    ::= { unisVsiXconnectEntry 2 }


unisVsiXconnectVsiName    OBJECT-TYPE
    SYNTAX      OCTET STRING(SIZE(1..31))
    MAX-ACCESS  read-create
    STATUS      current
    DESCRIPTION
        "Name of VSI.  Max string length of VSI name is 31."
    ::= { unisVsiXconnectEntry 3 }

unisVsiXconnectAccessMode    OBJECT-TYPE
    SYNTAX      INTEGER
    {
        vlan(1),
        ethernet(2)
    }
    MAX-ACCESS  read-create
    STATUS      current
    DESCRIPTION
        "Access mode of this service instance."
    ::= { unisVsiXconnectEntry 4 }

unisVsiXconnectHubSpoke    OBJECT-TYPE
    SYNTAX      INTEGER
    {
        none(1),
        hub(2),
        spoke(3)
    }
    MAX-ACCESS  read-create
    STATUS      current
    DESCRIPTION
        "Config HubSpoke property of this service instance."
    ::= { unisVsiXconnectEntry 5 }

unisVsiXconnectRowStatus     OBJECT-TYPE
    SYNTAX      RowStatus
    MAX-ACCESS  read-create
    STATUS      current
    DESCRIPTION
        "Operation status of this table entry."
    ::= { unisVsiXconnectEntry 6 }

-- =============================================================================
-- End of unisVsiXconnectTable Definition
-- =============================================================================

-- =============================================================================
-- unisVsiPwBindTable Definition
-- =============================================================================
unisVsiPwBindTable  OBJECT-TYPE
    SYNTAX      SEQUENCE OF UnisVsiPwBindEntry
    MAX-ACCESS  not-accessible
    STATUS      current
    DESCRIPTION
        "A table for PW(PseudoWire) mapping to VSI."
    ::= { unisVsiObjects 4 }

unisVsiPwBindEntry  OBJECT-TYPE
    SYNTAX      UnisVsiPwBindEntry
    MAX-ACCESS  not-accessible
    STATUS      current
    DESCRIPTION
        "Each entry means a PW mapping to a VSI."
    INDEX
    {
        unisVsiIndex,
        unisVsiPwIndex
    }
    ::= { unisVsiPwBindTable 1 }

UnisVsiPwBindEntry ::=
    SEQUENCE
    {
        unisVsiPwIndex            Unsigned32,
        unisVsiPwBindAttributes   BITS,
        unisVsiPwBindRowStatus    RowStatus
    }

unisVsiPwIndex    OBJECT-TYPE
    SYNTAX      Unsigned32
    MAX-ACCESS  not-accessible
    STATUS      current
    DESCRIPTION
        "A unique index for the conceptual row identifying
         a PW in the pwTable."
    ::= { unisVsiPwBindEntry 1 }

unisVsiPwBindAttributes    OBJECT-TYPE
    SYNTAX      BITS {
                     noSplitHorizon (0),
                     hub (1)
                    }
    MAX-ACCESS  read-create
    STATUS      current
    DESCRIPTION
        "This bit mask indicates optional values for this PW.
         The following describes these bit fields:

         noSplitHorizon flag indicates that the PW disable
         split horizon forwarding.

         hub flag indicates that the PW as the hub link the VSI."
    ::= { unisVsiPwBindEntry 2 }

unisVsiPwBindRowStatus     OBJECT-TYPE
    SYNTAX      RowStatus
    MAX-ACCESS  read-create
    STATUS      current
    DESCRIPTION
        "Operation status of this table entry.  A row entry cannot
        be modified when the value of this object is 'active'."
    ::= { unisVsiPwBindEntry 3 }

-- =============================================================================
-- End of unisVsiPwBindTable Definition
-- =============================================================================

-- =============================================================================
-- unisVsiFloodMacTable Definition
-- =============================================================================
unisVsiFloodMacTable  OBJECT-TYPE
    SYNTAX      SEQUENCE OF UnisVsiFloodMacEntry
    MAX-ACCESS  not-accessible
    STATUS      current
    DESCRIPTION
        "A table of MAC addresses enabled with selective flooding."
    ::= { unisVsiObjects 5 }

unisVsiFloodMacEntry  OBJECT-TYPE
    SYNTAX      UnisVsiFloodMacEntry
    MAX-ACCESS  not-accessible
    STATUS      current
    DESCRIPTION
        "Each entry represents a selective flooding MAC."
    INDEX
    {
        unisVsiIndex,
        unisVsiFloodMac
    }
    ::= { unisVsiFloodMacTable 1 }

UnisVsiFloodMacEntry ::=
    SEQUENCE
    {
        unisVsiFloodMac               MacAddress,
        unisVsiFloodMacRowStatus      RowStatus
    }

unisVsiFloodMac    OBJECT-TYPE
    SYNTAX      MacAddress
    MAX-ACCESS  not-accessible
    STATUS      current
    DESCRIPTION
        "MAC address."
    ::= { unisVsiFloodMacEntry 1 }

unisVsiFloodMacRowStatus     OBJECT-TYPE
    SYNTAX      RowStatus
    MAX-ACCESS  read-create
    STATUS      current
    DESCRIPTION
        "Operation status of this table entry."
    ::= { unisVsiFloodMacEntry 2 }

-- =============================================================================
-- End of unisVsiFloodMacTable Definition
-- =============================================================================

-- =============================================================================
-- unisVsiLocalMacTable Definition
-- =============================================================================
unisVsiLocalMacTable  OBJECT-TYPE
    SYNTAX      SEQUENCE OF UnisVsiLocalMacEntry
    MAX-ACCESS  not-accessible
    STATUS      current
    DESCRIPTION
        "A table for VSI local MAC addresses."
    ::= { unisVsiObjects 6 }

unisVsiLocalMacEntry  OBJECT-TYPE
    SYNTAX      UnisVsiLocalMacEntry
    MAX-ACCESS  not-accessible
    STATUS      current
    DESCRIPTION
        "A local MAC address of VSI."
    INDEX
    {
        unisVsiIndex,
        unisVsiLocalMacAddr
    }
    ::= { unisVsiLocalMacTable 1 }

UnisVsiLocalMacEntry ::=
    SEQUENCE
    {
        unisVsiLocalMacAddr            MacAddress,
        unisVsiLocalMacIfIndex         InterfaceIndex,
        unisVsiLocalMacSrvID           Unsigned32
    }

unisVsiLocalMacAddr    OBJECT-TYPE
    SYNTAX      MacAddress
    MAX-ACCESS  not-accessible
    STATUS      current
    DESCRIPTION
        "MAC address."
    ::= { unisVsiLocalMacEntry 1 }

unisVsiLocalMacIfIndex    OBJECT-TYPE
    SYNTAX      InterfaceIndex
    MAX-ACCESS  read-only
    STATUS      current
    DESCRIPTION
        "Index of the interface associated with the MAC address."
    ::= { unisVsiLocalMacEntry 2 }

unisVsiLocalMacSrvID    OBJECT-TYPE
    SYNTAX      Unsigned32
    MAX-ACCESS  read-only
    STATUS      current
    DESCRIPTION
        "Index of the service instance associated with the MAC address."
    ::= { unisVsiLocalMacEntry 3 }

-- =============================================================================
-- End of unisVsiLocalMacTable Definition
-- =============================================================================

-- =============================================================================
-- unisVsiPerfTable Definition
-- =============================================================================
unisVsiPerfTable  OBJECT-TYPE
    SYNTAX      SEQUENCE OF UnisVsiPerfEntry
    MAX-ACCESS  not-accessible
    STATUS      current
    DESCRIPTION
        "This table contains performance statistics for each VSI."
    ::= { unisVsiObjects 7 }

unisVsiPerfEntry  OBJECT-TYPE
    SYNTAX      UnisVsiPerfEntry
    MAX-ACCESS  not-accessible
    STATUS      current
    DESCRIPTION
        "A row in this table contains statistics for a VSI."
    INDEX
    {
        unisVsiIndex
    }
    ::= { unisVsiPerfTable 1 }

UnisVsiPerfEntry ::=
    SEQUENCE
    {
        unisVsiPerfInOctets            Counter64,
        unisVsiPerfInPackets           Counter64,
        unisVsiPerfInErrors            Counter64,
        unisVsiPerfInDiscards          Counter64,
        unisVsiPerfOutOctets           Counter64,
        unisVsiPerfOutPackets          Counter64,
        unisVsiPerfOutErrors           Counter64,
        unisVsiPerfOutDiscards         Counter64
    }

unisVsiPerfInOctets    OBJECT-TYPE
    SYNTAX      Counter64
    MAX-ACCESS  read-only
    STATUS      current
    DESCRIPTION
        "Total number of octets received by the VSI."
    ::= { unisVsiPerfEntry 1 }

unisVsiPerfInPackets    OBJECT-TYPE
    SYNTAX      Counter64
    MAX-ACCESS  read-only
    STATUS      current
    DESCRIPTION
        "Total number of packets received by the VSI."
    ::= { unisVsiPerfEntry 2 }

unisVsiPerfInErrors    OBJECT-TYPE
    SYNTAX      Counter64
    MAX-ACCESS  read-only
    STATUS      current
    DESCRIPTION
        "Number of error packets received by the VSI."
    ::= { unisVsiPerfEntry 3 }

unisVsiPerfInDiscards    OBJECT-TYPE
    SYNTAX      Counter64
    MAX-ACCESS  read-only
    STATUS      current
    DESCRIPTION
        "Number of incoming packets discarded by the VSI."
    ::= { unisVsiPerfEntry 4 }

unisVsiPerfOutOctets    OBJECT-TYPE
    SYNTAX      Counter64
    MAX-ACCESS  read-only
    STATUS      current
    DESCRIPTION
        "Total number of octets sent by the VSI."
    ::= { unisVsiPerfEntry 5 }

unisVsiPerfOutPackets    OBJECT-TYPE
    SYNTAX      Counter64
    MAX-ACCESS  read-only
    STATUS      current
    DESCRIPTION
        "Total number of packets sent by the VSI."
    ::= { unisVsiPerfEntry 6 }

unisVsiPerfOutErrors    OBJECT-TYPE
    SYNTAX      Counter64
    MAX-ACCESS  read-only
    STATUS      current
    DESCRIPTION
        "Number of packets that failed to be sent because of a VSI error."
    ::= { unisVsiPerfEntry 7 }

unisVsiPerfOutDiscards    OBJECT-TYPE
    SYNTAX      Counter64
    MAX-ACCESS  read-only
    STATUS      current
    DESCRIPTION
       "Number of packets discarded by the VSI because of transmission failure."
    ::= { unisVsiPerfEntry 8 }
-- =============================================================================
-- End of unisVsiPerfTable Definition
-- =============================================================================

-- =============================================================================
-- unisVsiNextAvailableVsiIfID Definition
-- =============================================================================
unisVsiNextAvailableVsiIfID OBJECT-TYPE
   SYNTAX        Unsigned32
   MAX-ACCESS    read-only
   STATUS        current
   DESCRIPTION
       "This object contains the next available value for unisVsiIfID
        when creating entries in the unisVsiIfTable.  A value of 0xFFFFFFFF
        indicates that no new entries can be created in this table.
        To prevent managers from creating entries in this table, the agent
        must set this object to this special value."
   ::= { unisVsiObjects 8 }

-- =============================================================================
-- unisVsiIfTable Definition
-- =============================================================================
unisVsiIfTable  OBJECT-TYPE
    SYNTAX      SEQUENCE OF UnisVsiIfEntry
    MAX-ACCESS  not-accessible
    STATUS      current
    DESCRIPTION
        "VSI interface table."
    ::= { unisVsiObjects 9 }

unisVsiIfEntry  OBJECT-TYPE
    SYNTAX      UnisVsiIfEntry
    MAX-ACCESS  not-accessible
    STATUS      current
    DESCRIPTION
        "A row in this table contains a VSI interface."
    INDEX
    {
        unisVsiIfID
    }
    ::= { unisVsiIfTable 1 }

UnisVsiIfEntry ::=
    SEQUENCE
    {
        unisVsiIfID               Unsigned32,
        unisVsiIfIndex            InterfaceIndex,
        unisVsiIfRowStatus        RowStatus
    }

unisVsiIfID    OBJECT-TYPE
    SYNTAX      Unsigned32
    MAX-ACCESS  not-accessible
    STATUS      current
    DESCRIPTION
        "VSI interface ID."
    ::= { unisVsiIfEntry 1 }

unisVsiIfIndex    OBJECT-TYPE
    SYNTAX      InterfaceIndex
    MAX-ACCESS  read-only
    STATUS      current
    DESCRIPTION
        "VSI interface index."
    ::= { unisVsiIfEntry 2 }

unisVsiIfRowStatus     OBJECT-TYPE
    SYNTAX      RowStatus
    MAX-ACCESS  read-create
    STATUS      current
    DESCRIPTION
        "Operation status of the table entry."
    ::= { unisVsiIfEntry 3 }

-- =============================================================================
-- End of unisVsiIfTable Definition
-- =============================================================================

END
