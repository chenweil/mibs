-- =================================================================
-- Copyright (c) 2020 Unisyue Technologies Co., Ltd.  All rights reserved.
--
-- Description:  ARP entry MIB
-- Reference:
-- Version: V1.0
-- History:
-- V1.0 Initial version created by z09684
-- =================================================================
UNIS-ARP-ENTRY-MIB DEFINITIONS ::= BEGIN
IMPORTS
    unisCommon
        FROM UNIS-OID-MIB
    OBJECT-TYPE, MODULE-IDENTITY, Counter32
        FROM SNMPv2-SMI;

unisARPEntry MODULE-IDENTITY
    LAST-UPDATED "201703140000Z"            -- March 14, 2017 at 00:00 GMT
    ORGANIZATION
        "Unisyue Technologies Co., Ltd."
    CONTACT-INFO
        ""
    DESCRIPTION
        "The MIB module is used for ARP entry."
    REVISION    "201703140000Z"
    DESCRIPTION
        "Initial version"
    ::= { unisCommon 168}

--
-- Define the ARP Entry GLOBAL.
--
unisARPEntryCountObjects OBJECT IDENTIFIER ::= { unisARPEntry 1 }

unisARPEntryOpenFlowCount OBJECT-TYPE
    SYNTAX      Counter32
    MAX-ACCESS  read-only
    STATUS      current
    DESCRIPTION
        "Count of ARP entries of type OpenFlow."
    ::= { unisARPEntryCountObjects 1 }

END
