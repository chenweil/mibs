-- =================================================================
-- Copyright (c) 2020 Unisyue Technologies Co., Ltd.  All rights reserved.
--
-- Description: QOS Profile MIB
-- Version: V2.1
-- History:
--   V1.0(Initial version) 6th Jul 2004
--     V2.0 2004-10-12 updated by gaolong
--        Import Integer32.
--        Modify unisQoSProfile to unisQosProfile
--        Replace INTEGER with Integer32.
--        Change value of unisQoSTrafPrioPolicedServiceType from underscores to hyphens.
--        Fix a default value error of unisQoSTrafPrioPolicedServiceType.
--        Add MODULE clause for unisQoSProfMibCompliance.
--   v2.1 2004-12-23 changed by zhuangyu
--        1 Add an enumeration in unisQoSTrafLmtConformActionType
--        2 Add unisQoSTrafLmtConformCos and unisQoSTrafLmtConformDscp in unisQoSTrafficLimitTable
--
-- =================================================================
UNIS-QOS-PROFILE-MIB DEFINITIONS ::= BEGIN

        IMPORTS
            unisCommon
                FROM UNIS-OID-MIB
            OBJECT-GROUP, MODULE-COMPLIANCE, NOTIFICATION-GROUP
                FROM SNMPv2-CONF
            IpAddress, OBJECT-TYPE, MODULE-IDENTITY, NOTIFICATION-TYPE, Integer32
                FROM SNMPv2-SMI
            RowStatus, TruthValue, MacAddress, TEXTUAL-CONVENTION
                FROM SNMPv2-TC;


        unisQosProfile MODULE-IDENTITY
            LAST-UPDATED "200407060000Z"
            ORGANIZATION
                "Unisyue Technologies Co., Ltd."
            CONTACT-INFO
                ""
            DESCRIPTION
                "The private MIB file includes the general information QoS profile."
            ::= { unisCommon 17 }


--
-- Textual conventions
--
        UnisQoSDirection ::= TEXTUAL-CONVENTION
            STATUS current
            DESCRIPTION
                "Description."
            SYNTAX INTEGER
                {
                invalid(0),
                input(1),
                ouput(2)
                }


--
-- Node definitions
--
        unisQoSProfObjects OBJECT IDENTIFIER ::= { unisQosProfile 1 }

        unisQoSProf OBJECT IDENTIFIER ::= { unisQoSProfObjects 1 }

        unisQoSProfTable OBJECT-TYPE
            SYNTAX SEQUENCE OF UnisQoSProfEntry
            MAX-ACCESS not-accessible
            STATUS current
            DESCRIPTION
                "QoS profile table is used to config the qos profiles."
            ::= { unisQoSProf 1 }

        unisQoSProfEntry OBJECT-TYPE
            SYNTAX UnisQoSProfEntry
            MAX-ACCESS not-accessible
            STATUS current
            DESCRIPTION             " "
            INDEX { unisQoSProfIndex }
            ::= { unisQoSProfTable 1 }

        UnisQoSProfEntry ::=
            SEQUENCE {
                unisQoSProfIndex
                    Integer32,
                unisQoSProfName
                    OCTET STRING,
                unisQoSProfActionNumber
                    Integer32,
                unisQoSProfRowStatus
                    RowStatus
             }

        unisQoSProfIndex OBJECT-TYPE
            SYNTAX Integer32 (1..65535)
            MAX-ACCESS not-accessible
            STATUS current
            DESCRIPTION
                "QoS profile table index."
            ::= { unisQoSProfEntry 1 }

        unisQoSProfName OBJECT-TYPE
            SYNTAX OCTET STRING (SIZE (1..32))
            MAX-ACCESS read-create
            STATUS current
            DESCRIPTION
                "QoS profile name."
            ::= { unisQoSProfEntry 2 }

        unisQoSProfActionNumber OBJECT-TYPE
            SYNTAX Integer32 (0..65535)
            MAX-ACCESS read-only
            STATUS current
            DESCRIPTION
                "Total number of actions of a QoS profile."
            ::= { unisQoSProfEntry 3 }

        unisQoSProfRowStatus OBJECT-TYPE
            SYNTAX RowStatus
            MAX-ACCESS read-create
            STATUS current
            DESCRIPTION
                "RowStatus,Now support three state:CreateAndGo,Active,Destroy."
            ::= { unisQoSProfEntry 4 }

        unisQoSAction OBJECT IDENTIFIER ::= { unisQoSProfObjects 2 }

        unisQoSTrafficLimitTable OBJECT-TYPE
            SYNTAX SEQUENCE OF UnisQoSTrafficLimitEntry
            MAX-ACCESS not-accessible
            STATUS current
            DESCRIPTION
                "Traffic limit table is used to set the average rate or peak rate of the flow.
                IP and Link ACL rules can be applied simultaneously,
                IP and User based ACL rules can not be applied simultaneously,
                Link and User based ACL rules can not be applied simultaneously.
                Unused ones is represented with default values."
            ::= { unisQoSAction 1 }

        unisQoSTrafficLimitEntry OBJECT-TYPE
            SYNTAX UnisQoSTrafficLimitEntry
            MAX-ACCESS not-accessible
            STATUS current
            DESCRIPTION             " "
            INDEX { unisQoSTrafLmtProfIndex, unisQoSTrafLmtActionIndex }
            ::= { unisQoSTrafficLimitTable 1 }

        UnisQoSTrafficLimitEntry ::=
            SEQUENCE {
                unisQoSTrafLmtProfIndex
                    Integer32,
                unisQoSTrafLmtActionIndex
                    Integer32,
                unisQoSTrafLmtDirection
                    UnisQoSDirection,
                unisQoSTrafLmtUserAclNum
                    Integer32,
                unisQoSTrafLmtUserAclRule
                    Integer32,
                unisQoSTrafLmtIpAclNum
                    Integer32,
                unisQoSTrafLmtIpAclRule
                    Integer32,
                unisQoSTrafLmtLinkAclNum
                    Integer32,
                unisQoSTrafLmtLinkAclRule
                    Integer32,
                unisQoSTrafLmtTargetRateMbps
                    Integer32,
                unisQoSTrafLmtTargetRateKbps
                    Integer32,
                unisQoSTrafLmtPeakRate
                    Integer32,
                unisQoSTrafLmtCIR
                    Integer32,
                unisQoSTrafLmtCBS
                    Integer32,
                unisQoSTrafLmtEBS
                    Integer32,
                unisQoSTrafLmtPIR
                    Integer32,
                unisQoSTrafLmtConformLocalPre
                    Integer32,
                unisQoSTrafLmtConformActionType
                    INTEGER,
                unisQoSTrafLmtExceedActionType
                    INTEGER,
                unisQoSTrafLmtExceedDscp
                    Integer32,
                unisQoSTrafLmtExceedCos
                    Integer32,
                unisQoSTrafLmtRowStatus
                    RowStatus,
                unisQoSTrafLmtConformCos
                    Integer32,
                unisQoSTrafLmtConformDscp
                    Integer32
             }

        unisQoSTrafLmtProfIndex OBJECT-TYPE
            SYNTAX Integer32 (1..65535)
            MAX-ACCESS not-accessible
            STATUS current
            DESCRIPTION
                "The index of QoS profile which the traffic-limit action belongs to."
            ::= { unisQoSTrafficLimitEntry 1 }

        unisQoSTrafLmtActionIndex OBJECT-TYPE
            SYNTAX Integer32 (1..65535)
            MAX-ACCESS not-accessible
            STATUS current
            DESCRIPTION
                "The index of traffic-limit action."
            ::= { unisQoSTrafficLimitEntry 2 }

        unisQoSTrafLmtDirection OBJECT-TYPE
            SYNTAX UnisQoSDirection
            MAX-ACCESS read-create
            STATUS current
            DESCRIPTION
                "The direction of traffic-limit action."
            ::= { unisQoSTrafficLimitEntry 3 }

        unisQoSTrafLmtUserAclNum OBJECT-TYPE
            SYNTAX Integer32 (0 | 5000..5999)
            MAX-ACCESS read-create
            STATUS current
            DESCRIPTION
                "The number of user-based acl group."
            DEFVAL { 0 }
            ::= { unisQoSTrafficLimitEntry 4 }

        unisQoSTrafLmtUserAclRule OBJECT-TYPE
            SYNTAX Integer32 (0..65535)
            MAX-ACCESS read-create
            STATUS current
            DESCRIPTION
                "The subitem of user-based acl rule."
            DEFVAL { 65535 }
            ::= { unisQoSTrafficLimitEntry 5 }

        unisQoSTrafLmtIpAclNum OBJECT-TYPE
            SYNTAX Integer32 (0 | 2000..3999)
            MAX-ACCESS read-create
            STATUS current
            DESCRIPTION
                "The number of Ip-based acl group."
            DEFVAL { 0 }
            ::= { unisQoSTrafficLimitEntry 6 }

        unisQoSTrafLmtIpAclRule OBJECT-TYPE
            SYNTAX Integer32 (0..65535)
            MAX-ACCESS read-create
            STATUS current
            DESCRIPTION
                "The subitem of IP-based acl rule."
            DEFVAL { 65535 }
            ::= { unisQoSTrafficLimitEntry 7 }

        unisQoSTrafLmtLinkAclNum OBJECT-TYPE
            SYNTAX Integer32 (0 | 4000..4999)
            MAX-ACCESS read-create
            STATUS current
            DESCRIPTION
                "The number of Link-based acl group"
            DEFVAL { 0 }
            ::= { unisQoSTrafficLimitEntry 8 }

        unisQoSTrafLmtLinkAclRule OBJECT-TYPE
            SYNTAX Integer32 (0..65535)
            MAX-ACCESS read-create
            STATUS current
            DESCRIPTION
                "The subitem of Link-based acl rule."
            DEFVAL { 65535 }
            ::= { unisQoSTrafficLimitEntry 9 }

        unisQoSTrafLmtTargetRateMbps OBJECT-TYPE
            SYNTAX Integer32 (0..10000)
            MAX-ACCESS read-create
            STATUS current
            DESCRIPTION
                "Target rate:Mbps
                Some products only support Mbps,but others support Kbps,so
                Kbps and Mbps should be supportted mutually exclusively on the same
                product."
            ::= { unisQoSTrafficLimitEntry 10 }

        unisQoSTrafLmtTargetRateKbps OBJECT-TYPE
            SYNTAX Integer32 (0..10000000)
            MAX-ACCESS read-create
            STATUS current
            DESCRIPTION
                "Target rate:Kbps.
                Some products only support Kbps,but others support Mbps,so
                Kbps and Mbps should be supportted mutually exclusively on the same
                product."
            ::= { unisQoSTrafficLimitEntry 11 }

        unisQoSTrafLmtPeakRate OBJECT-TYPE
            SYNTAX Integer32 (0 | 64..8388608)
            MAX-ACCESS read-create
            STATUS current
            DESCRIPTION
                "Peak rate"
            ::= { unisQoSTrafficLimitEntry 12 }

        unisQoSTrafLmtCIR OBJECT-TYPE
            SYNTAX Integer32 (0..34120000)
            MAX-ACCESS read-create
            STATUS current
            DESCRIPTION
                "Committed Information Rate.
                unit:kbps."
            ::= { unisQoSTrafficLimitEntry 13 }

        unisQoSTrafLmtCBS OBJECT-TYPE
            SYNTAX Integer32 (0..1048575)
            MAX-ACCESS read-create
            STATUS current
            DESCRIPTION
                "Committed Burst Size.
                unit:byte."
            ::= { unisQoSTrafficLimitEntry 14 }

        unisQoSTrafLmtEBS OBJECT-TYPE
            SYNTAX Integer32 (0..268435455)
            MAX-ACCESS read-create
            STATUS current
            DESCRIPTION
                "Excess Burst Size.
                unit:byte."
            ::= { unisQoSTrafficLimitEntry 15 }

        unisQoSTrafLmtPIR OBJECT-TYPE
            SYNTAX Integer32 (0..34120000)
            MAX-ACCESS read-create
            STATUS current
            DESCRIPTION
                "Peak Information Rate.
                unit:kbps."
            ::= { unisQoSTrafficLimitEntry 16 }

        unisQoSTrafLmtConformLocalPre OBJECT-TYPE
            SYNTAX Integer32 (0..7)
            MAX-ACCESS read-create
            STATUS current
            DESCRIPTION
                "The local precedence of conformed flow."
            ::= { unisQoSTrafficLimitEntry 17 }

        unisQoSTrafLmtConformActionType OBJECT-TYPE
            SYNTAX INTEGER
                {
                invalid(0),
                remark-cos(1),
                remark-drop-priority(2),
                remark-cos-drop-priority(3),
                remark-policed-service(4),
                remark-dscp(5)
                }
            MAX-ACCESS read-create
            STATUS current
            DESCRIPTION
                "The action type of conformed flow."
            DEFVAL { 1 }
            ::= { unisQoSTrafficLimitEntry 18 }

        unisQoSTrafLmtExceedActionType OBJECT-TYPE
            SYNTAX INTEGER
                {
                invalid(0),
                forward(1),
                drop(2),
                remarkdscp(3),
                exceed-cos(4)
                }
            MAX-ACCESS read-create
            STATUS current
            DESCRIPTION
                "The action type of non-conformed flow."
            DEFVAL { 1 }
            ::= { unisQoSTrafficLimitEntry 19 }

        unisQoSTrafLmtExceedDscp OBJECT-TYPE
            SYNTAX Integer32 (0..63 | 255)
            MAX-ACCESS read-create
            STATUS current
            DESCRIPTION
                "The remarked DSCP value of non-conformed flow.
                DSCP 255 is used as default value and for get/get-next operation of this
                node. If the user does not set exceeding action as remarking DSCP, then value 255
                is returned for get/get-next operation.
                "
            DEFVAL { 255 }
            ::= { unisQoSTrafficLimitEntry 20 }

        unisQoSTrafLmtExceedCos OBJECT-TYPE
            SYNTAX Integer32 (0..7 | 255)
            MAX-ACCESS read-create
            STATUS current
            DESCRIPTION
                "The remarked COS value of non-conformed flow.
                COS 255 is used as default value and for get/get-next operation of this
                node. If the user does not set exceeding action as remarking COS, then value 255
                is returned for get/get-next operation.
                "
            DEFVAL { 255 }
            ::= { unisQoSTrafficLimitEntry 21 }

        unisQoSTrafLmtRowStatus OBJECT-TYPE
            SYNTAX RowStatus
            MAX-ACCESS read-create
            STATUS current
            DESCRIPTION
                "RowStatus,Now support three state:CreateAndGo,Active,Destroy."
            ::= { unisQoSTrafficLimitEntry 22 }

        unisQoSTrafLmtConformCos OBJECT-TYPE
            SYNTAX Integer32 (0..7|255)
            MAX-ACCESS read-create
            STATUS current
            DESCRIPTION
                "If the user chooses remark-cos value of the unisQoSTrafLmtConformActionType,
                this object can be used to set the conform cos value.
                There are some enumerations as follows:
                best-effort         Specify best-effort priority(0)
                background          Specify background priority(1)
                spare               Specify spare priority(2)
                excellent-effort    Specify excellent-effort priority(3)
                controlled-load     Specify controlled-load priority(4)
                video               Specify video priority(5)
                voice               Specify voice priority(6)
                network-management  Specify network-management priority(7)
                255 indicates invalid value. "
              DEFVAL      { 255 }
            ::= { unisQoSTrafficLimitEntry 23 }

        unisQoSTrafLmtConformDscp OBJECT-TYPE
            SYNTAX Integer32 (0..63|255)
            MAX-ACCESS read-create
            STATUS current
            DESCRIPTION
                "If the user chooses remark-dscp value of the unisQoSTrafLmtConformActionType,
                this object can be used to set the conform dscp value.
                There are some enumerations as follows:
                <0-63>  Value of DSCP
                af11    Specify Assured Forwarding 11 service(10)
                af12    Specify Assured Forwarding 12 service(12)
                af13    Specify Assured Forwarding 13 service(14)
                af21    Specify Assured Forwarding 21 service(18)
                af22    Specify Assured Forwarding 22 service(20)
                af23    Specify Assured Forwarding 23 service(22)
                af31    Specify Assured Forwarding 31 service(26)
                af32    Specify Assured Forwarding 32 service(28)
                af33    Specify Assured Forwarding 33 service(30)
                af41    Specify Assured Forwarding 41 service(34)
                af42    Specify Assured Forwarding 42 service(36)
                af43    Specify Assured Forwarding 43 service(38)
                be      Specify Best Effort service(0)
                cs1     Specify Class Selector 1 service(8)
                cs2     Specify Class Selector 2 service(16)
                cs3     Specify Class Selector 3 service(24)
                cs4     Specify Class Selector 4 service(32)
                cs5     Specify Class Selector 5 service(40)
                cs6     Specify Class Selector 6 service(48)
                cs7     Specify Class Selector 7 service(56)
                ef      Specify Expedited Forwarding service(46)
                255 indicates invalid value. "
              DEFVAL      { 255 }
              ::= { unisQoSTrafficLimitEntry 24 }

        unisQoSTrafficPriorityTable OBJECT-TYPE
            SYNTAX SEQUENCE OF UnisQoSTrafficPriorityEntry
            MAX-ACCESS not-accessible
            STATUS current
            DESCRIPTION
                "Traffic priority table is used to remark the IP-precedence, DSCP or COS priority of packets.
                IP and Link ACL rules can be applied simultaneously,
                IP and User based ACL rules can not be applied simultaneously,
                Link and User based ACL rules can not be applied simultaneously.
                Unused ones is represented with default values.
                QOS policed service from DSCP mapping table is pre-defined in the unisDscpMapTable in the UNIS-LswQos-MIB.
                Policed service can decide what kind of QOS service the flow should get by the DSCP vlaue in the packets.
                Policed service includes remarking new DSCP,new EXP,new 802.1p priority,new local precedence and new drop priority.
                "
            ::= { unisQoSAction 2 }

        unisQoSTrafficPriorityEntry OBJECT-TYPE
            SYNTAX UnisQoSTrafficPriorityEntry
            MAX-ACCESS not-accessible
            STATUS current
            DESCRIPTION             " "
            INDEX { unisQoSTrafPrioProfIndex, unisQoSTrafPrioActionIndex }
            ::= { unisQoSTrafficPriorityTable 1 }

        UnisQoSTrafficPriorityEntry ::=
            SEQUENCE {
                unisQoSTrafPrioProfIndex
                    Integer32,
                unisQoSTrafPrioActionIndex
                    Integer32,
                unisQoSTrafPrioDirection
                    UnisQoSDirection,
                unisQoSTrafPrioUserAclNum
                    Integer32,
                unisQoSTrafPrioUserAclRule
                    Integer32,
                unisQoSTrafPrioIpAclNum
                    Integer32,
                unisQoSTrafPrioIpAclRule
                    Integer32,
                unisQoSTrafPrioLinkAclNum
                    Integer32,
                unisQoSTrafPrioLinkAclRule
                    Integer32,
                unisQoSTrafPrioDscp
                    Integer32,
                unisQoSTrafPrioIpPre
                    Integer32,
                unisQoSTrafPrioIpPreFromCos
                    TruthValue,
                unisQoSTrafPrioCos
                    Integer32,
                unisQoSTrafPrioCosFromIpPre
                    TruthValue,
                unisQoSTrafPrioLocalPre
                    Integer32,
                unisQoSTrafPrioPolicedServiceType
                    INTEGER,
                unisQoSTrafPrioPolicedServiceDscp
                    Integer32,
                unisQoSTrafPrioPolicedServiceExp
                    Integer32,
                unisQoSTrafPrioPolicedServiceCos
                    Integer32,
                unisQoSTrafPrioPolicedServiceLoaclPre
                    Integer32,
                unisQoSTrafPrioPolicedServiceDropPriority
                    Integer32,
                unisQoSTrafPrioRowStatus
                    RowStatus
             }

        unisQoSTrafPrioProfIndex OBJECT-TYPE
            SYNTAX Integer32 (1..65535)
            MAX-ACCESS not-accessible
            STATUS current
            DESCRIPTION
                "The index of QoS profile which the traffic-priority action belongs to."
            ::= { unisQoSTrafficPriorityEntry 1 }

        unisQoSTrafPrioActionIndex OBJECT-TYPE
            SYNTAX Integer32 (1..65535)
            MAX-ACCESS not-accessible
            STATUS current
            DESCRIPTION
                "The index of traffic-priority action."
            ::= { unisQoSTrafficPriorityEntry 2 }

        unisQoSTrafPrioDirection OBJECT-TYPE
            SYNTAX UnisQoSDirection
            MAX-ACCESS read-create
            STATUS current
            DESCRIPTION
                "The direction of traffic-priority action."
            ::= { unisQoSTrafficPriorityEntry 3 }

        unisQoSTrafPrioUserAclNum OBJECT-TYPE
            SYNTAX Integer32 (0 | 5000..5999)
            MAX-ACCESS read-create
            STATUS current
            DESCRIPTION
                "The number of user-based acl group."
            DEFVAL { 0 }
            ::= { unisQoSTrafficPriorityEntry 4 }

        unisQoSTrafPrioUserAclRule OBJECT-TYPE
            SYNTAX Integer32 (0..65535)
            MAX-ACCESS read-create
            STATUS current
            DESCRIPTION
                "The subitem of user-based acl rule."
            DEFVAL { 65535 }
            ::= { unisQoSTrafficPriorityEntry 5 }

        unisQoSTrafPrioIpAclNum OBJECT-TYPE
            SYNTAX Integer32 (0 | 2000..3999)
            MAX-ACCESS read-create
            STATUS current
            DESCRIPTION
                "The number of Ip-based acl group."
            DEFVAL { 0 }
            ::= { unisQoSTrafficPriorityEntry 6 }

        unisQoSTrafPrioIpAclRule OBJECT-TYPE
            SYNTAX Integer32 (0..65535)
            MAX-ACCESS read-create
            STATUS current
            DESCRIPTION
                "The subitem of IP-based acl rule."
            DEFVAL { 65535 }
            ::= { unisQoSTrafficPriorityEntry 7 }

        unisQoSTrafPrioLinkAclNum OBJECT-TYPE
            SYNTAX Integer32 (0 | 4000..4999)
            MAX-ACCESS read-create
            STATUS current
            DESCRIPTION
                "The number of Link-based acl group"
            DEFVAL { 0 }
            ::= { unisQoSTrafficPriorityEntry 8 }

        unisQoSTrafPrioLinkAclRule OBJECT-TYPE
            SYNTAX Integer32 (0..65535)
            MAX-ACCESS read-create
            STATUS current
            DESCRIPTION
                "The subitem of Link-based acl rule."
            DEFVAL { 65535 }
            ::= { unisQoSTrafficPriorityEntry 9 }

        unisQoSTrafPrioDscp OBJECT-TYPE
            SYNTAX Integer32 (0..63 | 255)
            MAX-ACCESS read-create
            STATUS current
            DESCRIPTION
                "Set new DSCP value of specifed flow.
                DSCP 255 is used as default value and for get/get-next operation of this
                node. If the user does not set action as remarking DSCP, then value 255
                is returned for get/get-next operation.
                "
            DEFVAL { 255 }
            ::= { unisQoSTrafficPriorityEntry 10 }

        unisQoSTrafPrioIpPre OBJECT-TYPE
            SYNTAX Integer32 (0..7 | 255)
            MAX-ACCESS read-create
            STATUS current
            DESCRIPTION
                "Set Ip precedence value of specifed flow.
                Ip precedence 255 is used as default value and for get/get-next operation of this
                node. If the user does not set action as remarking Ip precedence, then value 255
                is returned for get/get-next operation.
                "
            DEFVAL { 255 }
            ::= { unisQoSTrafficPriorityEntry 11 }

        unisQoSTrafPrioIpPreFromCos OBJECT-TYPE
            SYNTAX TruthValue
            MAX-ACCESS read-create
            STATUS current
            DESCRIPTION
                "Set Ip precedence according to vlan priority.
                False(2)is used as default value and for get/get-next operation of this
                node. If the user does not set action as remarking Ip precedence from COS, then value 2
                is returned for get/get-next operation.
                "
            DEFVAL { 2 }
            ::= { unisQoSTrafficPriorityEntry 12 }

        unisQoSTrafPrioCos OBJECT-TYPE
            SYNTAX Integer32 (0..7 | 255)
            MAX-ACCESS read-create
            STATUS current
            DESCRIPTION
                "Set vlan priority of specifed flow.
                COS 255 is used as default value and for get/get-next operation of this
                node. If the user does not set action as remarking COS, then value 255
                is returned for get/get-next operation.
                "
            DEFVAL { 255 }
            ::= { unisQoSTrafficPriorityEntry 13 }

        unisQoSTrafPrioCosFromIpPre OBJECT-TYPE
            SYNTAX TruthValue
            MAX-ACCESS read-create
            STATUS current
            DESCRIPTION
                "Set vlan priority according to IP precedence.
                False(2)is used as default value and for get/get-next operation of this
                node. If the user does not set action as remarking COS from Ip precedence, then value 2
                is returned for get/get-next operation.
                "
            DEFVAL { 2 }
            ::= { unisQoSTrafficPriorityEntry 14 }

        unisQoSTrafPrioLocalPre OBJECT-TYPE
            SYNTAX Integer32 (0..7 | 255)
            MAX-ACCESS read-create
            STATUS current
            DESCRIPTION
                "Set local precedence of specifed flow.
                Local precedence 255 is used as default value and for get/get-next operation of this
                node. If the user does not set action as remarking local precedence, then value 255
                is returned for get/get-next operation.
                "
            DEFVAL { 255 }
            ::= { unisQoSTrafficPriorityEntry 15 }

        unisQoSTrafPrioPolicedServiceType OBJECT-TYPE
            SYNTAX INTEGER
                {
                invalid(0),
                trust-dscp(2),
                new-dscp(3),
                untrusted(4)
                }
            MAX-ACCESS read-create
            STATUS current
            DESCRIPTION
                "The service type of policed Priority.
                Policed Service is not allowed to be set with remarking DSCP,IpPrecedence,IpPrecedenceFromCOS,COS,COSFromIpPrecedence and LocalPrecedence action simultaneously on the same product.
                Policed service is user-predefined qos policy parameters.
                trust-dscp(2) means to decide new police service parameters by the DSCP value in the packets.
                new-dscp(3) means to decide new police service parameters by the new DSCP value set by the user.
                And a DSCP mapping table should be pre-defined in the unisDscpMapTable in the UNIS-LswQos-MIB.
                Untrusted(4) means to set all the new DSCP,EXP,COS,Local precedence and Drop priority by the user.

                "
            DEFVAL { invalid }
            ::= { unisQoSTrafficPriorityEntry 16 }

        unisQoSTrafPrioPolicedServiceDscp OBJECT-TYPE
            SYNTAX Integer32 (0..63 | 255)
            MAX-ACCESS read-create
            STATUS current
            DESCRIPTION
                "The service Dscp of policed Priority"
            DEFVAL { 255 }
            ::= { unisQoSTrafficPriorityEntry 17 }

        unisQoSTrafPrioPolicedServiceExp OBJECT-TYPE
            SYNTAX Integer32 (0..7 | 255)
            MAX-ACCESS read-create
            STATUS current
            DESCRIPTION
                "The service Exp of policed Priority"
            DEFVAL { 255 }
            ::= { unisQoSTrafficPriorityEntry 18 }

        unisQoSTrafPrioPolicedServiceCos OBJECT-TYPE
            SYNTAX Integer32 (0..7 | 255)
            MAX-ACCESS read-create
            STATUS current
            DESCRIPTION
                "The service cos of policed Priority"
            DEFVAL { 255 }
            ::= { unisQoSTrafficPriorityEntry 19 }

        unisQoSTrafPrioPolicedServiceLoaclPre OBJECT-TYPE
            SYNTAX Integer32 (0..7 | 255)
            MAX-ACCESS read-create
            STATUS current
            DESCRIPTION
                "The service local pre of policed Priority"
            DEFVAL { 255 }
            ::= { unisQoSTrafficPriorityEntry 20 }

        unisQoSTrafPrioPolicedServiceDropPriority OBJECT-TYPE
            SYNTAX Integer32 (0..2 | 255)
            MAX-ACCESS read-create
            STATUS current
            DESCRIPTION
                "The service drop priority of proliced Priority"
            DEFVAL { 255 }
            ::= { unisQoSTrafficPriorityEntry 21 }

        unisQoSTrafPrioRowStatus OBJECT-TYPE
            SYNTAX RowStatus
            MAX-ACCESS read-create
            STATUS current
            DESCRIPTION
                "RowStatus,Now support three state:CreateAndGo,Active,Destroy."
            ::= { unisQoSTrafficPriorityEntry 22 }

        unisQoSTrafficFilterTable OBJECT-TYPE
            SYNTAX SEQUENCE OF UnisQoSTrafficFilterEntry
            MAX-ACCESS not-accessible
            STATUS current
            DESCRIPTION
                "Traffic filter table is used to deny or permit packets.
                IP and Link ACL rules can be applied simultaneously,
                IP and User based ACL rules can not be applied simultaneously,
                Link and User based ACL rules can not be applied simultaneously.
                Unused ones is represented with default values.
                To deny or permit packets,the ACL rules should be defined in unisAcl table.
                The 'deny' or 'permit' action should be defined with ACL rules.
                In this table,a predefined ACL rules can be referenced in a specified QOS profile group.
                'Direction' means the ACL rules can be applied to the inbound or outbound packets.

                "
            ::= { unisQoSAction 3 }

        unisQoSTrafficFilterEntry OBJECT-TYPE
            SYNTAX UnisQoSTrafficFilterEntry
            MAX-ACCESS not-accessible
            STATUS current
            DESCRIPTION             " "
            INDEX { unisQoSTrafFilterProfIndex, unisQoSTrafFilterActionIndex }
            ::= { unisQoSTrafficFilterTable 1 }

        UnisQoSTrafficFilterEntry ::=
            SEQUENCE {
                unisQoSTrafFilterProfIndex
                    Integer32,
                unisQoSTrafFilterActionIndex
                    Integer32,
                unisQoSTrafFilterDirection
                    UnisQoSDirection,
                unisQoSTrafFilterUserAclNum
                    Integer32,
                unisQoSTrafFilterUserAclRule
                    Integer32,
                unisQoSTrafFilterIpAclNum
                    Integer32,
                unisQoSTrafFilterIpAclRule
                    Integer32,
                unisQoSTrafFilterLinkAclNum
                    Integer32,
                unisQoSTrafFilterLinkAclRule
                    Integer32,
                unisQoSTrafFilterRowStatus
                    RowStatus
             }

        unisQoSTrafFilterProfIndex OBJECT-TYPE
            SYNTAX Integer32 (1..65535)
            MAX-ACCESS not-accessible
            STATUS current
            DESCRIPTION
                "The index of QoS profile which the traffic-filter action belongs to."
            ::= { unisQoSTrafficFilterEntry 1 }

        unisQoSTrafFilterActionIndex OBJECT-TYPE
            SYNTAX Integer32 (1..65535)
            MAX-ACCESS not-accessible
            STATUS current
            DESCRIPTION
                "The index of traffic-filter action."
            ::= { unisQoSTrafficFilterEntry 2 }

        unisQoSTrafFilterDirection OBJECT-TYPE
            SYNTAX UnisQoSDirection
            MAX-ACCESS read-create
            STATUS current
            DESCRIPTION
                "The direction of traffic-filter action."
            ::= { unisQoSTrafficFilterEntry 3 }

        unisQoSTrafFilterUserAclNum OBJECT-TYPE
            SYNTAX Integer32 (0 | 5000..5999 )
            MAX-ACCESS read-create
            STATUS current
            DESCRIPTION
                "The number of user-based acl group."
            DEFVAL { 0 }
            ::= { unisQoSTrafficFilterEntry 4 }

        unisQoSTrafFilterUserAclRule OBJECT-TYPE
            SYNTAX Integer32 (0..65535)
            MAX-ACCESS read-create
            STATUS current
            DESCRIPTION
                "The subitem of user-based acl rule."
            DEFVAL { 65535 }
            ::= { unisQoSTrafficFilterEntry 5 }

        unisQoSTrafFilterIpAclNum OBJECT-TYPE
            SYNTAX Integer32 (0 | 2000..3999)
            MAX-ACCESS read-create
            STATUS current
            DESCRIPTION
                "The number of Ip-based acl group."
            DEFVAL { 0 }
            ::= { unisQoSTrafficFilterEntry 6 }

        unisQoSTrafFilterIpAclRule OBJECT-TYPE
            SYNTAX Integer32 (0..65535)
            MAX-ACCESS read-create
            STATUS current
            DESCRIPTION
                "The subitem of IP-based acl rule."
            DEFVAL { 65535 }
            ::= { unisQoSTrafficFilterEntry 7 }

        unisQoSTrafFilterLinkAclNum OBJECT-TYPE
            SYNTAX Integer32 (0 | 4000..4999)
            MAX-ACCESS read-create
            STATUS current
            DESCRIPTION
                "The number of Link-based acl group"
            DEFVAL { 0 }
            ::= { unisQoSTrafficFilterEntry 8 }

        unisQoSTrafFilterLinkAclRule OBJECT-TYPE
            SYNTAX Integer32 (0..65535)
            MAX-ACCESS read-create
            STATUS current
            DESCRIPTION
                "The subitem of Link-based acl rule."
            DEFVAL { 65535 }
            ::= { unisQoSTrafficFilterEntry 9 }

        unisQoSTrafFilterRowStatus OBJECT-TYPE
            SYNTAX RowStatus
            MAX-ACCESS read-create
            STATUS current
            DESCRIPTION
                "RowStatus,Now support three state:CreateAndGo,Active,Destroy."
            ::= { unisQoSTrafficFilterEntry 10 }

        unisQoSProfPortMapping OBJECT IDENTIFIER ::= { unisQoSProfObjects 3 }

        unisQoSProfPortMappingTable OBJECT-TYPE
            SYNTAX SEQUENCE OF UnisQoSProfPortMappingEntry
            MAX-ACCESS not-accessible
            STATUS current
            DESCRIPTION
                "Port mapping table is used to apply the qos profile to the port.
                If a qos profile is applied to the port,
                then the port will have an entry in the table."
            ::= { unisQoSProfPortMapping 1 }

        unisQoSProfPortMappingEntry OBJECT-TYPE
            SYNTAX UnisQoSProfPortMappingEntry
            MAX-ACCESS not-accessible
            STATUS current
            DESCRIPTION             " "
            INDEX { unisQoSProfPortMappingIfIndex, unisQoSProfPortMappingProfIndex }
            ::= { unisQoSProfPortMappingTable 1 }

        UnisQoSProfPortMappingEntry ::=
            SEQUENCE {
                unisQoSProfPortMappingIfIndex
                    Integer32,
                unisQoSProfPortMappingProfIndex
                    Integer32,
                unisQoSProfPortMappingRowStatus
                    RowStatus
             }

        unisQoSProfPortMappingIfIndex OBJECT-TYPE
            SYNTAX Integer32 (1..2147483647)
            MAX-ACCESS not-accessible
            STATUS current
            DESCRIPTION
                "The ifindex which the specified QoS profile group is applied to."
            ::= { unisQoSProfPortMappingEntry 1 }

        unisQoSProfPortMappingProfIndex OBJECT-TYPE
            SYNTAX Integer32 (1..65535)
            MAX-ACCESS not-accessible
            STATUS current
            DESCRIPTION
                "The index of specified QoS profile group."
            ::= { unisQoSProfPortMappingEntry 2 }

        unisQoSProfPortMappingRowStatus OBJECT-TYPE
            SYNTAX RowStatus
            MAX-ACCESS read-create
            STATUS current
            DESCRIPTION
                "RowStatus,Now support three state:CreateAndGo,Active,Destroy."
            ::= { unisQoSProfPortMappingEntry 3 }

        unisQoSProfPortMappingModeTable OBJECT-TYPE
            SYNTAX SEQUENCE OF UnisQoSProfPortMappingModeEntry
            MAX-ACCESS not-accessible
            STATUS current
            DESCRIPTION
                "Port mapping mode table is used to set mapping mode of the port.
                When a qos profile is applied to a port, the profile can have two working ways:
                1)The profile is the same for all the users connected to the port;
                2)The profile can be different for different users connected to the port;
                Port-based mode means the profile is the same for all the users.
                User-based mode means the profile is different for different users.
                Default value is port-based."
            ::= { unisQoSProfPortMapping 2 }

        unisQoSProfPortMappingModeEntry OBJECT-TYPE
            SYNTAX UnisQoSProfPortMappingModeEntry
            MAX-ACCESS not-accessible
            STATUS current
            DESCRIPTION             " "
            INDEX { unisQoSProfPortMappingModeIfIndex }
            ::= { unisQoSProfPortMappingModeTable 1 }

        UnisQoSProfPortMappingModeEntry ::=
            SEQUENCE {
                unisQoSProfPortMappingModeIfIndex
                    Integer32,
                unisQoSProfPortMappingMode
                    INTEGER
             }

        unisQoSProfPortMappingModeIfIndex OBJECT-TYPE
            SYNTAX Integer32 (1..2147483647)
            MAX-ACCESS not-accessible
            STATUS current
            DESCRIPTION
                "The ifindex which the QoS profile mapping mode is applied to."
            ::= { unisQoSProfPortMappingModeEntry 1 }

        unisQoSProfPortMappingMode OBJECT-TYPE
            SYNTAX INTEGER
                {
                user-based(1),
                port-based(2)
                }
            MAX-ACCESS read-write
            STATUS current
            DESCRIPTION
                "The QoS profile mapping mode of specifed port."
            DEFVAL { 2 }
            ::= { unisQoSProfPortMappingModeEntry 2 }

        unisQoSProfDynPortMappingTable OBJECT-TYPE
            SYNTAX SEQUENCE OF UnisQoSProfDynPortMappingEntry
            MAX-ACCESS not-accessible
            STATUS current
            DESCRIPTION
                "Dynamic port mapping table is used to get user' port,MAC address,IP address,VLAN ID and user-specified qos profiles.
                Network managers can allocate different QOS profile groups to different users.
                Once the user is on line, then the user-specified QOS profiles will be dynamically applied to the port the user connects.
                Each port can have different groups of users simultaneously connected.
                Each group of users can have assiociation with multiple QOS profiles simultaneously.
                So the user's port,MAC address,IP address and VLAN ID will replace the source information in the ACL rules refered in the QOS profiles.
                Once the user is off line, then the user-specified QOS profiles will be dynamically deleted from the port the user connects."
            ::= { unisQoSProfPortMapping 3 }

        unisQoSProfDynPortMappingEntry OBJECT-TYPE
            SYNTAX UnisQoSProfDynPortMappingEntry
            MAX-ACCESS not-accessible
            STATUS current
            DESCRIPTION             " "
            INDEX { unisQoSProfDynPortMappingIfIndex, unisQoSProfDynPortMappingUserSrcMAC }
            ::= { unisQoSProfDynPortMappingTable 1 }

        UnisQoSProfDynPortMappingEntry ::=
            SEQUENCE {
                unisQoSProfDynPortMappingIfIndex
                    Integer32,
                unisQoSProfDynPortMappingUserSrcMAC
                    MacAddress,
                unisQoSProfDynPortMappingUserName
                    OCTET STRING,
                unisQoSProfDynPortMappingUserIPAddr
                    IpAddress,
                unisQoSProfDynPortMappingUserVLANID
                    Integer32,
                unisQoSProfDynPortMappingUserProfName
                    OCTET STRING
             }

        unisQoSProfDynPortMappingIfIndex OBJECT-TYPE
            SYNTAX Integer32 (1..2147483647)
            MAX-ACCESS not-accessible
            STATUS current
            DESCRIPTION
                "if index of the port user profile is applied."
            ::= { unisQoSProfDynPortMappingEntry 1 }

        unisQoSProfDynPortMappingUserSrcMAC OBJECT-TYPE
            SYNTAX MacAddress
            MAX-ACCESS not-accessible
            STATUS current
            DESCRIPTION
                "User sourc MAC address."
            ::= { unisQoSProfDynPortMappingEntry 2 }

        unisQoSProfDynPortMappingUserName OBJECT-TYPE
            SYNTAX OCTET STRING (SIZE (1..32))
            MAX-ACCESS read-only
            STATUS current
            DESCRIPTION
                "User name."
            ::= { unisQoSProfDynPortMappingEntry 3 }

        unisQoSProfDynPortMappingUserIPAddr OBJECT-TYPE
            SYNTAX IpAddress
            MAX-ACCESS read-only
            STATUS current
            DESCRIPTION
                "User IP address"
            ::= { unisQoSProfDynPortMappingEntry 4 }

        unisQoSProfDynPortMappingUserVLANID OBJECT-TYPE
            SYNTAX Integer32 (1..65535)
            MAX-ACCESS read-only
            STATUS current
            DESCRIPTION
                "User VLAN ID."
            ::= { unisQoSProfDynPortMappingEntry 5 }

        unisQoSProfDynPortMappingUserProfName OBJECT-TYPE
            SYNTAX OCTET STRING (SIZE (1..32))
            MAX-ACCESS read-only
            STATUS current
            DESCRIPTION
                "User profile name."
            ::= { unisQoSProfDynPortMappingEntry 6 }

        unisQoSProfPortMappingTraps OBJECT IDENTIFIER ::= { unisQosProfile 2 }

        unisQoSProfPortMappingError NOTIFICATION-TYPE
            STATUS current
            DESCRIPTION
                "An unisQoSProfPortMappingError notification is generated
                when a qos profile fails to be applied on the port."
            ::= { unisQoSProfPortMappingTraps 1 }

        unisQoSProfMibConformance OBJECT IDENTIFIER ::= { unisQosProfile 3 }

        unisQoSProfMibCompliances OBJECT IDENTIFIER ::= { unisQoSProfMibConformance 1 }

        unisQoSProfMibCompliance MODULE-COMPLIANCE
            STATUS current
            DESCRIPTION
                "The compliance statement for QoS Profile MIB."
            MODULE -- this module
                MANDATORY-GROUPS { unisQoSProfGroup, unisQoSActionGroup, unisQoSProfPortMappingGroup, unisQoSProfPortMappingTrapsGroup }
            ::= { unisQoSProfMibCompliances 1 }

        unisQoSProfMibGroups OBJECT IDENTIFIER ::= { unisQoSProfMibConformance 2 }

        unisQoSProfGroup OBJECT-GROUP
            OBJECTS { unisQoSProfName, unisQoSProfActionNumber, unisQoSProfRowStatus }
            STATUS current
            DESCRIPTION
                "Included table:
                unisQoSProfTable."
            ::= { unisQoSProfMibGroups 1 }

        unisQoSActionGroup OBJECT-GROUP
            OBJECTS { unisQoSTrafLmtDirection, unisQoSTrafLmtUserAclNum, unisQoSTrafLmtUserAclRule, unisQoSTrafLmtIpAclNum, unisQoSTrafLmtIpAclRule,
                unisQoSTrafLmtLinkAclNum, unisQoSTrafLmtLinkAclRule, unisQoSTrafLmtTargetRateMbps, unisQoSTrafLmtTargetRateKbps, unisQoSTrafLmtPeakRate,
                unisQoSTrafLmtCIR, unisQoSTrafLmtCBS, unisQoSTrafLmtEBS, unisQoSTrafLmtPIR, unisQoSTrafLmtConformLocalPre,
                unisQoSTrafLmtConformActionType, unisQoSTrafLmtExceedActionType, unisQoSTrafLmtExceedDscp, unisQoSTrafLmtExceedCos, unisQoSTrafLmtRowStatus,
                unisQoSTrafLmtConformCos,unisQoSTrafLmtConformDscp,
                unisQoSTrafPrioDirection, unisQoSTrafPrioUserAclNum, unisQoSTrafPrioUserAclRule, unisQoSTrafPrioIpAclNum, unisQoSTrafPrioIpAclRule,
                unisQoSTrafPrioLinkAclNum, unisQoSTrafPrioLinkAclRule, unisQoSTrafPrioDscp, unisQoSTrafPrioIpPre, unisQoSTrafPrioIpPreFromCos,
                unisQoSTrafPrioCos, unisQoSTrafPrioCosFromIpPre, unisQoSTrafPrioLocalPre, unisQoSTrafPrioPolicedServiceType, unisQoSTrafPrioPolicedServiceDscp,
                unisQoSTrafPrioPolicedServiceExp, unisQoSTrafPrioPolicedServiceCos, unisQoSTrafPrioPolicedServiceLoaclPre, unisQoSTrafPrioPolicedServiceDropPriority, unisQoSTrafPrioRowStatus,
                unisQoSTrafFilterDirection, unisQoSTrafFilterUserAclNum, unisQoSTrafFilterUserAclRule, unisQoSTrafFilterIpAclNum, unisQoSTrafFilterIpAclRule,
                unisQoSTrafFilterLinkAclNum, unisQoSTrafFilterLinkAclRule, unisQoSTrafFilterRowStatus }
            STATUS current
            DESCRIPTION
                "Included table:
                1)unisQoSTrafficLimitTable.
                2)unisQoSTrafficPriorityTable.
                3)unisQoSTrafficFilterTable
                "
            ::= { unisQoSProfMibGroups 2 }

        unisQoSProfPortMappingGroup OBJECT-GROUP
            OBJECTS { unisQoSProfPortMappingRowStatus, unisQoSProfPortMappingMode, unisQoSProfDynPortMappingUserName, unisQoSProfDynPortMappingUserIPAddr, unisQoSProfDynPortMappingUserVLANID,
                unisQoSProfDynPortMappingUserProfName }
            STATUS current
            DESCRIPTION
                "Included tables:
                1)unisQoSProfPortMappingTable.
                2)unisQoSProfPortMappingModeTable.
                3)unisQoSProfDynPortMappingTable.
                "
            ::= { unisQoSProfMibGroups 3 }

        unisQoSProfPortMappingTrapsGroup NOTIFICATION-GROUP
            NOTIFICATIONS { unisQoSProfPortMappingError }
            STATUS current
            DESCRIPTION
                "Included:
                unisQoSProfPortMappingTraps."
            ::= { unisQoSProfMibGroups 4 }


    END
