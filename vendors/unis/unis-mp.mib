-- =================================================================
-- Copyright (c) 2020 Unisyue Technologies Co., Ltd.  All rights reserved.
-- 
-- Description: This MIB file is used for inquiring for MP (Multilink PPP)
--              link status information.
-- Reference:
-- Version: V1.0
-- History:
--   V1.0 tianli,2004.5.18,publish 
-- =================================================================

UNIS-MP-MIB DEFINITIONS ::= BEGIN

        IMPORTS
            ifIndex			
                FROM RFC1213-MIB
            unisRhw
                FROM UNIS-OID-MIB                                                     
            OBJECT-GROUP, MODULE-COMPLIANCE                 
                FROM SNMPv2-CONF                        
            Integer32, Counter32, OBJECT-TYPE, MODULE-IDENTITY                   
                FROM SNMPv2-SMI
            TEXTUAL-CONVENTION, DisplayString
                FROM SNMPv2-TC;        

        unisMultilinkPPP MODULE-IDENTITY 
                LAST-UPDATED "200405180000Z"            -- May 18, 2004 at 00:00 GMT
                ORGANIZATION
                    "Unisyue Technologies Co., Ltd."
                CONTACT-INFO
                    ""
                DESCRIPTION 
                        "The UNIS-MP-MIB provides read access to MP(Multilink PPP) link
                        status information. The information available through this MIB includes:
                        the father channel, the bundled son channel, the slot on which MP bundled, 
                        the number of son channels, the bundle name,
                        the statistic of lost fragments, reordered packets, unassigned packets, 
                        interleaved packets, and the received/sent sequence, etc.
                        "
                ::= { unisRhw 33 }

--
-- Node definitions
--        
        
        unisMpObjects OBJECT IDENTIFIER ::= { unisMultilinkPPP  1 }
        
        unisMpMultilinkTable OBJECT-TYPE
                SYNTAX SEQUENCE OF UnisMpMultilinkEntry
                MAX-ACCESS not-accessible
                STATUS current
                DESCRIPTION
                        "This table describes the information of MP link. 
                        The index of this table is the interface index of MP group or 
                        VT(Virtual Template)."
                ::= { unisMpObjects 1 }

        unisMpMultilinkEntry OBJECT-TYPE
                SYNTAX UnisMpMultilinkEntry
                MAX-ACCESS not-accessible
                STATUS current
                DESCRIPTION
                        "Each entry in this table describes the information of MP link.
                        The available information includes: 
                        the father channel, the slot on which MP bundled, 
                        the number of bundled son channels, 
                        the statistics of lost fragments, reordered packets, 
                        unassigned packets, interleaved packets, 
                        and received/sent sequence.                         
                        "
                INDEX { ifIndex }
                ::= { unisMpMultilinkTable 1 }
        
        UnisMpMultilinkEntry ::=
                SEQUENCE {
                        unisMpMultilinkDescr
                                DisplayString,   
                        unisMpBundleName
                                DisplayString,                                               
                        unisMpBundledSlot
                                Integer32,
                        unisMpBundledMemberCnt
                                Integer32,
			unisMpLostFragments
				Counter32,
			unisMpReorderedPkts
				Counter32,
			unisMpUnassignedPkts
				Counter32,
			unisMpInterleavedPkts
				Counter32,
			unisMpRcvdSequence
				Integer32,
			unisMpSentSequence
				Integer32																														
                 } 
                                         
        unisMpMultilinkDescr OBJECT-TYPE
                SYNTAX DisplayString
                MAX-ACCESS read-only
                STATUS current
                DESCRIPTION
                        "The interface name of the father interface on which MP bundled. 
                        It is the name of a Virtual Temblate or a MP group."
                ::= { unisMpMultilinkEntry 1 } 
                
        unisMpBundleName OBJECT-TYPE
                SYNTAX DisplayString
                MAX-ACCESS read-only
                STATUS current
                DESCRIPTION
                        "The bundle name of the multilink. 
                        when authentication is configured, the bundle name is the authenticated
                        user name; when authentication not configured, the bundle name is
                        multilink.
                        "
                ::= { unisMpMultilinkEntry 2 }                 
                
        unisMpBundledSlot OBJECT-TYPE
                SYNTAX Integer32
                MAX-ACCESS read-only
                STATUS current
                DESCRIPTION
                        "The slot on which MP bundled. 
                        "
                ::= { unisMpMultilinkEntry 3 }
        
        unisMpBundledMemberCnt OBJECT-TYPE
                SYNTAX Integer32
                MAX-ACCESS read-only
                STATUS current
                DESCRIPTION
                        "The number of the bundled son channel of the MP link. "
                ::= { unisMpMultilinkEntry 4 }

        unisMpLostFragments OBJECT-TYPE
                SYNTAX Counter32
                MAX-ACCESS read-only
                STATUS current
                DESCRIPTION
                        "The number of fragments of the MP link discarded because 
                        bad fragments received, or assembling packet failed, etc."
                ::= { unisMpMultilinkEntry 5 }

         unisMpReorderedPkts OBJECT-TYPE
                SYNTAX Counter32
                MAX-ACCESS read-only
                STATUS current
                DESCRIPTION
                        "The number of received packets of the MP link reordered.
                        "
                ::= { unisMpMultilinkEntry 6 }                       

         unisMpUnassignedPkts OBJECT-TYPE
                SYNTAX Counter32
                MAX-ACCESS read-only
                STATUS current
                DESCRIPTION
                        "The number of received packets of the MP link waiting for reordering.
                        "
                ::= { unisMpMultilinkEntry 7 }      
                
         unisMpInterleavedPkts OBJECT-TYPE
                SYNTAX Counter32
                MAX-ACCESS read-only
                STATUS current
                DESCRIPTION
                        "The number of received packets of the MP link interleaved by the 
                        packets queued in RTPQ(Real-time Transport Protocol Queue) or 
                        LLQ(Low Latency Queue).
                        "
                ::= { unisMpMultilinkEntry 8 }  
                
         unisMpRcvdSequence OBJECT-TYPE
                SYNTAX Integer32
                MAX-ACCESS read-only
                STATUS current
                DESCRIPTION
                        "The current sequence number of the MP link for receiving.
                        "
                ::= { unisMpMultilinkEntry 9 }   

         unisMpSentSequence OBJECT-TYPE
                SYNTAX Integer32
                MAX-ACCESS read-only
                STATUS current
                DESCRIPTION
                        "The current sequence number of the MP link for sending.
                        "
                ::= { unisMpMultilinkEntry 10 }


        unisMpMemberlinkTable OBJECT-TYPE
                SYNTAX SEQUENCE OF UnisMpMemberlinkEntry
                MAX-ACCESS not-accessible
                STATUS current
                DESCRIPTION
                        "This table describes the information of son channels of the MP link.
                        The index of this table is the interface index of MP group or
                        VT(Virtual Template). 
                        "
                ::= { unisMpObjects 2 }

        unisMpMemberlinkEntry OBJECT-TYPE
                SYNTAX UnisMpMemberlinkEntry
                MAX-ACCESS not-accessible
                STATUS current
                DESCRIPTION
                        "Each entry in this table describes the information of the bundled
                        son channels of MP link. The available information includes: 
                        the interface index of the son channel, 
                        the interface name of the son channel.
                        "
                INDEX { ifIndex, unisMpMemberlinkSeqNumber }
                ::= { unisMpMemberlinkTable 1 }
        
        UnisMpMemberlinkEntry ::=
                SEQUENCE {
                        unisMpMemberlinkSeqNumber
                                Integer32,
                        unisMpMemberlinkIfIndex
                                Integer32,
                        unisMpMemberlinkDescr
                                DisplayString,
                        unisMpMemberlinkMpStatus
                                Integer32																													
                 } 

        unisMpMemberlinkSeqNumber OBJECT-TYPE
                SYNTAX Integer32
                MAX-ACCESS read-only
                STATUS current
                DESCRIPTION
                        "The bundled sequence number of the son channels of the MP link.
                        This object is one of the index of the table.
                        "
                ::= { unisMpMemberlinkEntry 1 }  

        unisMpMemberlinkIfIndex OBJECT-TYPE
                SYNTAX Integer32
                MAX-ACCESS read-only
                STATUS current
                DESCRIPTION
                        "The interface index of the son channels of the MP link.
                        "
                ::= { unisMpMemberlinkEntry 2 } 
                
        unisMpMemberlinkDescr OBJECT-TYPE
                SYNTAX DisplayString
                MAX-ACCESS read-only
                STATUS current
                DESCRIPTION
                        "The interface name of the son channels of the MP link.
                        "
                ::= { unisMpMemberlinkEntry 3 } 
                
        unisMpMemberlinkMpStatus OBJECT-TYPE
                SYNTAX Integer32
                MAX-ACCESS read-only
                STATUS current
                DESCRIPTION
                        "The MP status of the son channels of the MP link.
                        "
                ::= { unisMpMemberlinkEntry 4 } 
                                
         unisMpNotifications OBJECT IDENTIFIER ::= { unisMultilinkPPP 2 }

         
         unisMpConformance OBJECT IDENTIFIER ::= { unisMultilinkPPP 3 }

         
         unisMpCompliances OBJECT IDENTIFIER ::= { unisMpConformance 1 }

         
         unisMpCompliance MODULE-COMPLIANCE
                 STATUS current
                 DESCRIPTION 
                         "The compliance statement for entities which 
                         implement the Multilink PPP MIB."
                 MODULE -- this module
                         MANDATORY-GROUPS { unisMpMandatoryGroup }
                 ::= { unisMpCompliances 1 }

         
         unisMpGroups OBJECT IDENTIFIER ::= { unisMpConformance 2 }

         
         unisMpMandatoryGroup OBJECT-GROUP
                 OBJECTS { unisMpBundledMemberCnt, unisMpMemberlinkSeqNumber, unisMpMemberlinkIfIndex }
                 STATUS current
                 DESCRIPTION 
                         "A collection of objects providing mandatory MP information."
                 ::= { unisMpGroups 1 }
         
         unisMpInfoGroup OBJECT-GROUP
                 OBJECTS { unisMpMultilinkDescr, unisMpBundleName, 
                         unisMpBundledSlot, unisMpBundledMemberCnt,
                         unisMpLostFragments, unisMpReorderedPkts, 
                         unisMpUnassignedPkts, unisMpInterleavedPkts, 
                         unisMpRcvdSequence, unisMpSentSequence,
                         unisMpMemberlinkDescr,unisMpMemberlinkMpStatus }
                 STATUS current
                 DESCRIPTION 
                         "All running information of MP feature."
                 ::= { unisMpGroups 2 }                                                                                        
                                                                                                                                                                                    
   END
