-- ===========================================================================================================
-- Copyright (c) 2020 Unisyue Technologies Co., Ltd.  All rights reserved.
--
-- Description: ISSU MIB
-- Reference:
-- Version: V1.2
-- History:
--  Revision 1.0 2012-12-20 created by Wang Feng
--               2013-4-20 modified by Zhu Liuxing
--  Revision 1.1 2014-01-10 change unisIssuUpgradeImageIndex and
--               unisIssuUpgradeImageURL range by z03030
--  Revision 1.2 2018-04-08 change unisIssuUpgradeImageType by l07660
-- ============================================================================================================

UNIS-ISSU-MIB DEFINITIONS ::= BEGIN

IMPORTS
    unisCommon
        FROM UNIS-OID-MIB
    Integer32, OBJECT-TYPE, MODULE-IDENTITY, NOTIFICATION-TYPE
        FROM SNMPv2-SMI
    DisplayString, RowStatus, TruthValue
        FROM SNMPv2-TC;

unisIssuUpgrade MODULE-IDENTITY
    LAST-UPDATED "201301151536Z"        -- January 15, 2013 at 15:36 GMT
    ORGANIZATION
        "Unisyue Technologies Co., Ltd."
    CONTACT-INFO
        ""
    DESCRIPTION
        "This MIB provides objects for upgrading images on modules in the
        system, objects for showing the result of an upgrade operation,
        and objects for showing the result of a test operation.

        To perform an upgrade operation, a management application
        must first read the unisIssuUpgradeImageTable table and use the
        information in other tables, as explained below.  You can
        configure a new image name for each image type as listed in
        unisIssuUpgradeImageTable.  The system will use this image on the
        particular module at the next reboot.

        The management application used to perform an upgrade
        operation must first check if an upgrade operation is already
        in progress in the system.  This is done by reading the
        unisIssuOpType ('none' indicates that
        no other upgrade operation is in progress.  Any other value
        indicates that an upgrade is already in progress and a new upgrade
        operation is not allowed.  To start an 'install' operation,
        the user must first perform a 'test' operation to examine the
        version compatibility between the given set of images
        and the running images.  Only if the result of the 'test'
        operation is 'success' can the user proceed to do an install
        operation.  The table unisIssuTestResultTable
        provides the result of the 'test' operation performed by using unisIssuOpType.
        The table unisIssuUpgradeResultTable provides the result of the 'install' operation
        performed by using unisIssuOpType.
        "
    REVISION "201301151536Z"        -- January 15, 2013 at 15:36 GMT
    DESCRIPTION
        "Initial version of this MIB module.
        Added unisIssuUpgradeImageTable unisIssuOp unisIssuCompatibleResult
        unisIssuTestResultTable unisIssuUpgradeResultTable"
    ::= { unisCommon 133 }

--
-- Node definitions
--

unisIssuUpgradeMibObjects OBJECT IDENTIFIER ::= { unisIssuUpgrade 1 }


unisIssuUpgradeGroup OBJECT IDENTIFIER ::= { unisIssuUpgradeMibObjects 1 }


unisIssuUpgradeImageTable OBJECT-TYPE
    SYNTAX SEQUENCE OF UnisIssuUpgradeImageEntry
    MAX-ACCESS not-accessible
    STATUS current
    DESCRIPTION
        "A table listing the image variable types that
        exist in the device."
    ::= { unisIssuUpgradeGroup 1 }


unisIssuUpgradeImageEntry OBJECT-TYPE
    SYNTAX UnisIssuUpgradeImageEntry
    MAX-ACCESS not-accessible
    STATUS current
    DESCRIPTION
        "An unisIssuUpgradeImageEntry entry.  Each entry provides an
        image variable type that exists in the device."
    INDEX { unisIssuUpgradeImageIndex }
    ::= { unisIssuUpgradeImageTable 1 }


UnisIssuUpgradeImageEntry ::=
    SEQUENCE {
        unisIssuUpgradeImageIndex
            Integer32,
        unisIssuUpgradeImageType
            INTEGER,
        unisIssuUpgradeImageURL
            DisplayString,
        unisIssuUpgradeImageRowStatus
            RowStatus
     }

unisIssuUpgradeImageIndex OBJECT-TYPE
    SYNTAX Integer32 (1..2147483647)
    MAX-ACCESS not-accessible
    STATUS current
    DESCRIPTION
        "Index of each image."
    ::= { unisIssuUpgradeImageEntry 1 }


unisIssuUpgradeImageType OBJECT-TYPE
    SYNTAX INTEGER
        {
        boot(1),
        system(2),
        feature(3),
        ipe(4),
        patch(5)
        }
    MAX-ACCESS read-create
    STATUS current
    DESCRIPTION
        "Types of images that the system can run.  The value of
        this object has five image variable names:
        'boot', 'system', 'feature', 'ipe' and 'patch'.  This table will then
        list these five strings as follows:

              unisIssuUpgradeImageType
                  boot
                  system
                  feature
                  IPE
                  patch

              The user can assign images (using unisIssuUpgradeImageURL)
              to these variables and the system will use the assigned
              images to boot."
    ::= { unisIssuUpgradeImageEntry 2 }


unisIssuUpgradeImageURL OBJECT-TYPE
    SYNTAX DisplayString (SIZE (1..127))
    MAX-ACCESS read-create
    STATUS current
    DESCRIPTION
        "This object contains the path of the image
        of this entity."
    ::= { unisIssuUpgradeImageEntry 3 }


unisIssuUpgradeImageRowStatus OBJECT-TYPE
    SYNTAX RowStatus
    MAX-ACCESS read-create
    STATUS current
    DESCRIPTION
        "Row-status of image table."
    ::= { unisIssuUpgradeImageEntry 4 }


unisIssuOp OBJECT IDENTIFIER ::= { unisIssuUpgradeGroup 2 }


unisIssuOpType OBJECT-TYPE
    SYNTAX INTEGER
        {
        none(1),
        done(2),
        test(3),
        install(4),
        rollback(5)
        }
    MAX-ACCESS read-write
    STATUS current
    DESCRIPTION
        "Command to be executed.
        The 'test' command must be performed before the 'install'
        command can be executed.  The 'install'
        command is allowed only if a read of
        this object returns 'test' and the value of object
        unisIssuOpStatus is 'success'.

        Command                 Remarks

        none      If the user sets this object to 'none', the agent will return a success
                  without performing an upgrade operation.
        done      If this object returns any value other than
                  'none', setting this to 'done' will do
                  the required cleanup of the previous upgrade
                  operation and get the system ready for a new
                  upgrade operation.
        test      Check the version compatibility and upgrade method
                  for the given set of image files.
        install   For all the image entities listed in the
                  unisIssuUpgradeImageTable, perform the required
                  upgrade operation listed in that table.
        rollback  Abort the current 'install' operation and roll back
                  to the previous version.
          "
    DEFVAL { none }
    ::= { unisIssuOp 1 }


unisIssuImageFileOverwrite OBJECT-TYPE
    SYNTAX TruthValue
    MAX-ACCESS read-write
    STATUS current
    DESCRIPTION
        "If you want to overwrite the existing file, set the value of
        this object to enable.  Otherwise, set the value of this
        object to disable."
    DEFVAL { true }
    ::= { unisIssuOp 2 }


unisIssuOpTrapEnable OBJECT-TYPE
    SYNTAX TruthValue
    MAX-ACCESS read-write
    STATUS current
    DESCRIPTION
        "If you want to enable the trap, set the value of
        this object to enable.  Otherwise, set the value of this
        object to disable."
    DEFVAL { true }
    ::= { unisIssuOp 3 }


unisIssuOpStatus OBJECT-TYPE
    SYNTAX INTEGER
        {
        none(1),
        failure(2),
        inProgress(3),
        success(4),
        rollbackInProgress(5),
        rollbackSuccess(6)
        }
    MAX-ACCESS read-only
    STATUS current
    DESCRIPTION
        "Status of the specified operation.
        none                - No operation was performed.
        failure             - Specified operation has failed.
        inProgress          - Specified operation is in progress.
        success             - Specified operation completed successfully.
        rollbackInProgress     - Rollback operation is in progress.
        rollbackSuccess        - Rollback operation completed successfully.
          "
    DEFVAL { none }
    ::= { unisIssuOp 4 }


unisIssuFailedReason OBJECT-TYPE
    SYNTAX DisplayString (SIZE (0..255))
    MAX-ACCESS read-only
    STATUS current
    DESCRIPTION
        "Indicates the the cause of 'failure' state
        of the object 'unisIssuOpStatus'.
        This object would be a null string if the value of
        'unisIssuOpStatus' is not 'failure'."
    ::= { unisIssuOp 5 }


unisIssuOpTimeCompleted OBJECT-TYPE
    SYNTAX DisplayString (SIZE (0..255))
    MAX-ACCESS read-only
    STATUS current
    DESCRIPTION
        "Indicates the time when the upgrade operation was completed.
        This object would be a null string if unisIssuOpType is
        'none'. "
    ::= { unisIssuOp 6 }


unisIssuLastOpType OBJECT-TYPE
    SYNTAX INTEGER
        {
        none(1),
        done(2),
        test(3),
        install(4),
        rollback(5)
        }
    MAX-ACCESS read-only
    STATUS current
    DESCRIPTION
        "This object indicates the previous unisIssuOp value.
        It will be updated after a new unisIssuOp is set and delivered
        to the upgrade process.

        Command                 Remarks

        none      If the user sets this object to 'none', agent will return a success
                  without performing an upgrade operation.
        done      If this object returns any value other than
                  'none', setting this to 'done' will do
                  the required cleanup of the previous upgrade
                  operation and get the system ready for a new
                  upgrade operation.
        test      Check the version compatibility and upgrade method
                  for the given set of image files.
        install   For all the image entities listed in the
                  unisIssuUpgradeImageTable, perform the required
                  upgrade operation listed in that table.
        rollback  Abort the current install operation and roll back
                  to the previous version.
        "
    DEFVAL { none }
    ::= { unisIssuOp 7 }


unisIssuLastOpStatus OBJECT-TYPE
    SYNTAX INTEGER
        {
        none(1),
        failure(2),
        inProgress(3),
        success(4),
        rollbackInProgress(5),
        rollbackSuccess(6)
        }
    MAX-ACCESS read-only
    STATUS current
    DESCRIPTION
        "This object indicates previous unisIssuOpStatus value.
        It will be updated after new unisIssuOp is set and delivered
        to upgrade process.
        none                - No operation was performed.
        failure             - Specified operation has failed.
        inProgress          - Specified operation is active.
        success             - Specified operation completed successfully.
        rollbackInProgress     - Rollback operation is in progress.
        rollbackSuccess        - Rollback operation completed successfully.
        "
    DEFVAL { none }
    ::= { unisIssuOp 8 }


unisIssuLastOpFailedReason OBJECT-TYPE
    SYNTAX DisplayString (SIZE (0..255))
    MAX-ACCESS read-only
    STATUS current
    DESCRIPTION
        "Indicates the cause of 'failure' state
        of the object 'unisIssuOpStatus'.
        This object would be a null string if the value of
        'unisIssuOpStatus' is not 'failure'.
        The value will be updated when new unisIssuOp is set
        and delivered to the upgrade process."
    ::= { unisIssuOp 9 }


unisIssuLastOpTimeCompleted OBJECT-TYPE
    SYNTAX DisplayString (SIZE (0..255))
    MAX-ACCESS read-only
    STATUS current
    DESCRIPTION
        "Indicates the previous unisIssuOpTimeCompleted value.
        The value will be updated when new unisIssuOp is set
        and delivered to the upgrade process."
    ::= { unisIssuOp 10 }


unisIssuUpgradeResultGroup OBJECT IDENTIFIER ::= { unisIssuUpgradeMibObjects 2 }


unisIssuCompatibleResult OBJECT IDENTIFIER ::= { unisIssuUpgradeResultGroup 1 }


unisIssuCompatibleResultStatus OBJECT-TYPE
    SYNTAX INTEGER
        {
        none(1),
        inCompatible(2),
        compatible(3),
        failure(4)
        }
    MAX-ACCESS read-only
    STATUS current
    DESCRIPTION
        "Specifies whether the images provided in
        unisIssuUpgradeImageTable are compatible with each other as
        far as this module is concerned.
        none            - No operation was performed.
        inCompatible    - The images provided are compatible
                          and can be run on this module.
        compatible      - The images provided are incompatible
                          and can be run on this module.
        failure         - Failed to get the compatibility.
        "
    DEFVAL { none }
    ::= { unisIssuCompatibleResult 1 }


unisIssuCompatibleResultFailedReason OBJECT-TYPE
    SYNTAX DisplayString (SIZE (0..255))
    MAX-ACCESS read-only
    STATUS current
    DESCRIPTION
        "Indicates the cause of 'failure' state
        of the object 'unisIssuCompatibleResultStatus'.
        This object would be a null string if the value of
        'unisIssuCompatibleResultStatus' is not 'failure'."
    ::= { unisIssuCompatibleResult 2 }


unisIssuTestResultTable OBJECT-TYPE
    SYNTAX SEQUENCE OF UnisIssuTestResultEntry
    MAX-ACCESS not-accessible
    STATUS current
    DESCRIPTION
        "Shows the result of the test operation, from which you can
        see the upgrade method."
    ::= { unisIssuUpgradeResultGroup 2 }


unisIssuTestResultEntry OBJECT-TYPE
    SYNTAX UnisIssuTestResultEntry
    MAX-ACCESS not-accessible
    STATUS current
    DESCRIPTION
        "An unisIssuTestResultEntry entry.  Each entry provides the
        test result of a card in the device."
    INDEX { unisIssuTestResultIndex }
    ::= { unisIssuTestResultTable 1 }


UnisIssuTestResultEntry ::=
    SEQUENCE {
        unisIssuTestResultIndex
            Integer32,
        unisIssuTestDeviceChassisID
            Integer32,
        unisIssuTestDeviceSlotID
            Integer32,
        unisIssuTestDeviceCpuID
            Integer32,
        unisIssuTestDeviceUpgradeWay
            INTEGER
     }

unisIssuTestResultIndex OBJECT-TYPE
    SYNTAX Integer32 (1..65535)
    MAX-ACCESS not-accessible
    STATUS current
    DESCRIPTION
        "Internal index, not accessible."
    ::= { unisIssuTestResultEntry 1 }


unisIssuTestDeviceChassisID OBJECT-TYPE
    SYNTAX Integer32 (0..255)
    MAX-ACCESS read-only
    STATUS current
    DESCRIPTION
        "Chassis ID of the card."
    ::= { unisIssuTestResultEntry 2 }


unisIssuTestDeviceSlotID OBJECT-TYPE
    SYNTAX Integer32 (0..255)
    MAX-ACCESS read-only
    STATUS current
    DESCRIPTION
        "Slot ID of the card."
    ::= { unisIssuTestResultEntry 3 }


unisIssuTestDeviceCpuID OBJECT-TYPE
    SYNTAX Integer32 (0..7)
    MAX-ACCESS read-only
    STATUS current
    DESCRIPTION
        "CPU ID of the card."
    ::= { unisIssuTestResultEntry 4 }


unisIssuTestDeviceUpgradeWay OBJECT-TYPE
    SYNTAX INTEGER
        {
        none(1),
        reboot(2),
        sequenceReboot(3),
        issuReboot(4),
        serviceUpgrade(5),
        fileUpgrade(6),
        incompatibleUpgrade(7)
        }
    MAX-ACCESS read-only
    STATUS current
    DESCRIPTION
        "Upgrade method of the device.
        none                   - No operation was performed.
        reboot                 - The upgrade method of this device is Reboot.
        sequenceReboot         - The upgrade method of this device is SequenceReboot.
        issuReboot             - The upgrade method of this device is IssuReboot.
        serviceUpgrade         - The upgrade method of this device is ServiceReboot.
        fileUpgrade            - The upgrade method of this device is FileReboot.
        incompatibleUpgrade    - The upgrade method of this device is IncompatibleUpgrade.
        "
    DEFVAL { none }
    ::= { unisIssuTestResultEntry 5 }


unisIssuUpgradeResultTable OBJECT-TYPE
    SYNTAX SEQUENCE OF UnisIssuUpgradeResultEntry
    MAX-ACCESS not-accessible
    STATUS current
    DESCRIPTION
        "Shows the result of the install operation."
    ::= { unisIssuUpgradeResultGroup 3 }


unisIssuUpgradeResultEntry OBJECT-TYPE
    SYNTAX UnisIssuUpgradeResultEntry
    MAX-ACCESS not-accessible
    STATUS current
    DESCRIPTION
        "An unisIssuUpgradeResultEntry entry.  Each entry provides the
        upgrade result of a card in the device."
    INDEX { unisIssuUpgradeResultIndex }
    ::= { unisIssuUpgradeResultTable 1 }


UnisIssuUpgradeResultEntry ::=
    SEQUENCE {
        unisIssuUpgradeResultIndex
            Integer32,
        unisIssuUpgradeDeviceChassisID
            Integer32,
        unisIssuUpgradeDeviceSlotID
            Integer32,
        unisIssuUpgradeDeviceCpuID
            Integer32,
        unisIssuUpgradeState
            INTEGER,
        unisIssuDeviceUpgradeWay
            INTEGER,
        unisIssuUpgradeDeviceStatus
            INTEGER,
        unisIssuUpgradeFailedReason
            DisplayString
     }

unisIssuUpgradeResultIndex OBJECT-TYPE
    SYNTAX Integer32 (1..65535)
    MAX-ACCESS not-accessible
    STATUS current
    DESCRIPTION
        "Internal Index, not accessible."
    ::= { unisIssuUpgradeResultEntry 1 }


unisIssuUpgradeDeviceChassisID OBJECT-TYPE
    SYNTAX Integer32 (0..255)
    MAX-ACCESS read-only
    STATUS current
    DESCRIPTION
        "Chassis ID of the card."
    ::= { unisIssuUpgradeResultEntry 2 }


unisIssuUpgradeDeviceSlotID OBJECT-TYPE
    SYNTAX Integer32 (0..255)
    MAX-ACCESS read-only
    STATUS current
    DESCRIPTION
        "Slot ID of the card."
    ::= { unisIssuUpgradeResultEntry 3 }


unisIssuUpgradeDeviceCpuID OBJECT-TYPE
    SYNTAX Integer32 (0..7)
    MAX-ACCESS read-only
    STATUS current
    DESCRIPTION
        "CPU ID of the card."
    ::= { unisIssuUpgradeResultEntry 4 }


unisIssuUpgradeState OBJECT-TYPE
    SYNTAX INTEGER
        {
        init(1),
        loading(2),
        loaded(3),
        switching(4),
        switchover(5),
        committing(6),
        committed(7),
        rollbacking(8),
        rollbacked(9)
        }
    MAX-ACCESS read-only
    STATUS current
    DESCRIPTION
        "Upgrade status of the device.
        init           -The current status of the device is Init.
        loading        -The current status of the device is Loading.
        loaded         -The current status of the device is Loaded.
        switching      -The current status of the device is Switching.
        switchover     -The current status of the device is Switchover.
        committing     -The current status of the device is Committing.
        committed      -The current status of the device is Committed.
        rollbacking    -The current status of the device is Rollbacking.
        rollbacked     -The current status of the device is Rollbacked.
        "
    ::= { unisIssuUpgradeResultEntry 5 }


unisIssuDeviceUpgradeWay OBJECT-TYPE
    SYNTAX INTEGER
        {
        none(1),
        reboot(2),
        sequenceReboot(3),
        issuReboot(4),
        serviceUpgrade(5),
        fileUpgrade(6),
        incompatibleUpgrade(7)
        }
    MAX-ACCESS read-only
    STATUS current
    DESCRIPTION
        "Upgrade method of the card.
        none                   - No operation was performed.
        reboot                 - The upgrade method of this device is Reboot.
        sequenceReboot         - The upgrade method of this device is SequenceReboot.
        issuReboot             - The upgrade method of this device is IssuReboot.
        serviceUpgrade         - The upgrade method of this device is ServiceReboot.
        fileUpgrade            - The upgrade method of this device is FileReboot.
        incompatibleUpgrade    - The upgrade method of this device is IncompatibleUpgrade.
        "
    ::= { unisIssuUpgradeResultEntry 6 }


unisIssuUpgradeDeviceStatus OBJECT-TYPE
    SYNTAX INTEGER
        {
        waitingUpgrade(1),
        inProcess(2),
        success(3),
        failure(4)
        }
    MAX-ACCESS read-only
    STATUS current
    DESCRIPTION
        "Upgrade status of the device."
    ::= { unisIssuUpgradeResultEntry 7 }


unisIssuUpgradeFailedReason OBJECT-TYPE
    SYNTAX DisplayString (SIZE (0..255))
    MAX-ACCESS read-only
    STATUS current
    DESCRIPTION
        "Indicates the cause of 'failure' state
        of the object 'unisIssuUpgradeDeviceStatus'.
        This object would be a null string if the value of
        'unisIssuCompatibleResultStatus' is not 'failure'."
    ::= { unisIssuUpgradeResultEntry 8 }


unisIssuUpgradeNotify OBJECT IDENTIFIER ::= { unisIssuUpgrade 2 }


unisIssuUpgradeTrapPrefix OBJECT IDENTIFIER ::= { unisIssuUpgradeNotify 0 }


unisIssuUpgradeOpCompletionNotify NOTIFICATION-TYPE
    OBJECTS { unisIssuOpType, unisIssuOpStatus, unisIssuFailedReason, unisIssuOpTimeCompleted }
    STATUS current
    DESCRIPTION
        "An unisIssuUpgradeOpCompletionNotify is sent at the
        completion of upgrade operation denoted by
        unisIssuOp object, if such a notification
        was requested when the operation was initiated.
        unisIssuOpType indicates the type of the
        operation.  unisIssuOpStatus indicates the
        result of the operation.  unisIssuFailedReason
        indicates the operation failure reason.
        unisIssuOpTimeCompleted indicates the time
        when the operation was completed."
    ::= { unisIssuUpgradeTrapPrefix 1 }



END
