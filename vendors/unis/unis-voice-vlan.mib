-- ==================================================================
-- Copyright (c) 2020 Unisyue Technologies Co., Ltd.  All rights reserved.
--
-- Description:
-- Reference:
-- Version: V1.4
-- History:
-- V1.0 Created by luoqiang01280, 2004.06.08
-- V1.1 2004-10-12 updated by gaolong
--      Import TEXTUAL-CONVENTION.
-- V1.2 2004-12-7 add unisvoiceVlanPortTable by liaoyuxia.
-- V1.3 2009-5-15 add unisVoiceVlanPortLegacy and unisVoiceVlanPortQosTrust
--                by zhangqingjun.
-- V1.4 2016-12-1 add value 0 to unisVoiceVlanAgingTime by yuhaiyan.
-- ==================================================================
-- ==================================================================
--
-- Varibles and types be imported
--
-- ==================================================================
UNIS-VOICE-VLAN-MIB DEFINITIONS ::= BEGIN

IMPORTS
    unisCommon
        FROM UNIS-OID-MIB
    RowStatus, TruthValue, MacAddress, TEXTUAL-CONVENTION
        FROM SNMPv2-TC
    MODULE-IDENTITY, OBJECT-TYPE, Integer32
        FROM SNMPv2-SMI;

    unisVoiceVlan MODULE-IDENTITY

    LAST-UPDATED     "201612010000Z"        -- Dec 01, 2016 at 00:00 GMT
    ORGANIZATION
        "Unisyue Technologies Co., Ltd."
    CONTACT-INFO
        ""
    DESCRIPTION
            "This MIB contains objects to manage the voice vlan operations, which is used on
            lanswitch products. "
    REVISION "201612010000Z"
    DESCRIPTION
        "add value 0 to unisVoiceVlanAgingTime."
    REVISION "200905150000Z"
    DESCRIPTION
        "To fix bugs in the MIB file."
    REVISION "200207010000Z"
    DESCRIPTION
    "The initial revision of this MIB module."
        ::= { unisCommon 9 }

-- =============================================================
-- Textual Conventions
-- =============================================================

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

-- ==================================================================
--
-- ======================= definition begin =========================
--
-- ==================================================================

    unisvoiceVlanOuiTable OBJECT-TYPE
        SYNTAX  SEQUENCE OF UnisVoiceVlanOuiEntry
        MAX-ACCESS not-accessible
        STATUS   current
        DESCRIPTION " A table containing the mac address which can be identified by voice vlan "
        ::= { unisVoiceVlan  1  }

    unisvoiceVlanOuiEntry OBJECT-TYPE
        SYNTAX  UnisVoiceVlanOuiEntry
        MAX-ACCESS not-accessible
        STATUS current
        DESCRIPTION " A table containing the mac address which can be identified by voice vlan "
                INDEX   { unisVoiceVlanOuiAddress }
                ::= {unisvoiceVlanOuiTable 1}

    UnisVoiceVlanOuiEntry    ::=
    SEQUENCE {
        unisVoiceVlanOuiAddress    MacAddress  ,
        unisVoiceVlanOuiMask    MacAddress  ,
        unisVoiceVlanOuiDescription    OCTET STRING  ,
        unisVoiceVlanOuiRowStatus      RowStatus
        }

    unisVoiceVlanOuiAddress OBJECT-TYPE
        SYNTAX  MacAddress
        MAX-ACCESS read-only
        STATUS current
        DESCRIPTION " Mac address can be identified by voice vlan "
        ::= { unisvoiceVlanOuiEntry 1 }

    unisVoiceVlanOuiMask OBJECT-TYPE
        SYNTAX  MacAddress
        MAX-ACCESS read-write
        STATUS current
        DESCRIPTION " The mask of mac address "
        ::= { unisvoiceVlanOuiEntry 2 }

    unisVoiceVlanOuiDescription OBJECT-TYPE
        SYNTAX  OCTET STRING (SIZE(0..30))
        MAX-ACCESS read-write
        STATUS current
        DESCRIPTION " The description of oui "
        ::= { unisvoiceVlanOuiEntry 3 }

    unisVoiceVlanOuiRowStatus OBJECT-TYPE
        SYNTAX  RowStatus
        MAX-ACCESS read-create
        STATUS current
        DESCRIPTION " Current operation status of the row  "
        ::= { unisvoiceVlanOuiEntry 4 }

    unisVoiceVlanEnabledId  OBJECT-TYPE
        SYNTAX  Integer32
        MAX-ACCESS read-write
        STATUS current
        DESCRIPTION " Voice vlan enable status: enabled (2..4095), disabled (0xffffffff) "
        ::= { unisVoiceVlan 2 }

    unisVoiceVlanPortEnableList  OBJECT-TYPE
        SYNTAX  PortList
        MAX-ACCESS read-write
        STATUS current
        DESCRIPTION " Portlist of voice vlan enabled ports "
        ::= { unisVoiceVlan 3 }

    unisVoiceVlanAgingTime  OBJECT-TYPE
        SYNTAX  Integer32 (0|5..43200)
        MAX-ACCESS read-write
        STATUS current
        DESCRIPTION " Voice vlan aging time, the unit of which is minute.  0 means no aging."
        DEFVAL { 1440 }
        ::= { unisVoiceVlan  4 }

    unisVoiceVlanConfigState  OBJECT-TYPE
        SYNTAX  INTEGER
        {
        auto (1),
        manual (2)
        }
        MAX-ACCESS read-write
        STATUS current
        DESCRIPTION " Voice vlan configuration mode status "
        ::= { unisVoiceVlan 5 }

    unisVoiceVlanSecurityState  OBJECT-TYPE
        SYNTAX  INTEGER
        {
        security (1),
        normal (2)
        }
        MAX-ACCESS read-write
        STATUS current
        DESCRIPTION " Voice vlan security mode status "
        ::= { unisVoiceVlan 6 }

    unisvoiceVlanPortTable OBJECT-TYPE
        SYNTAX  SEQUENCE OF UnisVoiceVlanPortEntry
        MAX-ACCESS not-accessible
        STATUS   current
        DESCRIPTION " A list of voice vlan mode entries."
        ::= { unisVoiceVlan  7  }

    unisvoiceVlanPortEntry OBJECT-TYPE
        SYNTAX  UnisVoiceVlanPortEntry
        MAX-ACCESS not-accessible
        STATUS current
        DESCRIPTION " An entry containing voice vlan mode information,
            which is applicable to a voice vlan enabled interface."
        INDEX   { unisVoiceVlanPortifIndex }
        ::= {unisvoiceVlanPortTable 1}

    UnisVoiceVlanPortEntry ::=
        SEQUENCE {
            unisVoiceVlanPortifIndex    Integer32,
            unisVoiceVlanPortMode       INTEGER,
            unisVoiceVlanPortLegacy     TruthValue,
            unisVoiceVlanPortQosTrust   TruthValue
        }

    unisVoiceVlanPortifIndex OBJECT-TYPE
        SYNTAX Integer32(1..2147483647)
        MAX-ACCESS not-accessible
        STATUS current
        DESCRIPTION " The index of interface on which voice vlan function
            is enabled."
        REFERENCE "ifIndex in RFC1213"
    ::= { unisvoiceVlanPortEntry 1 }

    unisVoiceVlanPortMode OBJECT-TYPE
        SYNTAX  INTEGER
            {
            auto (1),
            manual (2)
            }
        MAX-ACCESS read-write
        STATUS current
        DESCRIPTION " Voice vlan configuration mode status, which is
            applicable to a voice vlan enabled interface."
        ::= { unisvoiceVlanPortEntry 2 }

    unisVoiceVlanPortLegacy OBJECT-TYPE
        SYNTAX  TruthValue
        MAX-ACCESS read-write
        STATUS current
        DESCRIPTION " Voice vlan configuration legacy status, which is
            applicable to a voice vlan enabled interface."
        ::= { unisvoiceVlanPortEntry 3 }

    unisVoiceVlanPortQosTrust OBJECT-TYPE
        SYNTAX  TruthValue
        MAX-ACCESS read-write
        STATUS current
        DESCRIPTION " Voice vlan configuration qos trust status, which is
            applicable to a voice vlan enabled interface."
        ::= { unisvoiceVlanPortEntry 4 }
END
