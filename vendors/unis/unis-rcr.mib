-- =================================================================
-- Copyright (c) 2020 Unisyue Technologies Co., Ltd.  All rights reserved.
--
-- Description: Resilient Controllable Routing MIB
-- Reference:
-- Version: V1.1
-- History:
--   V1.0 2005-04-06 created by ZhangQiang
--     Initial version
--   V1.1 2005-06-28 modified by TanZhi and DaiRuiqiang
--     Rewrite the whole MIB
-- =================================================================
UNIS-RCR-MIB DEFINITIONS ::= BEGIN

    IMPORTS
        unisCommon
            FROM UNIS-OID-MIB
        InterfaceIndex
            FROM IF-MIB
        InetAddressType, InetAddress
            FROM INET-ADDRESS-MIB
        Integer32, OBJECT-TYPE, MODULE-IDENTITY, NOTIFICATION-TYPE
            FROM SNMPv2-SMI;

    unisRcr MODULE-IDENTITY
        LAST-UPDATED "200506281936Z"        -- June 28, 2005 at 19:36 GMT
        ORGANIZATION
            "Unisyue Technologies Co., Ltd."
        CONTACT-INFO
            ""
        DESCRIPTION
            "This MIB is applicable to router-devices. It's made for RCR
            (Resilient Controllable Routing).
            RCR provides an effective resolution which can dynamically auto-adjust
            outbound traffic to the optimal external interface by monitoring the 
            performance and traffic load of each external interface. It provides 
            the functions of intelligentized traffic load distribution and the optimal external interface
            selection. This can optimally utilize the external interfaces. Furthermore,
            RCR realized the function which can select the optimal external interface
            based on different classes of operation flow."
        REVISION "200506281936Z"        -- June 28, 2005 at 19:36 GMT
        DESCRIPTION
            "The modified revision of this MIB module. Rewrite the whole MIB."
        ::= { unisCommon 48 }
--
-- Node definitions
--


-- The member router-device(MR) information is defined here.
    unisRcrMR OBJECT IDENTIFIER ::= { unisRcr 1 }

-- Scalar MIB objects, which are considered as global variables
-- to all member router-devices, are defined in this section.
-- This group contains global variables of all member router-devices which
-- are controlled by RCR.

    unisRcrMRGroup OBJECT IDENTIFIER ::= {   unisRcrMR 1  }

    unisRcrMRAllMaxUsedBandRate OBJECT-TYPE
        SYNTAX Integer32 (1..100)
        UNITS "%"
        MAX-ACCESS read-write
        STATUS current
        DESCRIPTION
            "The max used band rate of all external interfaces on member
            router-devices(MRs) which are controlled by RCR."
        ::= { unisRcrMRGroup 1 }

    unisRcrMRAllMinUsedBandRate OBJECT-TYPE
        SYNTAX Integer32 (0..100)
        UNITS "%"
        MAX-ACCESS read-write
        STATUS current
        DESCRIPTION
            "The min used band rate of all external interfaces on MRs
            which are controlled by RCR."
        ::= { unisRcrMRGroup 2 }


    unisRcrMRListenTime OBJECT-TYPE
        SYNTAX Integer32 (1..1440)
        UNITS "minute"
        MAX-ACCESS read-write
        STATUS current
        DESCRIPTION
            "The persistent time of a probe on member router-device(MR) which is
            controlled by RCR."
        ::= { unisRcrMRGroup 3 }


    unisRcrMRStateTable OBJECT-TYPE
        SYNTAX SEQUENCE OF UnisRcrMRStateEntry
        MAX-ACCESS not-accessible
        STATUS current
        DESCRIPTION
            "This table contains state information of each MR
            which is controlled by RCR."
        ::= { unisRcrMR 2 }

    unisRcrMRStateEntry OBJECT-TYPE
        SYNTAX UnisRcrMRStateEntry
        MAX-ACCESS not-accessible
        STATUS current
        DESCRIPTION
            "Entry items"
        INDEX { unisRcrMRName }
        ::= { unisRcrMRStateTable 1 }

    UnisRcrMRStateEntry ::=
        SEQUENCE {
            unisRcrMRName
                OCTET STRING,
            unisRcrMRState
                INTEGER,
            unisRcrMRAuthType
                INTEGER,
            unisRcrMRAuthPwd
                OCTET STRING
                 }

    unisRcrMRName OBJECT-TYPE
        SYNTAX OCTET STRING (SIZE(1..32))
        MAX-ACCESS not-accessible
        STATUS current
        DESCRIPTION
            "The name of MR which is controlled by RCR."
        ::= { unisRcrMRStateEntry 1 }

    unisRcrMRState OBJECT-TYPE
        SYNTAX INTEGER
            {
            down(1),
            up(2),
            controlled(3)
            }
        MAX-ACCESS read-only
        STATUS current
        DESCRIPTION
            "The state of MR where identified on the controller
            router-device(CR).
            down: The MR has been enabled but has not connected
                  to the CR with TCP connection.
            up: The MR has already successfully connected to
                the CR but has not been ready for adjusting
                route.
            controlled: The MR has already passed the
                        consultation with the CR and could
                        be controlled by it."
        ::= { unisRcrMRStateEntry 2 }

     unisRcrMRAuthType OBJECT-TYPE
        SYNTAX INTEGER
            {
            simple(1),
            md5(2)
            }
        MAX-ACCESS read-write
        STATUS current
        DESCRIPTION
            "The authentication type of communication packet between CR and MR."
        ::= { unisRcrMRStateEntry 3 }

    unisRcrMRAuthPwd OBJECT-TYPE
        SYNTAX OCTET STRING
        MAX-ACCESS read-write
        STATUS current
        DESCRIPTION
            "The authentication password of communication packet between CR
            and MR.
            Reading this object always results in an OCTET STRING of length zero;
            authentication may not be bypassed by reading the MIB object."
        ::= { unisRcrMRStateEntry 4 }

    unisRcrMROutIfStateTable OBJECT-TYPE
        SYNTAX SEQUENCE OF UnisRcrMROutIfStateEntry
        MAX-ACCESS not-accessible
        STATUS current
        DESCRIPTION
            "This table contains the external interface states of each MR
            which is controlled by RCR."
        ::= { unisRcrMR 3 }

    unisRcrMROutIfStateEntry OBJECT-TYPE
        SYNTAX UnisRcrMROutIfStateEntry
        MAX-ACCESS not-accessible
        STATUS current
        DESCRIPTION
            "Entry items"
        INDEX { unisRcrMRName, unisRcrMROutIfName }
        ::= { unisRcrMROutIfStateTable 1 }

    UnisRcrMROutIfStateEntry ::=
        SEQUENCE {
            unisRcrMROutIfName
                OCTET STRING,
            unisRcrMROutIfState
                INTEGER,
            unisRcrMROutIfMaxUsedBandRate
                Integer32,
            unisRcrMROutIfMinUsedBandRate
                Integer32,
            unisRcrMROutIfUsedBandRate
                Integer32
                 }

    unisRcrMROutIfName OBJECT-TYPE
        SYNTAX OCTET STRING (SIZE(1..48))
        MAX-ACCESS not-accessible
        STATUS current
        DESCRIPTION
            "The name of external interface on each MR."
        ::= { unisRcrMROutIfStateEntry 1 }

    unisRcrMROutIfState OBJECT-TYPE
        SYNTAX INTEGER
            {
            down(1),
            up(2),
            notExist(3)
            }
        MAX-ACCESS read-only
        STATUS current
        DESCRIPTION
            "The state of external interface on each MR."
        ::= { unisRcrMROutIfStateEntry 2 }

    unisRcrMROutIfMaxUsedBandRate OBJECT-TYPE
        SYNTAX Integer32 (1..100)
        UNITS "%"
        MAX-ACCESS read-write
        STATUS current
        DESCRIPTION
            "The max spendable bandwidth rate on external interface."
        ::= { unisRcrMROutIfStateEntry 3 }

    unisRcrMROutIfMinUsedBandRate OBJECT-TYPE
        SYNTAX Integer32 (0..100)
        UNITS "%"
        MAX-ACCESS read-write
        STATUS current
        DESCRIPTION
            "The min spendable bandwidth rate on external interface."
        ::= { unisRcrMROutIfStateEntry 4 }

    unisRcrMROutIfUsedBandRate  OBJECT-TYPE
        SYNTAX Integer32 (0..100)
        UNITS "%"
        MAX-ACCESS read-only
        STATUS current
        DESCRIPTION
            "The used bandwidth rate on external interface."
        ::= { unisRcrMROutIfStateEntry 5 }

-- The controller router-device information are defined here.
   unisRcrCR OBJECT IDENTIFIER ::= { unisRcr 2 }

-- Scalar MIB objects, which are considered as global variables
-- to all member router-devices, are defined in this section.
    unisRcrCRGroup OBJECT IDENTIFIER ::= {   unisRcrCR 1  }

    unisRcrCRState OBJECT-TYPE
        SYNTAX INTEGER
            {
            down(1),
            init(2),
            active(3)
            }
        MAX-ACCESS read-only
        STATUS current
        DESCRIPTION
            "The state of the CR which is controlled
            by RCR.
            down: The CR has been enabled but has not
                  started a TCP connection server.
            init: The CR has started a TCP connection
                  server and has been waiting for MR
                  connection, but has not been ready for adjusting route.
            active: The CR is ready for adjusting route."
        ::= { unisRcrCRGroup 1 }

    unisRcrCRPortNum OBJECT-TYPE
        SYNTAX Integer32
        MAX-ACCESS read-write
        STATUS current
        DESCRIPTION
            "The communication port number between CR and MR."
        ::= { unisRcrCRGroup 2 }

     unisRcrCRCtrlMode OBJECT-TYPE
        SYNTAX INTEGER
            {
            control(1),
            observe(2)
            }
        MAX-ACCESS read-write
        STATUS current
        DESCRIPTION

            "The observe mode or control mode is configured to operate in the CR.
             observe: The CR monitors prefixes and external interfaces based on default
                      and user-defined policies and then reports the status of
                      the network and the decisions that should be made but does
                      not implement any changes.
             controlled: The CR monitors prefixes and external interfaces based on default
                         and user-defined policies and then reports the status
                         of the network and the decisions that should be made
                         and implement any changes."
       ::= { unisRcrCRGroup 3 }

    unisRcrCRChooseMode OBJECT-TYPE
        SYNTAX INTEGER
        {
        good(1),
        best(2)
        }
        MAX-ACCESS read-write
        STATUS current
        DESCRIPTION
            "The algorithm used to choose an alternative external interface for a prefix.
             good: The first external interface that conforms to the policy is selected as
                   the new external interface.
             best: Information is collected from all external interfaces and the best one
                   is selected even though the best external interface may not be in-policy."
        ::= { unisRcrCRGroup 4 }

    unisRcrCRKeepaliveTime OBJECT-TYPE
        SYNTAX Integer32 (1..1000)
        UNITS "second"
        MAX-ACCESS read-write
        STATUS current
        DESCRIPTION
            "The interval time of the transmission of the keepalive communication
             packet between CR and MR."
        ::= { unisRcrCRGroup 5 }


    unisRcrCRPolicyMode OBJECT-TYPE
        SYNTAX INTEGER
            {
            prefix(1),
            operation(2),
            study(3)
            }
        MAX-ACCESS read-write
        STATUS current
        DESCRIPTION
            "The chosen policy mode which decides to change what prefix.
            prefix: An RCR policy is designed to select IP prefixes or to
                     select RCR learn policies using a match clause and then to
                     apply RCR policy configurations using a set clause.
            operation: To deside to adjusted prefixes based on operation
                        which user configured.
            study: To learn and optimize prefixes based on the highest
                    throughput or the highest delay."
        ::= { unisRcrCRGroup 6 }

    unisRcrCRStudyMode OBJECT-TYPE
        SYNTAX INTEGER
            {
            maxThoughout(1),
            maxDelay(2)
            }
        MAX-ACCESS read-write
        STATUS current
        DESCRIPTION
            "The mode of collecting prefix in studying configuration mode.
            It's to collect either the prefix of max thoughtout or the prefix
            of max delay time. It doesn't have a value when CR isn't in studying
            configuration mode."
        ::= { unisRcrCRGroup 7 }

    unisRcrCRStudyIpPrefixNum OBJECT-TYPE
        SYNTAX Integer32 (1..2500)
        MAX-ACCESS read-write
        STATUS current
        DESCRIPTION
            "The max number of collecting prefix in studying configuration mode."
        ::= { unisRcrCRGroup 8 }

	unisRcrCRIpPrefixLen OBJECT-TYPE
        SYNTAX Integer32 (1..32)
        MAX-ACCESS read-write
        STATUS current
        DESCRIPTION
            "The mask length of collecting prefix in configuration mode."
        DEFVAL { 24 }
        ::= { unisRcrCRGroup 9 }

--RCR policy table is defined here.
    unisRcrCRRcrPolicyTable OBJECT-TYPE
        SYNTAX SEQUENCE OF UnisRcrCRRcrPolicyEntry
        MAX-ACCESS not-accessible
        STATUS current
        DESCRIPTION
            "This table contains objects to get statistic information
            of interfaces on a device."
        ::= { unisRcrCR 2 }

    unisRcrCRRcrPolicyEntry OBJECT-TYPE
        SYNTAX UnisRcrCRRcrPolicyEntry
        MAX-ACCESS not-accessible
        STATUS current
        DESCRIPTION
            "Entry items"
        INDEX { unisRcrCRRcrPlyID }
        ::= { unisRcrCRRcrPolicyTable 1 }

    UnisRcrCRRcrPolicyEntry ::=
        SEQUENCE {
            unisRcrCRRcrPlyID
                Integer32,
            unisRcrCRRcrPlyMatchIPListName
                OCTET STRING,
            unisRcrCRRcrPlyMatchStudyEnable
                INTEGER,
            unisRcrCRRcrPlyMatchOperPlyName
                OCTET STRING,
            unisRcrCRRcrAclNumber
                Integer32,
            unisRcrCRRcrPlyDelayTime
                Integer32,
            unisRcrCRRcrPlyLossRate
                Integer32
                  }

    unisRcrCRRcrPlyID OBJECT-TYPE
        SYNTAX Integer32
        MAX-ACCESS not-accessible
        STATUS current
        DESCRIPTION
            "The ID of RCR policy which the user has configured."
        ::= { unisRcrCRRcrPolicyEntry 1 }

    unisRcrCRRcrPlyMatchIPListName OBJECT-TYPE
        SYNTAX OCTET STRING  (SIZE(1..19))
        MAX-ACCESS read-write
        STATUS current
        DESCRIPTION
            "The matched IP prefix list name of RCR policy which the user has
            configured."
        ::= { unisRcrCRRcrPolicyEntry 2 }

    unisRcrCRRcrPlyMatchStudyEnable OBJECT-TYPE
        SYNTAX INTEGER
            {
            disable(1),
            enable(2)
            }
        MAX-ACCESS read-write
        STATUS current
        DESCRIPTION
            "Whether the RCR policy which the user has configured is matched
            for studying prefix mode."
        ::= { unisRcrCRRcrPolicyEntry 3 }

    unisRcrCRRcrPlyMatchOperPlyName OBJECT-TYPE
        SYNTAX OCTET STRING  (SIZE(1..19))
        MAX-ACCESS read-write
        STATUS current
        DESCRIPTION
            "The matched operation policy name of RCR policy which the user
            has configured."
        ::= { unisRcrCRRcrPolicyEntry 4 }

   unisRcrCRRcrAclNumber OBJECT-TYPE
        SYNTAX Integer32 (3000..3999)
        MAX-ACCESS read-write
        STATUS current
        DESCRIPTION
            "The matched acl number of RCR operation policy which the user
            has configured."
        ::= { unisRcrCRRcrPolicyEntry 5 }

    unisRcrCRRcrPlyDelayTime OBJECT-TYPE
        SYNTAX Integer32  (1..10000)
        UNITS "millisecond"
        MAX-ACCESS read-write
        STATUS current
        DESCRIPTION
            "The absolute maximum delay time. The range of values that can be
            configured is from 1 to 10000."
        ::= { unisRcrCRRcrPolicyEntry 6 }

    unisRcrCRRcrPlyLossRate OBJECT-TYPE
        SYNTAX Integer32 (1..100)
        UNITS "%"
        MAX-ACCESS read-write
        STATUS current
        DESCRIPTION
            "The packet loss percent of prefix which the CR concerns."
        ::= { unisRcrCRRcrPolicyEntry 7 }

--Matched prefix performance table define
    unisRcrCRMatPrefixPerfTable OBJECT-TYPE
        SYNTAX SEQUENCE OF UnisRcrCRMatPrefixPerfEntry
        MAX-ACCESS not-accessible
        STATUS current
        DESCRIPTION
            "This table contains the matched prefix performance
            information."
        ::= { unisRcrCR 3 }

    unisRcrCRMatPrefixPerfEntry OBJECT-TYPE
        SYNTAX UnisRcrCRMatPrefixPerfEntry
        MAX-ACCESS not-accessible
        STATUS current
        DESCRIPTION
            "Entry items"
        INDEX { unisRcrCRMatPrefPerfAddrType, unisRcrCRMatPrefPerfDestIPAddr,
                unisRcrCRMatPrefPerfDestMaskLen }
        ::= { unisRcrCRMatPrefixPerfTable 1 }

    UnisRcrCRMatPrefixPerfEntry ::=
        SEQUENCE {
            unisRcrCRMatPrefPerfAddrType
                InetAddressType,
            unisRcrCRMatPrefPerfDestIPAddr
                InetAddress,
            unisRcrCRMatPrefPerfDestMaskLen
                Integer32,
            unisRcrCRMatPrefPerfDelayTime
                Integer32,
            unisRcrCRMatPrefPerfLossRate
                Integer32,
            unisRcrCRMatPrefPerfThroughput
                Integer32
                    }

    unisRcrCRMatPrefPerfAddrType OBJECT-TYPE
        SYNTAX InetAddressType
        MAX-ACCESS not-accessible
        STATUS current
        DESCRIPTION
            "The destination IP addresses type of matched prefix which the CR
            wants (IPv4 or IPv6)."
        ::= { unisRcrCRMatPrefixPerfEntry 1 }

    unisRcrCRMatPrefPerfDestIPAddr OBJECT-TYPE
        SYNTAX InetAddress
        MAX-ACCESS not-accessible
        STATUS current
        DESCRIPTION
            "The destination IP address of matched prefix which the CR wants."
        ::= { unisRcrCRMatPrefixPerfEntry 2 }

    unisRcrCRMatPrefPerfDestMaskLen OBJECT-TYPE
        SYNTAX Integer32 (0..32)
        MAX-ACCESS not-accessible
        STATUS current
        DESCRIPTION
            "The destination IP address mask length of matched prefix which
            the CR wants."
        ::= { unisRcrCRMatPrefixPerfEntry 3 }

    unisRcrCRMatPrefPerfDelayTime OBJECT-TYPE
        SYNTAX Integer32  (1..10000)
        UNITS "second"
        MAX-ACCESS read-only
        STATUS current
        DESCRIPTION
            "The absolute maximum delay time of prefix which the CR has
            configured."
        ::= { unisRcrCRMatPrefixPerfEntry 4 }

    unisRcrCRMatPrefPerfLossRate OBJECT-TYPE
        SYNTAX Integer32 (1..100)
        UNITS "%"
        MAX-ACCESS read-only
        STATUS current
        DESCRIPTION
            "The packet loss percent of prefix which the CR has configured."
        ::= { unisRcrCRMatPrefixPerfEntry 5 }

    unisRcrCRMatPrefPerfThroughput OBJECT-TYPE
        SYNTAX Integer32
        UNITS "kb"
        MAX-ACCESS read-only
        STATUS current
        DESCRIPTION
            "The bandwidth of prefix which the CR has monitored."
        ::= { unisRcrCRMatPrefixPerfEntry 6 }

--Adjusted prefix table define
    unisRcrCRAdjustPrefixTable OBJECT-TYPE
        SYNTAX SEQUENCE OF UnisRcrCRAdjustPrefixEntry
        MAX-ACCESS not-accessible
        STATUS current
        DESCRIPTION
            "This table contains objects to get adjusted prefix information
            which the CR controlled."
        ::= { unisRcrCR 4 }

    unisRcrCRAdjustPrefixEntry OBJECT-TYPE
        SYNTAX UnisRcrCRAdjustPrefixEntry
        MAX-ACCESS not-accessible
        STATUS current
        DESCRIPTION
            "Entry items"
        INDEX { unisRcrCRAdjuPrefDestAddrType, unisRcrCRAdjuPrefDestAddr,
        	   unisRcrCRAdjuPrefMaskLen, unisRcrCRAdjuPrefPreMRName,
        	   unisRcrCRAdjuPrefPreOutIfName }
        ::= { unisRcrCRAdjustPrefixTable 1 }

    UnisRcrCRAdjustPrefixEntry ::=
        SEQUENCE {
            unisRcrCRAdjuPrefDestAddrType
                InetAddressType,
            unisRcrCRAdjuPrefDestAddr
                InetAddress,
            unisRcrCRAdjuPrefMaskLen
                Integer32,
            unisRcrCRAdjuPrefPreMRName
                OCTET STRING,
            unisRcrCRAdjuPrefPreOutIfName
                OCTET STRING,
            unisRcrCRAdjuPrefCurMRName
                OCTET STRING,
            unisRcrCRAdjuPrefCurOutIfName
                OCTET STRING,
            unisRcrCRAdjuPrefPersistTime
                Integer32,
            unisRcrCRAdjuPrefAgeTime
                Integer32
                    }

    unisRcrCRAdjuPrefDestAddrType OBJECT-TYPE
        SYNTAX InetAddressType
        MAX-ACCESS not-accessible
        STATUS current
        DESCRIPTION
            "The IP address type of the adjusted prefix which CR controlled
            (IPv4 or IPv6)."
        ::= { unisRcrCRAdjustPrefixEntry 1 }

    unisRcrCRAdjuPrefDestAddr OBJECT-TYPE
        SYNTAX InetAddress
        MAX-ACCESS not-accessible
        STATUS current
        DESCRIPTION
            "The IP address of the adjusted prefix which CR controlled."
        ::= { unisRcrCRAdjustPrefixEntry 2 }

    unisRcrCRAdjuPrefMaskLen OBJECT-TYPE
        SYNTAX Integer32  (0..32)
        MAX-ACCESS not-accessible
        STATUS current
        DESCRIPTION
            "The IP address mask length of the adjusted prefix which CR
            controlled."
        ::= { unisRcrCRAdjustPrefixEntry 3 }

    unisRcrCRAdjuPrefPreMRName OBJECT-TYPE
        SYNTAX OCTET STRING   (SIZE(1..32))
        MAX-ACCESS not-accessible
        STATUS current
        DESCRIPTION
            "The name of the MR which the previous outbound traffic
            flows through."
        ::= { unisRcrCRAdjustPrefixEntry 4 }

    unisRcrCRAdjuPrefPreOutIfName OBJECT-TYPE
        SYNTAX OCTET STRING (SIZE(1..48))
        MAX-ACCESS not-accessible
        STATUS current
        DESCRIPTION
            "The name of the external interface on the MR which the previous
            outbound traffic flows through."
        ::= { unisRcrCRAdjustPrefixEntry 5 }

    unisRcrCRAdjuPrefCurMRName OBJECT-TYPE
        SYNTAX OCTET STRING   (SIZE(1..32))
        MAX-ACCESS read-only
        STATUS current
        DESCRIPTION
            "The name of the MR which the current outbound traffic flows through."
        ::= { unisRcrCRAdjustPrefixEntry 6 }

    unisRcrCRAdjuPrefCurOutIfName OBJECT-TYPE
        SYNTAX OCTET STRING
        MAX-ACCESS read-only
        STATUS current
        DESCRIPTION
            "The name of the external interface on the MR which the current outbound
            traffic flows through."
        ::= { unisRcrCRAdjustPrefixEntry 7 }

    unisRcrCRAdjuPrefPersistTime OBJECT-TYPE
        SYNTAX Integer32
        UNITS "second"
        MAX-ACCESS read-only
        STATUS current
        DESCRIPTION
            "The persisting time from the time which the adjusted outbound
            traffic has been adjusted by CR to now."
        ::= { unisRcrCRAdjustPrefixEntry 8 }

    unisRcrCRAdjuPrefAgeTime OBJECT-TYPE
        SYNTAX Integer32
        UNITS "second"
        MAX-ACCESS read-only
        STATUS current
        DESCRIPTION
            "The time which the adjusted prefix remains."
        ::= { unisRcrCRAdjustPrefixEntry 9 }
END
