-- ==================================================================
-- Copyright (c) 2020 Unisyue Technologies Co., Ltd.  All rights reserved.
--
-- Description: MSTP MIB
-- Reference:
-- Version: V1.16
-- History:
--      v1.0 (1) Created by Zhang Shilin, 2001.6.29
--           (2) Revised by Qi Zhenglin, 2002.01.08
--      v1.01 2004-7-13 remove default value
--         of unisdot1sMstDefaultVlanAllo & unisdot1sMstDefaultRegionName
--      v1.02 2004-08-19 Revised by Song Jianyong,
--            add unisdot1sStpPathCostStandard in mstp global table
--      v1.1 2004-10-12 updated by gaolong
--           Import OBJECT-IDENTITY, NOTIFICATION-TYPE, TEXTUAL-CONVENTION.
--           Import dot1dStpPort.
--           Relocate unisdot1sMstp MODULE-IDENTITY clause.
--           Fix default value errors for unisdot1sMstBpduGuard, unisdot1sMstiStpPortEdgeport,
--           unisdot1sMstiStpStatus, unisdot1sMstiPortRootGuard, unisdot1sMstiPortLoopGuard.
--      v1.11 2004-10-23 Revised by Song Jianyong,
--            modify the range of unisdot1sMstiPathCost value in unisdot1sPortTable
--      v1.12 2005-01-22 Revised by Song Jianyong,
--            Add an enumeration for unisdot1sStpForceVersion in mstp global table
--            Add an enumeration for unisdot1sStpPathCostStandard in unisdot1sPortTable
--            Adjust format of objects' description
--     V1.13 2005-6-30 Updated by zhanghaihong
--            add unisdot1sMstiStpPortSendingBPDUType, unisdot1sMstiStpOperPortPointToPoint
--            in unisdot1sPortTable
--     V1.14 2005-11-07 Updated by zhanghaihong
--            Modify the description of unisdot1sMstiStpOperPortPointToPoint in
--            unisdot1sPortTable.
--            Add unisdot1sMstiStpPortAdminBPDUFmt, unisdot1sMstiStpPortOperBPDUFmt
--            in unisdot1sPortTable.
--     V1.15 2011-8-11 Updated by zhangwei
--            Modify the range of unisdot1sAdminMstID, unisdot1sOperMstID in
--            unisdot1sPortTable and unisdot1sInstanceID in unisdot1sInstanceTable.
--            Remove the default value of unisdot1sMstiStpTransLimit.
--            Add unisdot1sMstiStpPortRoleRestriction, unisdot1sMstiStpPortTcRestriction and
--            unisdot1sMstiStpPortDisputed in unisdot1sPortTable.
--     V1.16 2014-02-11 Updated by wangmingjun
--            Add the binding value unisdot1sMstiDesignatedBridge of unisPortMstiBpduGuarded
--            in mstp traps table.
--            Add unisMstiNewRoot, unisPortPvstBpduProtection in mstp traps table.
-- ==================================================================
-- ==================================================================
--
-- Variables and types be imported
--
-- ==================================================================
-- ------------------------------------------------------------------
-- ------------------------------------------------------------------
UNIS-LswMSTP-MIB DEFINITIONS ::= BEGIN

IMPORTS

    MODULE-IDENTITY,OBJECT-TYPE, Integer32, Counter32, OBJECT-IDENTITY, NOTIFICATION-TYPE
        FROM SNMPv2-SMI
    TEXTUAL-CONVENTION, TruthValue
        FROM SNMPv2-TC
    dot1dStpPortEntry, dot1dStpPort
        FROM BRIDGE-MIB
    unislswCommon
        FROM UNIS-OID-MIB;

    unisdot1sMstp MODULE-IDENTITY
            LAST-UPDATED "200106290000Z"
            ORGANIZATION
                "Unisyue Technologies Co., Ltd."
            CONTACT-INFO
                ""
            DESCRIPTION
            "This MIB defines objects for managing MSTP."
            REVISION "200106290000Z"
            DESCRIPTION
            "The initial version of this MIB file."
            ::= { unislswCommon  14 }

    EnabledStatus ::= TEXTUAL-CONVENTION
    STATUS      current
    DESCRIPTION
        "A simple status value for the object."
    SYNTAX      INTEGER { enabled(1), disabled(2) }

    BridgeId ::= OCTET STRING (SIZE (8))

    Unisdot1sFormatStatus ::= TEXTUAL-CONVENTION
    STATUS      current
    DESCRIPTION
        "Legacy means that the BPDU format is legacy.  Dot1s means that the
        BPDU format is IEEE 802.1s.  Auto means that the format of BPDU sending
        on the port is determined by the BPDU format of its connective port."
    SYNTAX      INTEGER { legacy(1), dot1s(2), auto(3) }


  unisdot1sStpStatus OBJECT-TYPE
    SYNTAX      EnabledStatus
    MAX-ACCESS  read-write
    STATUS      current
    DESCRIPTION
      "Whether the Bridge MSTP is enabled."
    DEFVAL      { 2 }
    ::= { unisdot1sMstp 1 }

  unisdot1sStpForceVersion OBJECT-TYPE
    SYNTAX      INTEGER{stp(0),rstp(2),mstp(3)}
    MAX-ACCESS  read-write
    STATUS      current
    DESCRIPTION
      " The mode of this Bridge spanning-tree protocol."
    DEFVAL      { mstp}
    ::= { unisdot1sMstp 2 }

  unisdot1sStpDiameter OBJECT-TYPE
    SYNTAX      Integer32(2..7)
    MAX-ACCESS  read-write
    STATUS      current
    DESCRIPTION
      "The diameter of Bridge."
    DEFVAL      { 7}
    ::= { unisdot1sMstp 3 }

  unisdot1sMstBridgeMaxHops OBJECT-TYPE
    SYNTAX      Integer32(1..40)
    MAX-ACCESS  read-write
    STATUS      current
    DESCRIPTION
      "The maximum value of the  Bridge hops."
    DEFVAL      { 20}
    ::= { unisdot1sMstp 4 }

  unisdot1sMstMasterBridgeID OBJECT-TYPE
    SYNTAX      BridgeId
    MAX-ACCESS  read-only
    STATUS      current
    DESCRIPTION
      "The Bridge Identifier of the current Master Bridge."
    ::= { unisdot1sMstp 5 }

  unisdot1sMstMasterPathCost OBJECT-TYPE
    SYNTAX      Integer32
    MAX-ACCESS  read-only
    STATUS      current
    DESCRIPTION
      "The CIST path cost from the transmitting Bridge to the Master Bridge."
    DEFVAL      { 0}
    ::= { unisdot1sMstp 6 }

  unisdot1sMstBpduGuard OBJECT-TYPE
    SYNTAX      EnabledStatus
    MAX-ACCESS  read-write
    STATUS      current
    DESCRIPTION
      "Whether the Bridge BPDU Guard function is enabled.  If the function
      is enabled, the port will shutdown when received BPDU and the port
      is configured as portfast."
    DEFVAL      { disabled}
    ::= { unisdot1sMstp 7 }

  unisdot1sMstAdminFormatSelector OBJECT-TYPE
    SYNTAX      Integer32
    MAX-ACCESS  read-write
    STATUS      current
    DESCRIPTION
      "The administrative Configuration Identifier Format Selector in use
      by the Bridge.  This has a value of 0 indicate the format specified
      in the Standard of IEEE 802.1s."
    DEFVAL      { 0}
    ::= { unisdot1sMstp 8 }

  unisdot1sMstAdminRegionName OBJECT-TYPE
    SYNTAX      OCTET STRING(SIZE(1..32))
    MAX-ACCESS  read-write
    STATUS      current
    DESCRIPTION
      "This MSTP administrative region name."
    ::= { unisdot1sMstp 9 }

  unisdot1sMstAdminRevisionLevel OBJECT-TYPE
    SYNTAX      Integer32(0..65535)
    MAX-ACCESS  read-write
    STATUS      current
    DESCRIPTION
      "This MSTP administrative revision level."
    DEFVAL      { 0}
    ::= { unisdot1sMstp 10 }

  unisdot1sMstOperFormatSelector OBJECT-TYPE
    SYNTAX      Integer32
    MAX-ACCESS  read-only
    STATUS      current
    DESCRIPTION
      "The operative Configuration Identifier Format Selector in use by the
      Bridge.  This has a value of 0 indicate the format specified in the
      Standard of IEEE 802.1s."
    DEFVAL      { 0}
    ::= { unisdot1sMstp 11 }

  unisdot1sMstOperRegionName OBJECT-TYPE
    SYNTAX      OCTET STRING( SIZE(0..32) )
    MAX-ACCESS  read-only
    STATUS      current
    DESCRIPTION
      "This MSTP operative region name."
    ::= { unisdot1sMstp 12 }

  unisdot1sMstOperRevisionLevel OBJECT-TYPE
    SYNTAX      Integer32(0..65535)
    MAX-ACCESS  read-only
    STATUS      current
    DESCRIPTION
      "This MSTP operative revision level."
    DEFVAL      { 0}
    ::= { unisdot1sMstp 13 }

  unisdot1sMstOperConfigDigest OBJECT-TYPE
    SYNTAX      OCTET STRING(SIZE(0..16))
    MAX-ACCESS  read-only
    STATUS      current
    DESCRIPTION
      "This MSTP Region's Configuration Digest Signature Key."
    ::= { unisdot1sMstp 14 }

  unisdot1sMstRegionConfActive OBJECT-TYPE
    SYNTAX      INTEGER{enable(1),disable(2)}
    MAX-ACCESS  read-write
    STATUS      current
    DESCRIPTION
      "Active the region configuration."
    DEFVAL      { disable }
    ::= { unisdot1sMstp 15 }

  unisdot1sMstDefaultVlanAllo OBJECT-TYPE
    SYNTAX      INTEGER{enable(1),unused(65535)}
    MAX-ACCESS  read-write
    STATUS      current
    DESCRIPTION
      "Set default configuration about VLAN allocation and all VLANs
      are mapped to CIST."
    ::= { unisdot1sMstp 16 }

  unisdot1sMstDefaultRegionName OBJECT-TYPE
    SYNTAX      INTEGER{enable(1),unused(65535)}
    MAX-ACCESS  read-write
    STATUS      current
    DESCRIPTION
      "Set default region name."
    ::= { unisdot1sMstp 17 }

-- TABLE: unisdot1sVIDAllocationTable ------
  unisdot1sVIDAllocationTable OBJECT-TYPE
    SYNTAX      SEQUENCE OF Unisdot1sVIDAllocationEntry
    MAX-ACCESS  not-accessible
    STATUS      current
    DESCRIPTION
      "MSTP VLAN-to-instance mapping table."
    ::= { unisdot1sMstp 18 }

  unisdot1sVIDAllocationEntry OBJECT-TYPE
    SYNTAX      Unisdot1sVIDAllocationEntry
    MAX-ACCESS  not-accessible
    STATUS      current
    DESCRIPTION
      "MSTP VLAN-to-instance mapping table entry."
    INDEX {
              unisdot1sMstVID
             }
    ::= { unisdot1sVIDAllocationTable 1 }

  Unisdot1sVIDAllocationEntry ::=
    SEQUENCE
    {
      unisdot1sMstVID Integer32,
      unisdot1sAdminMstID Integer32,
      unisdot1sOperMstID  Integer32
    }

  unisdot1sMstVID OBJECT-TYPE
    SYNTAX      Integer32(1..4094)
    MAX-ACCESS  read-only
    STATUS      current
    DESCRIPTION
        "VLAN Identifier"
    ::={ unisdot1sVIDAllocationEntry 1 }

  unisdot1sAdminMstID OBJECT-TYPE
    SYNTAX      Integer32(0..4094)
    MAX-ACCESS  read-write
    STATUS      current
    DESCRIPTION
        "Administrative Multiple spanning-tree instance Identifier."
    ::={ unisdot1sVIDAllocationEntry 2 }

  unisdot1sOperMstID OBJECT-TYPE
    SYNTAX      Integer32(0..4094)
    MAX-ACCESS  read-only
    STATUS      current
    DESCRIPTION
        "Operative Multiple spanning-tree instance Identifier."
    ::={ unisdot1sVIDAllocationEntry 3 }

-- TABLE: unisdot1sInstanceTable ------
  unisdot1sInstanceTable OBJECT-TYPE
    SYNTAX      SEQUENCE OF Unisdot1sInstanceEntry
    MAX-ACCESS  not-accessible
    STATUS      current
    DESCRIPTION
      "MSTI table."
    ::= { unisdot1sMstp 19 }

  unisdot1sInstanceEntry OBJECT-TYPE
    SYNTAX      Unisdot1sInstanceEntry
    MAX-ACCESS  not-accessible
    STATUS      current
    DESCRIPTION
      "MSTI table entry."
    INDEX {
              unisdot1sInstanceID
             }
    ::= { unisdot1sInstanceTable 1 }

  Unisdot1sInstanceEntry ::=
    SEQUENCE
    {
      unisdot1sInstanceID Integer32,
      unisdot1sMstiBridgeID   BridgeId,
      unisdot1sMstiBridgePriority Integer32,
      unisdot1sMstiDesignedRoot   BridgeId,
      unisdot1sMstiRootPathCost   Integer32,
      unisdot1sMstiRootPort   Integer32,
      unisdot1sMstiRootType   INTEGER,
      unisdot1sMstiRemainingHops  Integer32,
      unisdot1sMstiAdminMappedVlanListLow OCTET STRING,
      unisdot1sMstiAdminMappedVlanListHigh OCTET STRING,
      unisdot1sMstiOperMappedVlanListLow OCTET STRING,
      unisdot1sMstiOperMappedVlanListHigh OCTET STRING
    }

  unisdot1sInstanceID OBJECT-TYPE
    SYNTAX      Integer32(0..4094)
    MAX-ACCESS  read-only
    STATUS      current
    DESCRIPTION
        "Multiple spanning-tree instance Identifier"
    ::={ unisdot1sInstanceEntry 1 }

  unisdot1sMstiBridgeID OBJECT-TYPE
    SYNTAX      BridgeId
    MAX-ACCESS  read-only
    STATUS      current
    DESCRIPTION
        "The Bridge Identifier for the spanning tree instance
        identified by MSTID"
    ::={ unisdot1sInstanceEntry 2 }

  unisdot1sMstiBridgePriority OBJECT-TYPE
    SYNTAX      Integer32(0..61440)
    MAX-ACCESS  read-write
    STATUS      current
    DESCRIPTION
        "The Bridge Priority for the spanning tree instance
        identified by MSTID.  Step of 4096"
    DEFVAL      { 32768 }
    ::={ unisdot1sInstanceEntry 3 }

  unisdot1sMstiDesignedRoot OBJECT-TYPE
    SYNTAX      BridgeId
    MAX-ACCESS  read-only
    STATUS      current
    DESCRIPTION
        "The Bridge Identifier of the Root Bridge for the spanning
        tree instance identified by MSTID"
    ::={ unisdot1sInstanceEntry 4 }

  unisdot1sMstiRootPathCost OBJECT-TYPE
    SYNTAX      Integer32
    MAX-ACCESS  read-only
    STATUS      current
    DESCRIPTION
        "The path cost from the transmitting Bridge to the Root Bridge
        for the spanning tree instance  identified by MSTID"
    ::={ unisdot1sInstanceEntry 5 }

  unisdot1sMstiRootPort OBJECT-TYPE
    SYNTAX      Integer32
    MAX-ACCESS  read-only
    STATUS      current
    DESCRIPTION
        "The Root Port for the spanning tree instance identified by the MSTID"
    ::={ unisdot1sInstanceEntry 6 }

  unisdot1sMstiRootType OBJECT-TYPE
    SYNTAX      INTEGER{normal(0), secondary(1), primary(2)}
    MAX-ACCESS  read-write
    STATUS      current
    DESCRIPTION
        "Config this Bridge as a primary root or secondary root and or cancel
        the root for this spanning tree instance  identified by MSTID"
    DEFVAL      { normal }
    ::={ unisdot1sInstanceEntry 7 }

  unisdot1sMstiRemainingHops OBJECT-TYPE
    SYNTAX      Integer32
    MAX-ACCESS  read-only
    STATUS      current
    DESCRIPTION
        "The remaining hops of the spanning tree instance  identified by MSTID"
    ::={ unisdot1sInstanceEntry 8 }

  unisdot1sMstiAdminMappedVlanListLow  OBJECT-TYPE
    SYNTAX  OCTET STRING (SIZE(0..256))
    MAX-ACCESS read-only
    STATUS current
    DESCRIPTION
        " The lower part of administrative Vlan list mapped to the spanning
        tree instance identified by MSTID"
    ::= { unisdot1sInstanceEntry 9 }

  unisdot1sMstiAdminMappedVlanListHigh  OBJECT-TYPE
    SYNTAX  OCTET STRING (SIZE(0..256))
    MAX-ACCESS read-only
    STATUS current
    DESCRIPTION
        " The higher part of administrative Vlan  list mapped to the spanning
        tree instance identified by MSTID"
    ::= { unisdot1sInstanceEntry 10 }

  unisdot1sMstiOperMappedVlanListLow  OBJECT-TYPE
    SYNTAX  OCTET STRING (SIZE(0..256))
    MAX-ACCESS read-only
    STATUS current
    DESCRIPTION
        " The lower part of operative Vlan list mapped to the spanning
        tree instance identified by MSTID"
    ::= { unisdot1sInstanceEntry 11 }

  unisdot1sMstiOperMappedVlanListHigh  OBJECT-TYPE
    SYNTAX  OCTET STRING (SIZE(0..256))
    MAX-ACCESS read-only
    STATUS current
    DESCRIPTION
        " The higher part of operative Vlan list mapped to the spanning
        tree instance identified by MSTID"
    ::= { unisdot1sInstanceEntry 12 }

-- TABLE: unisdot1sPortTable ------
  unisdot1sPortTable OBJECT-TYPE
    SYNTAX      SEQUENCE OF Unisdot1sPortEntry
    MAX-ACCESS  not-accessible
    STATUS      current
    DESCRIPTION
      "MSTP interface table."
    ::= { unisdot1sMstp 20 }

  unisdot1sPortEntry OBJECT-TYPE
    SYNTAX      Unisdot1sPortEntry
    MAX-ACCESS  not-accessible
    STATUS      current
    DESCRIPTION
      "MSTP interface table entry."
    INDEX {   unisdot1sInstanceID,
              unisdot1sMstiPortIndex
             }
    ::= { unisdot1sPortTable 1 }

  Unisdot1sPortEntry ::=
    SEQUENCE
    {
      unisdot1sMstiPortIndex  Integer32,
      unisdot1sMstiState  INTEGER,
      unisdot1sMstiPortPriority   Integer32,
      unisdot1sMstiPathCost   Integer32,
      unisdot1sMstiDesignatedRoot BridgeId,
      unisdot1sMstiDesignatedCost Integer32,
      unisdot1sMstiDesignatedBridge   BridgeId,
      unisdot1sMstiDesignatedPort OCTET STRING,
      unisdot1sMstiMasterBridgeID BridgeId,
      unisdot1sMstiMasterPortCost Integer32,
      unisdot1sMstiStpPortEdgeport    EnabledStatus,
      unisdot1sMstiStpPortPointToPoint    INTEGER,
      unisdot1sMstiStpMcheck  INTEGER,
      unisdot1sMstiStpTransLimit  Integer32,
      unisdot1sMstiStpRXStpBPDU   Counter32,
      unisdot1sMstiStpTXStpBPDU   Counter32,
      unisdot1sMstiStpRXTCNBPDU   Counter32,
      unisdot1sMstiStpTXTCNBPDU   Counter32,
      unisdot1sMstiStpRXRSTPBPDU  Counter32,
      unisdot1sMstiStpTXRSTPBPDU  Counter32,
      unisdot1sMstiStpRXMSTPBPDU  Counter32,
      unisdot1sMstiStpTXMSTPBPDU  Counter32,
      unisdot1sMstiStpClearStatistics INTEGER,
      unisdot1sMstiStpDefaultPortCost INTEGER,
      unisdot1sMstiStpStatus  EnabledStatus,
      unisdot1sMstiPortRootGuard  EnabledStatus,
      unisdot1sMstiPortLoopGuard  EnabledStatus,
      unisdot1sMstiStpPortSendingBPDUType  INTEGER,
      unisdot1sMstiStpOperPortPointToPoint INTEGER,
      unisdot1sMstiStpPortAdminBPDUFmt  Unisdot1sFormatStatus,
      unisdot1sMstiStpPortOperBPDUFmt  Unisdot1sFormatStatus,
      unisdot1sMstiStpPortRoleRestriction  EnabledStatus,
      unisdot1sMstiStpPortTcRestriction  EnabledStatus,
      unisdot1sMstiStpPortDisputed  TruthValue
    }

  unisdot1sMstiPortIndex OBJECT-TYPE
    SYNTAX      Integer32(0..65535)
    MAX-ACCESS  read-only
    STATUS      current
    DESCRIPTION
        "The index of the Bridge Port"
    ::={ unisdot1sPortEntry 1 }

  unisdot1sMstiState OBJECT-TYPE
    SYNTAX      INTEGER{disabled(1),discarding(2),learning(4),forwarding(5)}
    MAX-ACCESS  read-only
    STATUS      current
    DESCRIPTION
        "The current state of the Port (i.e., Disabled, Discarding ,
        Learning, Forwarding)"
    ::={ unisdot1sPortEntry 2 }

  unisdot1sMstiPortPriority OBJECT-TYPE
    SYNTAX      Integer32(0..240)
    MAX-ACCESS  read-write
    STATUS      current
    DESCRIPTION
        "The value of the priority field which is contained in the
        first (in network byte order)  four bits of the (2 octet long) Port ID.
        The other octet of the Port ID is given by the value of mstiPortIndex.
        And step of 16"
    DEFVAL      { 128 }
    ::={ unisdot1sPortEntry 3 }

  unisdot1sMstiPathCost OBJECT-TYPE
    SYNTAX      Integer32(1..200000000)
    MAX-ACCESS  read-write
    STATUS      current
    DESCRIPTION
        "The contribution of this port to the path cost of paths towards the
        spanning tree root which include this port.  The range of path cost
        is 1..65535 for 802.1d standard, is 1..200000000 for 802.1t standard,
        and is 1..200000 for the legacy standard."
    ::={ unisdot1sPortEntry 4 }

  unisdot1sMstiDesignatedRoot OBJECT-TYPE
    SYNTAX      BridgeId
    MAX-ACCESS  read-only
    STATUS      current
    DESCRIPTION
        "The Bridge Identifier of the Root Bridge for the port of the Spanning
         Tree instance identified by the MSTID"
    ::={ unisdot1sPortEntry 5 }

  unisdot1sMstiDesignatedCost OBJECT-TYPE
    SYNTAX      Integer32
    MAX-ACCESS  read-only
    STATUS      current
    DESCRIPTION
        "The path cost of the Designated Port of the segment connected to
        this port.  This value is compared to the Root Path Cost field
        in received bridge PDUs."
    ::={ unisdot1sPortEntry 6 }

  unisdot1sMstiDesignatedBridge OBJECT-TYPE
    SYNTAX      BridgeId
    MAX-ACCESS  read-only
    STATUS      current
    DESCRIPTION
        "The Bridge Identifier of the bridge which this port considers to
        be the Designated Bridge for this port's segment."
    ::={ unisdot1sPortEntry 7 }

  unisdot1sMstiDesignatedPort OBJECT-TYPE
    SYNTAX      OCTET STRING(SIZE (2))
    MAX-ACCESS  read-only
    STATUS      current
    DESCRIPTION
        "The Port Identifier of the port on the Designated Bridge
        for this port's segment."
    ::={ unisdot1sPortEntry 8 }

  unisdot1sMstiMasterBridgeID OBJECT-TYPE
    SYNTAX      BridgeId
    MAX-ACCESS  read-only
    STATUS      current
    DESCRIPTION
        "The Bridge Identifier of the current Master Bridge.
        Effective in CIST."
    ::={ unisdot1sPortEntry 9 }

  unisdot1sMstiMasterPortCost OBJECT-TYPE
    SYNTAX      Integer32
    MAX-ACCESS  read-only
    STATUS      current
    DESCRIPTION
        "The CIST path cost from the transmitting Bridge to
        the Master Bridge.  Effective in CIST."
    ::={ unisdot1sPortEntry 10 }

  unisdot1sMstiStpPortEdgeport OBJECT-TYPE
    SYNTAX      EnabledStatus
    MAX-ACCESS  read-write
    STATUS      current
    DESCRIPTION
        "Whether the port fast is enabled.  Effective in CIST."
    DEFVAL      { disabled }
    ::={ unisdot1sPortEntry 11 }

  unisdot1sMstiStpPortPointToPoint OBJECT-TYPE
    SYNTAX      INTEGER{forceTrue (1),forceFalse (2),auto  (3)}
    MAX-ACCESS  read-write
    STATUS      current
    DESCRIPTION
        "Whether the port connects the point to point link.  Effective in CIST."
    DEFVAL      { auto }
    ::={ unisdot1sPortEntry 12 }

  unisdot1sMstiStpMcheck OBJECT-TYPE
    SYNTAX      INTEGER{enable(1),unused(65535)}
    MAX-ACCESS  read-write
    STATUS      current
    DESCRIPTION
        " Forcing the state machine to send MST BPDUs in this manner
        can be used to test whether all legacy Bridges on a given LAN
        have been removed.  Effective in CIST."
    ::={ unisdot1sPortEntry 13 }

  unisdot1sMstiStpTransLimit OBJECT-TYPE
    SYNTAX      Integer32(1..255)
    MAX-ACCESS  read-write
    STATUS      current
    DESCRIPTION
        "The value used by the Port Transmit state machine to limit
        the maximum transmission rate.  Effective in CIST."
    ::={ unisdot1sPortEntry 14 }

  unisdot1sMstiStpRXStpBPDU OBJECT-TYPE
    SYNTAX      Counter32
    MAX-ACCESS  read-only
    STATUS      current
    DESCRIPTION
        "The number of received Config BPDU.  Effective in CIST."
    ::={ unisdot1sPortEntry 15 }

  unisdot1sMstiStpTXStpBPDU OBJECT-TYPE
    SYNTAX      Counter32
    MAX-ACCESS  read-only
    STATUS      current
    DESCRIPTION
        "The number of transmitted Config BPDU.  Effective in CIST."
    ::={ unisdot1sPortEntry 16 }

  unisdot1sMstiStpRXTCNBPDU OBJECT-TYPE
    SYNTAX      Counter32
    MAX-ACCESS  read-only
    STATUS      current
    DESCRIPTION
        "The number of received TCN BPDU.  Effective in CIST."
    ::={ unisdot1sPortEntry 17 }

  unisdot1sMstiStpTXTCNBPDU OBJECT-TYPE
    SYNTAX      Counter32
    MAX-ACCESS  read-only
    STATUS      current
    DESCRIPTION
        "The number of transmitted TCN BPDU.  Effective in CIST."
    ::={ unisdot1sPortEntry 18 }

  unisdot1sMstiStpRXRSTPBPDU OBJECT-TYPE
    SYNTAX      Counter32
    MAX-ACCESS  read-only
    STATUS      current
    DESCRIPTION
        "The number of received RST BPDU.  Effective in CIST."
    ::={ unisdot1sPortEntry 19 }

  unisdot1sMstiStpTXRSTPBPDU OBJECT-TYPE
    SYNTAX      Counter32
    MAX-ACCESS  read-only
    STATUS      current
    DESCRIPTION
        "The number of transmitted RST BPDU.  Effective in CIST."
    ::={ unisdot1sPortEntry 20 }

  unisdot1sMstiStpRXMSTPBPDU OBJECT-TYPE
    SYNTAX      Counter32
    MAX-ACCESS  read-only
    STATUS      current
    DESCRIPTION
        "The number of received MST BPDU.  Effective in CIST."
    ::={ unisdot1sPortEntry 21 }

  unisdot1sMstiStpTXMSTPBPDU OBJECT-TYPE
    SYNTAX      Counter32
    MAX-ACCESS  read-only
    STATUS      current
    DESCRIPTION
        "The number of transmitted MST BPDU.  Effective in CIST."
    ::={ unisdot1sPortEntry 22 }

  unisdot1sMstiStpClearStatistics OBJECT-TYPE
    SYNTAX      INTEGER{clear(1),unused(65535)}
    MAX-ACCESS  read-write
    STATUS      current
    DESCRIPTION
        "Clear the spanning tree statistic.  Effective in CIST."
    ::={ unisdot1sPortEntry 23 }

  unisdot1sMstiStpDefaultPortCost OBJECT-TYPE
    SYNTAX      INTEGER{enable(1),unused(65535)}
    MAX-ACCESS  read-write
    STATUS      current
    DESCRIPTION
        "Set default Port path cost."
    ::={ unisdot1sPortEntry 24 }

  unisdot1sMstiStpStatus OBJECT-TYPE
    SYNTAX      EnabledStatus
    MAX-ACCESS  read-write
    STATUS      current
    DESCRIPTION
        "Whether the spanning tree protocol is enabled on this port.
        Effective in CIST."
    DEFVAL      { enabled}
    ::={ unisdot1sPortEntry 25 }

  unisdot1sMstiPortRootGuard OBJECT-TYPE
    SYNTAX      EnabledStatus
    MAX-ACCESS  read-write
    STATUS      current
    DESCRIPTION
        "Whether the root guard is enabled.  Effective in CIST."
    DEFVAL      { disabled }
    ::={ unisdot1sPortEntry 26 }

  unisdot1sMstiPortLoopGuard OBJECT-TYPE
    SYNTAX      EnabledStatus
    MAX-ACCESS  read-write
    STATUS      current
    DESCRIPTION
        "Whether the loop protection is enabled.  Effective in CIST."
    DEFVAL      { disabled }
    ::={ unisdot1sPortEntry 27 }

  unisdot1sMstiStpPortSendingBPDUType  OBJECT-TYPE
    SYNTAX  INTEGER {
                    stp(1),
                    rstp(2),
                    mstp(3)
                    }
    MAX-ACCESS read-only
    STATUS     current
    DESCRIPTION
        "Type of BPDU which the port is sending."
    ::= { unisdot1sPortEntry 28 }

  unisdot1sMstiStpOperPortPointToPoint  OBJECT-TYPE
    SYNTAX  INTEGER {
                    true(1),
                    false(2)
                    }
    MAX-ACCESS read-only
    STATUS current
    DESCRIPTION
        "This object indicates whether the port has connected to a
        point-to-point link or not.  The value of the node is an operative value.
        The administrative value can be read from the node
        unisdot1sMstiStpPortPointToPoint.  If the value of
        unisdot1sMstiStpPortPointToPoint is auto, the value of this node
        should be calculated by the network topology of this port.  If the
        value of unisdot1sMstiStpPortPointToPoint is forceFalse, the value of this
        node is false.  If the value of unisdot1sMstiStpPortPointToPoint is
        forceTrue, the value of this node is true."
    ::= { unisdot1sPortEntry 29 }

  unisdot1sMstiStpPortAdminBPDUFmt  OBJECT-TYPE
    SYNTAX     Unisdot1sFormatStatus
    MAX-ACCESS read-write
    STATUS     current
    DESCRIPTION
       "The value of the node is an administrative value.  Value legacy means that
       the MST BPDU format is forced to legacy.  Value dot1s means that the MST BPDU format
       is forced to IEEE 802.1s.  Value auto means that the format of MST BPDU sending
       on the port is determined by the MST BPDU that the port has received.  Effective in
       CIST."
      ::= { unisdot1sPortEntry 30 }

  unisdot1sMstiStpPortOperBPDUFmt  OBJECT-TYPE
    SYNTAX     Unisdot1sFormatStatus
    MAX-ACCESS read-only
    STATUS     current
    DESCRIPTION
      "The format of MST BPDU which the port is sending.  Value legacy means that the
      format of MST BPDU sending on the port is legacy.  Value dot1s means that the
      format of MST BPDU sending on the port is IEEE 802.1s.  Effective in CIST."
    ::= { unisdot1sPortEntry 31 }

  unisdot1sMstiStpPortRoleRestriction OBJECT-TYPE
    SYNTAX      EnabledStatus
    MAX-ACCESS  read-write
    STATUS      current
    DESCRIPTION
        "Whether the role-restriction is enabled.  Effective in CIST.
         The role-restriction causes the port not to be selected as root port for the
         CIST or any MSTI."
    DEFVAL      { disabled }
    ::= { unisdot1sPortEntry 32 }

  unisdot1sMstiStpPortTcRestriction OBJECT-TYPE
    SYNTAX      EnabledStatus
    MAX-ACCESS  read-write
    STATUS      current
    DESCRIPTION
        "Whether the tc-restriction is enabled.  Effective in CIST.
         The tc-restriction causes the port not to propagate topology changes to
         other ports."
    DEFVAL      { disabled }
    ::= { unisdot1sPortEntry 33 }

  unisdot1sMstiStpPortDisputed OBJECT-TYPE
    SYNTAX      TruthValue
    MAX-ACCESS  read-only
    STATUS      current
    DESCRIPTION
        "Whether the port is disputed for the CIST or MSTI."
    ::= { unisdot1sPortEntry 34 }

  unisdot1sStpPathCostStandard  OBJECT-TYPE
    SYNTAX      INTEGER{legacy(0),dot1d-1998(1),dot1t(2)}
    MAX-ACCESS  read-write
    STATUS      current
    DESCRIPTION
      "Path cost standard of the bridge.  Value dot1d-1998 is
      IEEE 802.1d standard in 1998, value dot1t is IEEE 802.1t standard,
      and value legacy is a private legacy standard."
    ::= { unisdot1sMstp 21 }

--  Mstp Traps

  unisMstpEventsV2 OBJECT-IDENTITY
     STATUS      current
     DESCRIPTION "Definition point for Mstp notifications."
     ::= { unisdot1sMstp 0 }

  unisPortMstiStateForwarding NOTIFICATION-TYPE
     OBJECTS  { unisdot1sInstanceID , unisdot1sMstiPortIndex}
     STATUS   current
     DESCRIPTION
         "The SNMP trap that is generated when a port turns into
         forwarding state form other state."
     ::= { unisMstpEventsV2 1 }

  unisPortMstiStateDiscarding NOTIFICATION-TYPE
     OBJECTS  { unisdot1sInstanceID , unisdot1sMstiPortIndex}
     STATUS   current
     DESCRIPTION
         "The SNMP trap that is generated when a port turns into
         discarding state form forwarding state."
     ::= { unisMstpEventsV2 2 }


  unisBridgeLostRootPrimary NOTIFICATION-TYPE
     OBJECTS  { unisdot1sInstanceID }
     STATUS   current
     DESCRIPTION
         "The SNMP trap that is generated when the bridge is no longer
         the root bridge of the instance.  Another switch with higher
         priority has already been the root bridge of the instance."
     ::= { unisMstpEventsV2 3 }

  unisPortMstiRootGuarded NOTIFICATION-TYPE
     OBJECTS  { unisdot1sInstanceID , unisdot1sMstiPortIndex}
     STATUS   current
     DESCRIPTION
         "The SNMP trap that is generated when a root-guard port
         receives a superior message on the relevant instance."
     ::= { unisMstpEventsV2 4 }

  unisPortMstiBpduGuarded NOTIFICATION-TYPE
     OBJECTS  { dot1dStpPort , unisdot1sMstiDesignatedBridge}
     STATUS   current
     DESCRIPTION
         "The SNMP trap is generated when an edged port of the BPDU-guard
         device receives a BPDU.  If the designated bridge ID can't be obtained
         from the BPDU, the designated bridge ID will be zero."
     ::= { unisMstpEventsV2 5 }

  unisPortMstiLoopGuarded NOTIFICATION-TYPE
     OBJECTS  { unisdot1sInstanceID , unisdot1sMstiPortIndex}
     STATUS   current
     DESCRIPTION
         "The SNMP trap that is generated when an Alternate-Port
         or Root-Port is aged out."
     ::= { unisMstpEventsV2 6 }

  unisMstiNewRoot NOTIFICATION-TYPE
     OBJECTS  { unisdot1sInstanceID , unisdot1sMstiDesignedRoot , unisdot1sMstiDesignedRoot}
     STATUS   current
     DESCRIPTION
         "The SNMP trap is generated when the sending device becomes the new
         root of the spanning tree.  The first root bridge ID means the
         old root bridge ID, and the second one means the new root bridge ID."
     ::= { unisMstpEventsV2 7 }

  unisPortPvstBpduProtection NOTIFICATION-TYPE
     OBJECTS  { dot1dStpPort , unisdot1sMstiDesignatedBridge}
     STATUS   current
     DESCRIPTION
         "The SNMP trap is generated when a PVST BPDU is received on an MSTP port
         that is enabled with the PVST protection feature.  If the designated
         bridge ID can't be obtained from the BPDU, the designated bridge ID
         will be zero."
     ::= { unisMstpEventsV2 8 }
END
