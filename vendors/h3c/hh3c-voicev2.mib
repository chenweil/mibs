-- ====================================================================
-- Copyright (c) 2004-2024 New H3C Tech. Co., Ltd. All rights reserved.
--
-- Description: The MIB is designed to get voice call statistic information.
--
-- Reference:
-- Version: 1.0
-- History:
--     V1.0: The initial version created by Liuliangchen.
-- =====================================================================
HH3C-VOICEV2-MIB DEFINITIONS ::= BEGIN

IMPORTS
    Counter64, OBJECT-TYPE, MODULE-IDENTITY
        FROM SNMPv2-SMI
    hh3cCommon
        FROM HH3C-OID-MIB;

hh3cVoiceV2 MODULE-IDENTITY
    LAST-UPDATED "202407241347Z"            -- Jul. 24, 2024  GMT
    ORGANIZATION
        "New H3C Technologies Co., Ltd."
    CONTACT-INFO
        "No.466 Changhe Road, Binjiang District, Hangzhou, Zhejiang
        http://www.h3c.com
        Zip: 310052"
    DESCRIPTION
        "The MIB is designed to get statistic information of
        voice.  With this MIB, we can get information of Call Statistic."
    REVISION
        "202407241347Z"
    DESCRIPTION
        "Initial version."
    ::= { hh3cCommon 269 }


-- ========================================================================
-- Node definitions
-- ========================================================================
-- Begin the node of hh3cVoiceV2Objects.

hh3cVoiceV2Objects OBJECT IDENTIFIER ::= { hh3cVoiceV2 1 }
-- ================================================
-- Begin the hh3cVoiceV2CallStats.
-- ================================================

hh3cVoiceV2CallStats OBJECT IDENTIFIER ::= { hh3cVoiceV2Objects 1 }

hh3cVoiceV2CallTotalCount OBJECT-TYPE
    SYNTAX Counter64
    MAX-ACCESS read-only
    STATUS current
    DESCRIPTION
        "Total Call Count from Process Start to Process End."
    ::= { hh3cVoiceV2CallStats 1 }

hh3cVoiceV2CallSuccessCount OBJECT-TYPE
    SYNTAX Counter64
    MAX-ACCESS read-only
    STATUS current
    DESCRIPTION
        "Count of Successfully Answered Calls from Process Start to Process End."
    ::= { hh3cVoiceV2CallStats 2 }

END
