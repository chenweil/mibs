-- =================================================================
-- Copyright (c) 2004-2023 New H3C Tech. Co., Ltd.  All rights reserved.
--
-- Description: Password Control MIB
-- Reference:
-- Version: V1.0
-- History:
--  V1.0 2023-10-17 Initial version, create by jiangzuhuan
-- =================================================================
HH3C-PASSWORD-CONTROL-MIB DEFINITIONS ::= BEGIN


IMPORTS
    hh3cCommon
        FROM HH3C-OID-MIB
    NOTIFICATION-TYPE, MODULE-IDENTITY
        FROM SNMPv2-SMI;

hh3cPwdctl MODULE-IDENTITY
    LAST-UPDATED "202310171800Z"            -- October 17, 2023 at 18:00 GMT
    ORGANIZATION
        "New H3C Technologies Co., Ltd."
    CONTACT-INFO
        "No.466 Changhe Road, Binjiang District, Hangzhou, Zhejiang
         http://www.h3c.com
         Zip: 310052"
    DESCRIPTION
        "The MIB module is used for managing password control."
    REVISION "202310171800Z"        -- October 17, 2023 at 18:00 GMT
    DESCRIPTION
         "The initial version."
    ::= { hh3cCommon 267 }

-- ----------------------------------------------------------------------
-- hh3cPwdctlTraps Table
-- ----------------------------------------------------------------------
hh3cPwdctlTraps      OBJECT IDENTIFIER ::= { hh3cPwdctl 1 }
hh3cPwdctlTrapsDefine      OBJECT IDENTIFIER ::= { hh3cPwdctlTraps 0 }

hh3cPwdctlFailedCopyFileTrap NOTIFICATION-TYPE
    STATUS current
    DESCRIPTION
        "This notification is generated when the device is unable to copy
         password control file to the backup control board."
    ::= { hh3cPwdctlTrapsDefine 1 }

hh3cPwdctlFailedWritePwdTrap NOTIFICATION-TYPE
    STATUS current
    DESCRIPTION
        "This notification is generated when the device is unable to write
        the password records to the password control file."
    ::= { hh3cPwdctlTrapsDefine 2 }

hh3cPwdctlFailedOpenFileTrap NOTIFICATION-TYPE
    STATUS current
    DESCRIPTION
        "This notification is generated when the device fails to create or open
         the password control file."
    ::= { hh3cPwdctlTrapsDefine 3 }

hh3cPwdctlNoEnoughSpaceTrap NOTIFICATION-TYPE
    STATUS current
    DESCRIPTION
        "This notification is generated when the storage medium
        where the password control file is located does not have
        sufficient storage space."
    ::= { hh3cPwdctlTrapsDefine 4 }

hh3cPwdctlNotifyWriteFileTrap NOTIFICATION-TYPE
    STATUS current
    DESCRIPTION
        "This notification is generated when the device fails to notify
         the event of writing password records to the password control file."
    ::= { hh3cPwdctlTrapsDefine 5 }

hh3cPwdctlRecFormatConvTrap NOTIFICATION-TYPE
    STATUS current
    DESCRIPTION
        "This notification is generated when the device fails to convert
        the password record format."
    ::= { hh3cPwdctlTrapsDefine 6 }

END
