-- =============================================================================
-- Copyright (c) 2004-2023 New H3C Tech. Co., Ltd.  All rights reserved.
--
-- Description:
--   The file defines a MIB to provide AP object information such as
--   performance statistic and notification events.
-- Reference:
-- Version: V3.8
-- History:
--   V1.0 2006-05-10 Initial version, created by shiyang (Richard)
--   V1.1 2007-02-01 modified by xingjichen(Daniel)
--        Changed DESCRIPTION of hh3cDot11APRxStatisTable,
--        hh3cDot11APTxStatisTable,hh3cDot11APMtRadioFailTrap,
--        hh3cDot11APMtRadioFailRecoverTrap.
--   V1.2 2007-04-27 modified by shiyang(Richard)
--        Add new nodes of hh3cDot11APChannelChgMode and hh3cDot11APChgWorkMode.
--        Split hh3cDot11APObjectTable table into hh3cDot11APObjectStatusTable
--        and hh3cDot11APObjectTable.
--        Rename hh3cDot11APRadioRelationTable as hh3cDot11APRadioTable.
--        Rename hh3cDot11APBSSRelationTable as hh3cDot11APBSSTable.
--   V1.3 2007-06-19 modified by Banasree
--        Add new table of hh3cDot11APIfTable for hh3cDot11APObjectGroup.
--        Add new table of hh3cDot11APAssocStatisTable for hh3cDot11APStatisGroup.
--        Add new node of hh3cDot11CurrAPName, hh3cDot11CurrAPModelName,
--        hh3cDot11CurrAPImageName, hh3cDot11CurrAPSoftwareVersion,
--        hh3cDot11CurrAPIPNetMask, hh3cDot11CurrRadioModeSupport for
--        hh3cDot11APObjectTable.
--        Add new node of hh3cDot11Channel, hh3cDot11TxPowerLevel,
--        hh3cDot11APRadioIfIndex, hh3cDot11AntennaGain for hh3cDot11APRadioTable.
--        Add new node of hh3cDot11APManufacturer, hh3cDot11APCPUType,
--        hh3cDot11APCPUClockSpeed, hh3cDot11APMemoryType, hh3cDot11APMemorySize,
--        hh3cDot11APFlashType, hh3cDot11APFlashSize for hh3cDot11APModelTable
--        Add hh3cDot11APReset node to the hh3cDot11APObjectStatusTable.
--        Add hh3cDot11RxFrameErrorRatio to the hh3cDot11APRxStatisTable.
--        Add_hh3cDot11TxFrameRetryRatio to the hh3cDot11APTxStatisTable.
--   V1.4 2007-12-21 modified by wanghao (Kumar)
--        Add hh3cDot11BSSRxStatisTable, hh3cDot11BSSTxStatisTable,
--        hh3cDot11BSSAssocStatisTable for BSS statistics.
--        Add hh3cDot11APCpuUsage to hh3cDot11APObjectStatusTable.
--        Add hh3cDot11MaxBandwidth to hh3cDot11APRadioTable.
--        Add hh3cDot11RxPhyErrorCnt, hh3cDot11RxMICErrorCnt,
--        hh3cDot11RxDataFrameBytes to hh3cDot11APRxStatisTable.
--        Add hh3cDot11TxDataFrameCnt, hh3cDot11TxDataFrameBytes to
--        hh3cDot11APTxStatisTable.
--        Add hh3cDot11ApStationExDeAuthenSum, hh3cDot11ApStationCurAssocSum to
--        hh3cDot11APAssocStatisTable.
--   V1.5 2008-02-25 modified by wanghao (Kumar)
--        Add hh3cDot11ResourceUseRatio to hh3cDot11APRadioTable.
--   V1.6 2008-07-09 modified by ChangHuifeng
--        Add hh3cDot11APConnectionType to hh3cDot11APObjectStatusTable.
--   V1.7 2008-11-07 modified by Wang Lu and Li Yugang
--        Add hh3cDot11APLinkStatisTable and hh3cDot11RadioAssocStatisTable.
--        Add hh3cDot11CurrIfNumber to hh3cDot11APObjectTable.
--        Add hh3cDot11RadioModeSupport, hh3cDot11TxPowerLevel2 and
--        hh3cDot11PowerMgmtStatus to hh3cDot11APRadioTable.
--        Add hh3cDot11SSID to hh3cDot11APBSSTable.
--        Add hh3cDot11APIfSpeed, hh3cDot11APIfInDataRate and
--        hh3cDot11APIfOutDataRate to hh3cDot11APIfTable
--        Add hh3cDot11RadioRxAverSnr to hh3cDot11APRxStatisTable.
--        Add hh3cDot11APMtTimeSynFail, hh3cDot11APMtChlIntfDetected,
--        hh3cDot11APMtIntfAPDetected, hh3cDot11APMtIntfStaDetected,
--        hh3cDot11APMtIPChange, hh3cDot11APFlashWriteFailure,
--        hh3cDot11APSysReboot, hh3cDot11APMtAvailChlTooLow and
--        hh3cDot11APImgDwldSuccess to hh3cDot11APMtTraps.
--        Add hh3cDot11APIntfDevMACAddress and hh3cDot11APMtTrapOldIPAddr to
--        hh3cDot11APMtTrapVarObjects.
--        Add hh3cDot11ChannelSwitchTimes to hh3cDot11APRadioTable.
--        Add hh3cDot11RxPayloadBytes, hh3cDot11RxTrafficSpeed to
--        hh3cDot11APRxStatisTable.
--        Add hh3cDot11TxMSDUCnt, hh3cDot11TxDiscardMSDUCnt,
--        hh3cDot11RetryMSDUCnt, hh3cDot11TxPayloadBytes,
--        hh3cDot11TxTrafficSpeed to hh3cDot11APTxStatisTable.
--        Add hh3cDot11ApStaCurAuthSuccSum, hh3cDot11AllStationUpSumTime,
--        hh3cDot11ApStationAssocReqSum to hh3cDot11APAssocStatisTable.
--        Add hh3cDot11BSSRxFrameErrorRatio, hh3cDot11BSSRxPayloadBytes to
--        hh3cDot11BSSRxStatisTable.
--        Add hh3cDot11BSSTxPayloadBytes to hh3cDot11BSSTxStatisTable.
--        Add hh3cDot11BSSStationAssocReqSum to hh3cDot11BSSAssocStatisTable.
--        Add new tables hh3cDot11RadioMngFrameStatisTable,
--        hh3cDot11APAuthFailStatisTable, hh3cDot11APAssocFailStatisTable,
--        hh3cDot11APReassocStatisTable, hh3cDot11APUserAuthStatisTable,
--        hh3cDot11APDeauthStatisTable, hh3cDot11APDeassocStatisTable to
--        hh3cDot11APStatisGroup.
--   V1.8 2009-04-17 modified by WangChunsheng
--        Add hh3cDot11AntennaType to hh3cDot11APRadioTable.
--   V1.9 2009-05-07 modified by Li Yugang, Wang Shaojie, Jin Yi
--        Add hh3cDot11CurrAPElementID to hh3cDot11APObjectTable.
--        Add hh3cDot11DiversitySelectionRx, hh3cDot11MaxTxPwrLvl,
--        hh3cDot11PwrAttRange, hh3cDot11AvgRxSignalStrength,
--        hh3cDot11HighestRxSignalStrength, hh3cDot11LowestRxSignalStrength
--        hh3cDot11RadioIfUpdownTimes, hh3cDot11RadioIfLastChange
--        to hh3cDot11APRadioTable.
--        Add hh3cDot11CurrSSIDResourceUseRatio to hh3cDot11APBSSTable.
--        Add new table hh3cDot11APSSIDObjectTable, hh3cDot11APSysInfoTable
--        to hh3cDot11APObjectGroup.
--        Add hh3cDot11TxErrFrameRatio, hh3cDot11TxFrameRate
--        to hh3cDot11APTxStatisTable.
--        Add hh3cDot11BSSRxUniFrameCnt, hh3cDot11BSSRxNonUniFrameCnt,
--        hh3cDot11BSSRxAuthenFrameCnt to hh3cDot11BSSRxStatisTable.
--        Add hh3cDot11BSSTxRetryCnt, hh3cDot11BSSTxUniFrameCnt,
--        hh3cDot11BSSTxNonUniFrameCnt, hh3cDot11BSSTxAuthenFrameCnt
--        to hh3cDot11BSSTxStatisTable.
--        Add new table hh3cDot11APAssocFailStatis2Table, hh3cDot11APIfStatisTable
--        to hh3cDot11APStatisGroup.
--        Add hh3cDot11APInterfDetectedTrap,
--        hh3cDot11APInterfClearTrap, hh3cDot11StaInterfDetectedTrap,
--        hh3cDot11StaInterfClearTrap, hh3cDot11OtherDevIntDetectedTrap,
--        hh3cDot11OtherDevIntClearTrap, hh3cDot11APModuleTroubleTrap,
--        hh3cDot11APModuleTroubleClearTrap, hh3cDot11APRadioDownTrap,
--        hh3cDot11APRadioDownRecovTrap, hh3cDot11APStaFullTrap,
--        hh3cDot11APStaFullRecoverTrap, hh3cDot11DFSFreeCntBelowThrRecov,
--        hh3cDot11APCpuUsageHigh, hh3cDot11APCpuUsageHighRecover,
--        hh3cDot11APMemUsageHigh, hh3cDot11APMemUsageHighRecover
--        to hh3cDot11APMtTraps.
--        Add hh3cDot11CurrInterfDetectedNum, hh3cDot11StaFullReason,
--        hh3cDot11StaLimitNumber, hh3cDot11APRadioDownReason,
--        hh3cDot11InterfMacList to hh3cDot11APMtTrapVarObjects.
--        Add hh3cDot11APLastImgDownloadTime to hh3cDot11APObjectStatusTable.
--   V2.0 2009-07-29 modified by Heziqi
--        Add new node hh3cDot11CurrAPMode for hh3cDot11APObjectTable.
--        Add new node hh3cDot11APEssVlanId and hh3cDot11APBSSResourceUseRatio
--        for hh3cDot11APBSSTable.
--        Add new node hh3cDot11APTrapUserCnt and hh3cDot11APTrapUserThreshold
--        for hh3cDot11APMtTrapVarObjects.
--        Add hh3cDot11APUserCntOverFlow for hh3cDot11APMtNotifyGroup.
--        Add new node hh3cDot11TxDiscardFrameRatio, hh3cDot11TxFrameRate,
--        hh3cDot11TxMgtFrameCnt and hh3cDot11TxCtrlFrameCnt
--        for hh3cDot11APTxStatisTable.
--        Add new node hh3cDot11APIPv6Address for hh3cDot11APObjectStatusTable.
--        Add new node hh3cDot11CurrAPIPv6Address for hh3cDot11APObjectTable.
--        Add hh3cDot11RadioMngFrmStatisTable.
--   V2.1 2009-08-07 modified by wang shaojie, Jin Yi
--        Add hh3cDot11APIfInBrdcastPkts, hh3cDot11APIfOutBrdcastPkts,
--        hh3cDot11APIfInMulcastPkts, hh3cDot11APIfOutMulcastPkts,
--        hh3cDot11APIfInPayloadOctets, hh3cDot11APIfOutPayloadOctets to
--        hh3cDot11APIfStatisTable.
--        Add new node hh3cDot11APLastRegisterTime to hh3cDot11APObjectStatusTable
--        Add new node hh3cDot11TxMACErrCnt, hh3cDot11TxErrFrameCnt to
--        hh3cDot11APTxStatisTable.
--        Add new variable bindings hh3cDot11APMtChanlChgCount to
--        hh3cDot11APMtRdoChanlChgTrap.
--   V2.2 2009-12-01 modified by Wang Shaojie, duyanbing
--        Add new table hh3cDot11APIdleListTable to hh3cDot11APObjectGroup.
--        Add new table hh3cDot11APPacketSizeStatisTable,
--        hh3cDot11APPacketRateStatisTable, hh3cDot11APPacketMCSRateStatisTable to
--        hh3cDot11APStatisGroup.
--        Add new node hh3cDot11RxUcastDataFrameCnt, hh3cDot11RxNUcastDataFrameCnt
--        to hh3cDot11APRxStatisTable.
--        Add new node hh3cDot11TxUcastDataFrameCnt, hh3cDot11TxNUcastDataFrameCnt
--        to hh3cDot11APTxStatisTable.
--        Add new node hh3cDot11CurrAPSSIDNumber to hh3cDot11APObjectTable.
--        Add new node hh3cDot11AllStationUpSumTimeTicks to
--        hh3cDot11APAssocStatisTable
--        Add new node hh3cDot11RxTotalDiscardFrameCnt to hh3cDot11APRxStatisTable.
--        Added hh3cDot11APMtTrapSwitch.
--        2010-02-23 modified by Wang Shaojie
--        Add hh3cDot11APMtDetectedIntfAP, hh3cDot11APMtDetectedIntfSTA,
--        hh3cDot11APMtDetectedIntfOtherDev to hh3cDot11APMtTraps.
--        Add hh3cDot11APMtFormerApVersion, hh3cDot11APMtAPID, hh3cDot11APMtRadioID
--        hh3cDot11APMtChannel, hh3cDot11APMtInterfMacAdd to
--        hh3cDot11APMtTrapVarObjects.
--        2010-03-15 modified by Deng Gaoliang
--        Add hh3cDot11APAssocFailStatis3Table
--        Add hh3cDot11APFlashSizeInBytes
--        Remove hh3cDot11APMtTrapSwitch
--        2010-05-31 modified by LiuChen, Wang Chunsheng, Wang Shaojie
--        Add new table hh3cDot11APSysInfoByAPIDTable.
--        Add new node hh3cDot11CurrAPManufacturer, hh3cDot11CurrAPMemorySize,
--        hh3cDot11CurrAPMemSizeInBytes, hh3cDot11CurrAPFlashSize,
--        hh3cDot11CurrAPFlashSizeInBytes to hh3cDot11APObjectTable.
--        Add new table hh3cDot11APUserSecAuthStatisTable to hh3cDot11APStatisGroup.
--        Add new table hh3cDot11APUserInfoStatisTable to hh3cDot11APStatisGroup.
--        2010-08-05 modified by LiuChen, Yinjunjie
--        Add new node hh3cDot11CurrAPReleasedVersion to hh3cDot11APObjectTable.
--        Add new node hh3cDot11BSSStationCurAuthSum to hh3cDot11BSSAssocStatisTable.
--        Add new node hh3cDot11APMtAdjChannel.
--        Add hh3cDot11DetcAdjChlIntfAP, hh3cDot11DetcAdjChlIntfAPClear
--        to hh3cDot11APMtTraps.
--        2010-08-05 modified by Yinjunjie
--        Add new table hh3cDot11APReassocStatis2Table
--        2010-09-16 Change names from hh3cDot11APIfLastChange and
--        hh3cDot11APIfLastChange2 to hh3cDot11APIfStatusKeepTime and
--        hh3cDot11APIfStatusKeepTime2 by shuaixiaojuan
--   V2.3 2010-10-11 modified by Wuxiaopeng
--        Add new node hh3cDot11APIfInDataOctets2, hh3cDot11APIfOutDataOctets2,
--        to hh3cDot11APIfStatisByAPIDTable.
--        Add new node hh3cDot11APMacAddress2 to hh3cDot11APSysInfoByAPIDTable.
--        Modify node hh3cDot11APChgWorkMode.
--   V2.4 2011-07-13 modified by Yu Bo
--        Add new node hh3cDot11RxTotalIPCheckErrPacketCnt to hh3cDot11APRxStatisTable
--        Add new node hh3cDot11APConfigPortalStaNum to hh3cDot11APSSIDObjectTable
--        2011-08-08 modified by Donglaqi
--        Add new node hh3cDot11AllUserOnlineTime to hh3cDot11APUserSecAuthStatisTable
--        2011-08-10 modified by limingjin
--        Add new node hh3cDot11RadioModeSupport2 to hh3cDot11APRadioTable
--        Add new node hh3cDot11CurrRadioModeSupport2 to hh3cDot11APObjectTable
--   V2.5 2011-09-27 modified by Limingjin
--        Add hh3cDot11TrafficTable
--        2011-09-28 modified by Li Honghao & jiaolibin
--        Add new table hh3cDot11APEchoStatisTable
--        Add hh3cDot11APEchoAvgDelay, hh3cDot11APEchoRequestCnt,
--        hh3cDot11APEchoRespLossCnt to hh3cDot11APEchoStatisTable
--        Add hh3cDot11APMtFirstTrapTime to hh3cDot11APMtTrapVarObjects and
--        varialbe bindings hh3cDot11APMtFirstTrapTime for
--        hh3cDot11APInterfClearTrap, hh3cDot11StaInterfDetectedTrap,
--        hh3cDot11StaInterfClearTrap, hh3cDot11OtherDevIntDetectedTrap,
--        hh3cDot11OtherDevIntClearTrap, hh3cDot11APRadioDownTrap ,
--        hh3cDot11APRadioDownRecovTrap, hh3cDot11APStaFullTrap,
--        hh3cDot11APStaFullRecoverTrap, hh3cDot11APMtDetectedIntfAP,
--        hh3cDot11DetcAdjChlIntfAP, hh3cDot11DetcAdjChlIntfAPClear,
--        hh3cDot11APMtDetectedIntfSTA
--   V2.6 2012-05-08 modified by Lihonghao
--        Add new table hh3cDot11APUserSecAuthTypeStatisTable
--        Add hh3cDot11APPortalOnlineUserNum, hh3cDot11APAuthFreeOnlineUserNum,
--        hh3cDot11APAssocAuthOnlineUserNum, hh3cDot11APMacAuthOnlineUserNum,
--        hh3cDot11APAllPortalUserOnlineTime, hh3cDot11APAllAuthFreeUserOnlineTime,
--        hh3cDot11APAllAssocAuthUserOnlineTime, hh3cDot11APAllMacAuthUserOnlineTime,
--        hh3cDot11APPortalUserLostCnntCnt, hh3cDot11APAuthFreeUserLostCnntCnt,
--        hh3cDot11APAssocAuthUserLostCnntCnt, hh3cDot11APMacAuthUserLostCnntCnt,
--        hh3cDot11APPortalAuthReqCnt, hh3cDot11APAssocAuthReqCnt,
--        hh3cDot11APMacAuthReqCnt, hh3cDot11APPortalAuthSucCnt,
--        hh3cDot11APAssocAuthSucCnt, hh3cDot11APMacAuthSucCnt,
--        hh3cDot11APPortalAuthReqFailCnt, hh3cDot11APAssocAuthReqFailCnt,
--        hh3cDot11APMacAuthReqFailCnt to hh3cDot11APUserSecAuthTypeStatisTable
--    2012-04-25 modified by Wang Shaojie
--        Add new table hh3cDot11RadioRxStatis64Table, hh3cDot11RadioTxStatis64Table,
--        hh3cDot11BSSRxStatis64Table, hh3cDot11BSSTxStatis64Table to
--        hh3cDot11APStatisGroup.
--    2012-08-12 modified by Zhang Congcong & Chen Zhao liang & Li Xin
--        Add new node   hh3cDot11APMtTrapAPMacAddress to hh3cDot11APMtTrapVarObjects
--        Add new object hh3cDot11APMtTrapAPMacAddress to hh3cDot11APMtWorkModeChgTrap
--        Add new object hh3cDot11APMtTrapAPMacAddress to hh3cDot11APFlashWriteFailure
--        Add new object hh3cDot11APMtTrapAPMacAddress to hh3cDot11APMtDetectedIntfAP
--        Add new object hh3cDot11APMtTrapAPMacAddress to hh3cDot11APInterfClearTrap
--        Add new object hh3cDot11APMtTrapAPMacAddress to hh3cDot11APMtDetectedIntfSTA
--        Add new object hh3cDot11APMtTrapAPMacAddress to hh3cDot11StaInterfClearTrap
--        Add new object hh3cDot11APMtTrapAPMacAddress to hh3cDot11APMtDetectedIntfOtherDev
--        Add new object hh3cDot11APMtTrapAPMacAddress to hh3cDot11OtherDevIntClearTrap
--        Add new object hh3cDot11APMtTrapAPMacAddress to hh3cDot11APModuleTroubleTrap
--        Add new object hh3cDot11APMtTrapAPMacAddress to hh3cDot11APModuleTroubleClearTrap
--        Add new object hh3cDot11APMtTrapAPMacAddress to hh3cDot11APRadioDownTrap
--        Add new object hh3cDot11APMtTrapAPMacAddress to hh3cDot11APRadioDownRecovTrap
--        Add new object hh3cDot11APMtTrapAPMacAddress to hh3cDot11APStaFullTrap
--        Add new object hh3cDot11APMtTrapAPMacAddress to hh3cDot11APStaFullRecoverTrap
--        Add new object hh3cDot11APMtTrapAPMacAddress to hh3cDot11APMtAvailChlTooLow
--        Add new object hh3cDot11APMtTrapAPMacAddress to hh3cDot11DFSFreeCntBelowThrRecov
--        Add new object hh3cDot11APMtTrapAPMacAddress to hh3cDot11APMtRdoChanlChgTrap
--   V2.7 2013-01-16 modified by Peng Nao
--        Add new object hh3cDot11APMtTrapAPMacAddress to hh3cDot11APCpuUsageHigh
--        Add new object hh3cDot11APMtTrapAPMacAddress to hh3cDot11APCpuUsageHighRecover
--        Add new object hh3cDot11APMtTrapAPMacAddress to hh3cDot11APMemUsageHigh
--        Add new object hh3cDot11APMtTrapAPMacAddress to hh3cDot11APMemUsageHighRecover
--   V2.8 2013-07-01 modified by LiuYanjie
--        Add new table hh3cDot11APPacketMCSRateStatis2Table to hh3cDot11APStatisGroup.
--        2013-07-08 modified by Chen Guoxi
--        Add new node  hh3cDot11ApStationReassocReqSum      to hh3cDot11APAssocStatisEntry
--        Add new node  hh3cDot11ApStationReassocFailSum     to hh3cDot11APAssocStatisEntry
--   V2.9 2013-09-02 Added hh3cDot11OperStatusCM to hh3cDot11APRadioTable by Zhang Siyu
--        2013-09-13 Added hh3cDot11APIfAdminStatus,hh3cDot11APIfOperStatusCM and
--        hh3cDot11APACAssociateStatusCM by duyanbing
--   V3.0 2014-02-10 modified by weixiangxiang
--        Add new object hh3cDot11APResetCM to hh3cDot11APObjectStatusTable
--        Add new object hh3cDot11CurrAPCPUTypeCM to hh3cDot11APObjectTable
--        Add new object hh3cDot11CurrAPMemoryTypeCM to hh3cDot11APObjectTable
--        Add new object hh3cDot11CurrAPBSSIDNumberCM to hh3cDot11APObjectTable
--        Add new object hh3cDot11APIfTypeCM to hh3cDot11APIfTable
--        Add new object hh3cDot11RxSignalStrengthPacketCntCM to hh3cDot11APRxStatisTable
--        Add new object hh3cDot11APAssocFailStatis3RSSILowCntCM to hh3cDot11APAssocFailStatis3Table
--        Add new object hh3cDot11APUserLoginNameCM to hh3cDot11APUserInfoStatisTable
--        Add new object hh3cDot11APUserAuthTypeCM to hh3cDot11APUserInfoStatisTable
--        Add new object hh3cDot11APUserTxPacketCntCM to hh3cDot11APUserInfoStatisTable
--        Add new object hh3cDot11APUserTxBytesCM to hh3cDot11APUserInfoStatisTable
--        Add new object hh3cDot11APUserRxPacketCntCM to hh3cDot11APUserInfoStatisTable
--        Add new object hh3cDot11APUserRxBytesCM to hh3cDot11APUserInfoStatisTable
--        Add new table hh3cDot11APUserSecAuthStatisCMTable to hh3cDot11APStatisGroup
--        Add new object hh3cDot11APAutoAuthOnlineUserNumCM to hh3cDot11APUserSecAuthTypeStatisTable
--        Add new object hh3cDot11APAllAutoAuthOnlineTimeCM to hh3cDot11APUserSecAuthTypeStatisTable
--        Add new object hh3cDot11APAutoAuthUserLostCnntCntCM to hh3cDot11APUserSecAuthTypeStatisTable
--        Add new object hh3cDot11APAutoAuthReqCntCM to hh3cDot11APUserSecAuthTypeStatisTable
--        Add new object hh3cDot11APAutoAuthSucCntCM to hh3cDot11APUserSecAuthTypeStatisTable
--        Add new object hh3cDot11APAutoAuthReqFailCntCM to hh3cDot11APUserSecAuthTypeStatisTable
--        Modify object hh3cDot11APPortalOnlineUserNum from hh3cDot11APUserSecAuthTypeStatisTable
--        Modify object hh3cDot11APAssocAuthOnlineUserNum from hh3cDot11APUserSecAuthTypeStatisTable
--        Add hh3cDot11RxDataFrameCntCM to hh3cDot11APRxStatisTable
--        Add hh3cDot11Rx64DataFrameBytesCM to hh3cDot11RadioRxStatis64Table
--   V3.1 2014-05-15 modified by yubo
--        Add new object hh3cDot11PrivateSrvRxFrameBytes  to hh3cDot11APLinkStatisTable
--        Add new object hh3cDot11PrivateSrvTxFrameBytes  to hh3cDot11APLinkStatisTable
--        Add new object hh3cDot11APInternetAllRxBytes    to hh3cDot11APLinkStatisTable
--        Add new object hh3cDot11APInternetAllTxBytes    to hh3cDot11APLinkStatisTable
--        Add new object hh3cDot11APLocalAllRxBytes       to hh3cDot11APLinkStatisTable
--        Add new object hh3cDot11APLocalAllTxBytes       to hh3cDot11APLinkStatisTable
--        Add new object hh3cDot11APPowerOffTrap          to hh3cDot11APMtTraps
--        Add new object hh3cDot11APPowerOnTrap           to hh3cDot11APMtTraps
--        Add new object hh3cDot11UpLinkSwitchTrap        to hh3cDot11APMtTraps
--        Add new object hh3cDot11APMtUpLinkSwitchInfo    to hh3cDot11APMtTrapVarObjects
--        Add new object hh3cDot11APMtUpLinkSwitchTime    to hh3cDot11APMtTrapVarObjects
--        Add new object hh3cDot11APMtOldCellId           to hh3cDot11APMtTrapVarObjects
--        Add new object hh3cDot11APMtCurCellId           to hh3cDot11APMtTrapVarObjects
--        Add new object hh3cDot11APMtOldBand             to hh3cDot11APMtTrapVarObjects
--        Add new object hh3cDot11APMtActiveBand          to hh3cDot11APMtTrapVarObjects
--        Add new table hh3cDot11APUserInfoStatis2CMTable to hh3cDot11APStatisGroup
--        Add new object hh3cDot11RxTotalFrameCnt         to hh3cDot11APRxStatisTable
--        Add new object hh3cDot11TxTotalFrameCnt         to hh3cDot11APTxStatisTable
--   V3.2 2014-11-19 modified by yubo
--        Add new object hh3cDot11AirPrimChnlBusy       to hh3cDot11APRadioTable
--        Add new object hh3cDot11AirPrimChnlTxBusy     to hh3cDot11APRadioTable
--        Add new object hh3cDot11AirPrimChnlRxBusy     to hh3cDot11APRadioTable
--        Add new object hh3cDot11AirExtChnlBusy        to hh3cDot11APRadioTable
--        Add new object hh3cDot11CurrAPIPv6PrefixLen   to hh3cDot11APObjectTable
--        Add new object hh3cDot11APIPv6PrefixLen       to hh3cDot11APObjectStatusTable
--        Add new object hh3cDot11APUserIPv6Addr2CM     to hh3cDot11APUserInfoStatis2CMTable
--        2014-12-12 modified by yubo
--        Add new object hh3cDot11APAssocStaNum   to hh3cDot11APSSIDObjectTable
--   V3.3 2015-6-20 modified by wangshaojie
--        Add new object hh3cDot11WTUAPInfoTable        to hh3cDot11APObjectGroup
--   V3.4 2016-3-11 modified by yubo 04460
--        Changed DESCRIPTION of hh3cDot11RadioModeSupport, hh3cDot11RadioModeSupport2,
--        hh3cDot11TxDiscardFrameBytes, hh3cDot11Tx64DiscardFrameBytes
--        Add hh3cDot11APUserInCirValueCM to hh3cDot11APUserInfoStatis2CMTable
--        Add hh3cDot11APUserOutCirValueCM to hh3cDot11APUserInfoStatis2CMTable
--        Add hh3cDot11APUserMac2CM to hh3cDot11APUserInfoStatis2CMTable
--        Add hh3cDot11BSSRxFrameErrCntCM to hh3cDot11BSSRxStatisTable
--        Add hh3cDot11BSSTxFrameErrCntCM to hh3cDot11BSSTxStatisTable
--        Add hh3cDot11APFactoryDataResetCM to hh3cDot11APObjectStatusTable
--        2016-6-15 modified by zhouwenshuai kf6157
--        Add new node  hh3cDot11WsmAPLicenseType      to hh3cDot11APModelTable
--   V3.5 2018-06-04 modified licheng lkf7405
--        Add new table hh3cDot11ApBriefInfoTable to hh3cDot11APObjectGroup
--        Add new nodes hh3cDot11APGpsLongitude, hh3cDot11APGpsLatitude,
--        hh3cDot11APGpsVelocity, hh3cDot11APGpsOrientation,
--        hh3cDot11APGpsElevation, and hh3cDot11APGpsObtainTime to Hh3cDot11APObjectStatusEntry
--        Add new table hh3cDot11MaxPowerCapaTable to hh3cDot11APObjectGroup
--        Add new nodes hh3cDot11APGateWayIPv4 and hh3cDot11APGateWayIPv6 to Hh3cDot11APObjectStatusEntry
--   V3.6 2021-06-18 modified by liyapeng
--        Add new object hh3cDot11APMtTrapRadioFailReason to hh3cDot11APMtRadioFailRecoverTrap
--   V3.7 2023-01-06 modified by fanwenyang
--        Add new object hh3cDot11RadioType to hh3cDot11APRadioTable
--        Add new object hh3cDot11RadioOper to hh3cDot11APRadioTable
--        Add new object hh3cDot11BindSSID to hh3cDot11APRadioTable
--        Add new object hh3cDot11RadioAverageSignalStrength to hh3cDot11APRadioTable
--        Add new object hh3cDot11RadioMaxSignalStrength to hh3cDot11APRadioTable
--        Add new object hh3cDot11RadioMinSignalStrength to hh3cDot11APRadioTable
--   V3.8 2023-11-29 modified by mengjun
--        Add new object hh3cDot11CurrRadioMode to hh3cDot11APRadioTable
--        Modify hh3cDot11APID object from hh3cDot11APObjectStatusTable
-- =============================================================================
HH3C-DOT11-APMT-MIB DEFINITIONS ::= BEGIN

IMPORTS
        MODULE-IDENTITY,
        OBJECT-TYPE,
        NOTIFICATION-TYPE,
        Integer32,
        Counter32,
        IpAddress,
        Unsigned32,
        TimeTicks,
        Counter64,
        Gauge32
    FROM SNMPv2-SMI
        MacAddress,
        TruthValue,
        DateAndTime,
        TimeStamp
    FROM SNMPv2-TC
        hh3cDot11,
        Hh3cDot11ObjectIDType,
        Hh3cDot11MACModeType,
        Hh3cDot11RadioScopeType,
        Hh3cDot11NotifyReasonType,
        Hh3cDot11ChannelScopeType,
        Hh3cDot11ServicePolicyIDType,
        Hh3cDot11RFModeType,
        Hh3cDot11TxPwrLevelScopeType,
        Hh3cDot11RadioElementIndex,
        hh3cDot11APElementIndex,
        Hh3cDot11SSIDStringType
    FROM HH3C-DOT11-REF-MIB;

hh3cDot11APMT MODULE-IDENTITY
    LAST-UPDATED "202311291800Z"        -- Nov 29, 2023 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB provides AP information which includes AP current object
        information, AP statistic data.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable STA invocation
        of the distribution system services.
        (Wireless clients attempt to connect to
        access points.)

        Basic Rate
        A data rate that is mandatory for client
        devices to support in order for them to achieve
        successful association."
    REVISION "202311291800Z"        -- Nov 29, 2023 at 18:00 GMT
    DESCRIPTION
        "Modified to add new nodes."
    REVISION "202301061800Z"        -- Jan 6, 2023 at 18:00 GMT
    DESCRIPTION
        "Modified to add new nodes."
    REVISION "202106181800Z"        -- Jun 18, 2021 at 18:00 GMT
    DESCRIPTION
        " Modify the OBJECTS of the trap node."
    REVISION "201806041800Z"        -- Jun 04, 2018 at 18:00 GMT
    DESCRIPTION
        "Modified to add new tables and new nodes."
    REVISION "201603111800Z"        -- Mar 11, 2016 at 18:00 GMT
    DESCRIPTION
        "Modified to add new tables and new nodes."
    REVISION "201506201800Z"        -- June 20, 2015 at 18:00 GMT
    DESCRIPTION
        "Modified to add new tables and new nodes."

    REVISION "201205071800Z"        -- May 07, 2012 at 18:00 GMT
    DESCRIPTION
        "Modified to add new tables."

    REVISION "201010111800Z"        -- Oct 11, 2010 at 18:00 GMT
    DESCRIPTION
        "Modified to add new nodes."
    REVISION "201009151200Z"        -- Sep 15, 2010 at 12:00 GMT
    DESCRIPTION
        "Modified to add new table."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new tables and new nodes."
    REVISION "200811071000Z"        -- Nov 07, 2008 at 10:00 GMT
    DESCRIPTION
        "Modified to add new tables and new nodes."
    REVISION "200807091800Z"        -- July 09, 2008 at 18:00 GMT
    DESCRIPTION
        "Modified to add new nodes."
    REVISION "200802251800Z"        -- Feb 25, 2008 at 18:00 GMT
    DESCRIPTION
        "Modified to add new nodes."
    REVISION "200712211800Z"        -- Dec 21, 2007 at 18:00 GMT
    DESCRIPTION
        "Modified to add new tables and new nodes."
    REVISION "200706191800Z"        -- June 19, 2007 at 18:00 GMT
    DESCRIPTION
        "Modified for new requirements and fix some issue."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { hh3cDot11 2 }

-- *****************************************************************************
-- *  Major sections
-- *****************************************************************************
--  AP Object Group
--  DEFINED AS "The group to provide the basic information for APs.
--  In order to support fit and fat AP, it uses tables to keep
--  information.  For fat AP, if it is needful, it could add more
--  tables to keep information."
hh3cDot11APObjectGroup OBJECT IDENTIFIER   ::= { hh3cDot11APMT 1 }

--  AP Object Group has the following children:
--  hh3cDot11APObjectStatusTable           ::= { hh3cDot11APObjectGroup 1 }
--  hh3cDot11APObjectTable                 ::= { hh3cDot11APObjectGroup 2 }
--  hh3cDot11APRadioTable                  ::= { hh3cDot11APObjectGroup 3 }
--  hh3cDot11APBSSTable                    ::= { hh3cDot11APObjectGroup 4 }
--  hh3cDot11APModelTable                  ::= { hh3cDot11APObjectGroup 5 }
--  hh3cDot11APIfTable                     ::= { hh3cDot11APObjectGroup 6 }
--  hh3cDot11APSSIDObjectTable             ::= { hh3cDot11APObjectGroup 7 }
--  hh3cDot11APSysInfoTable                ::= { hh3cDot11APObjectGroup 8 }
--  hh3cDot11APIdleListTable               ::= { hh3cDot11APObjectGroup 9 }
--  hh3cDot11APSysInfoByAPIDTable          ::= { hh3cDot11APObjectGroup 10 }
--  hh3cDot11WTUAPInfoTable                ::= { hh3cDot11APObjectGroup 11 }
--  hh3cDot11ApBriefInfoTable              ::= { hh3cDot11APObjectGroup 12 }
--  hh3cDot11MaxPowerCapaTable             ::= { hh3cDot11APObjectGroup 13 }

--  AP Statistic Group
--  DEFINED AS "The group to provide the statistic information of Rx
--  and Tx for AP."
hh3cDot11APStatisGroup OBJECT IDENTIFIER   ::= { hh3cDot11APMT 2 }

--  AP Statistic Group has the following children:
--  hh3cDot11APRxStatisTable               ::= { hh3cDot11APStatisGroup 1 }
--  hh3cDot11APTxStatisTable               ::= { hh3cDot11APStatisGroup 2 }
--  hh3cDot11APAssocStatisTable            ::= { hh3cDot11APStatisGroup 3 }
--  hh3cDot11BSSRxStatisTable              ::= { hh3cDot11APStatisGroup 4 }
--  hh3cDot11BSSTxStatisTable              ::= { hh3cDot11APStatisGroup 5 }
--  hh3cDot11BSSAssocStatisTable           ::= { hh3cDot11APStatisGroup 6 }
--  hh3cDot11APLinkStatisTable             ::= { hh3cDot11APStatisGroup 7 }
--  hh3cDot11RadioAssocStatisTable         ::= { hh3cDot11APStatisGroup 8 }
--  hh3cDot11RadioMngFrameStatisTable      ::= { hh3cDot11APStatisGroup 9 }
--  hh3cDot11APAuthFailStatisTable         ::= { hh3cDot11APStatisGroup 10 }
--  hh3cDot11APAssocFailStatisTable        ::= { hh3cDot11APStatisGroup 11 }
--  hh3cDot11APReassocStatisTable          ::= { hh3cDot11APStatisGroup 12 }
--  hh3cDot11APUserAuthStatisTable         ::= { hh3cDot11APStatisGroup 13 }
--  hh3cDot11APDeauthStatisTable           ::= { hh3cDot11APStatisGroup 14 }
--  hh3cDot11APDeassocStatisTable          ::= { hh3cDot11APStatisGroup 15 }
--  hh3cDot11APAssocFailStatis2Table       ::= { hh3cDot11APStatisGroup 16 }
--  hh3cDot11APIfStatisTable               ::= { hh3cDot11APStatisGroup 17 }
--  hh3cDot11RadioMngFrmStatisTable        ::= { hh3cDot11APStatisGroup 18 }
--  hh3cDot11APPacketSizeStatisTable       ::= { hh3cDot11APStatisGroup 19 }
--  hh3cDot11APPacketRateStatisTable       ::= { hh3cDot11APStatisGroup 20 }
--  hh3cDot11APPacketMCSRateStatisTable    ::= { hh3cDot11APStatisGroup 21 }
--  hh3cDot11APAssocFailStatis3Table       ::= { hh3cDot11APStatisGroup 22 }
--  hh3cDot11APIfStatisByAPIDTable         ::= { hh3cDot11APStatisGroup 23 }
--  hh3cDot11APUserSecAuthStatisTable      ::= { hh3cDot11APStatisGroup 24 }
--  hh3cDot11APUserInfoStatisTable         ::= { hh3cDot11APStatisGroup 25 }
--  hh3cDot11APReassocStatis2Table         ::= { hh3cDot11APStatisGroup 26 }
--  hh3cDot11TrafficTable                  ::= { hh3cDot11APStatisGroup 27 }
--  hh3cDot11APEchoStatisTable             ::= { hh3cDot11APStatisGroup 28 }
--  hh3cDot11APUserSecAuthTypeStatisTable  ::= { hh3cDot11APStatisGroup 29 }
--  hh3cDot11RadioRxStatis64Table          ::= { hh3cDot11APStatisGroup 30 }
--  hh3cDot11RadioTxStatis64Table          ::= { hh3cDot11APStatisGroup 31 }
--  hh3cDot11BSSRxStatis64Table            ::= { hh3cDot11APStatisGroup 32 }
--  hh3cDot11BSSTxStatis64Table            ::= { hh3cDot11APStatisGroup 33 }
--  hh3cDot11APPacketMCSRateStatis2Table   ::= { hh3cDot11APStatisGroup 34 }
--  hh3cDot11APUserSecAuthStatisCMTable    ::= { hh3cDot11APStatisGroup 35 }
--  hh3cDot11APUserInfoStatis2CMTable      ::= { hh3cDot11APStatisGroup 36 }

--  AP Event Notification
--  DEFINED AS " The group to provide AP management notification."
hh3cDot11APMtNotifyGroup OBJECT IDENTIFIER ::= { hh3cDot11APMT 3 }

-- *****************************************************************************
-- *  hh3cDot11APObjectStatusTable Definition
-- *****************************************************************************
hh3cDot11APObjectStatusTable OBJECT-TYPE
    SYNTAX      SEQUENCE OF Hh3cDot11APObjectStatusEntry
    MAX-ACCESS  not-accessible
    STATUS      current
    DESCRIPTION
        "The table will provide the general information about APs in
        different status."
    ::= { hh3cDot11APObjectGroup 1 }

hh3cDot11APObjectStatusEntry OBJECT-TYPE
    SYNTAX      Hh3cDot11APObjectStatusEntry
    MAX-ACCESS  not-accessible
    STATUS      current
    DESCRIPTION
        "Each entry contains the general information of an AP."
    INDEX
        {
            hh3cDot11APID
        }
    ::= { hh3cDot11APObjectStatusTable 1 }

Hh3cDot11APObjectStatusEntry ::= SEQUENCE
    {
        hh3cDot11APID                  Hh3cDot11ObjectIDType,
        hh3cDot11APIPAddress           IpAddress,
        hh3cDot11APMacAddress          MacAddress,
        hh3cDot11APOperationStatus     INTEGER,
        hh3cDot11APTemplateNameOfAP    OCTET STRING,
        hh3cDot11APReset               TruthValue,
        hh3cDot11APCpuUsage            Integer32,
        hh3cDot11APConnectionType      INTEGER,
        hh3cDot11APLastImgDownloadTime DateAndTime,
        hh3cDot11APIPv6Address         OCTET STRING,
        hh3cDot11APLastRegisterTime    DateAndTime,
        hh3cDot11APResetCM             INTEGER,
        hh3cDot11APIPv6PrefixLen       Integer32,
        hh3cDot11APFactoryDataResetCM  INTEGER,
        hh3cDot11APGpsLongitude        OCTET STRING,
        hh3cDot11APGpsLatitude         OCTET STRING,
        hh3cDot11APGpsVelocity         OCTET STRING,
        hh3cDot11APGpsOrientation      OCTET STRING,
        hh3cDot11APGpsElevation        OCTET STRING,
        hh3cDot11APGpsObtainTime       DateAndTime,
        hh3cDot11APGateWayIPv4         IpAddress,
        hh3cDot11APGateWayIPv6         OCTET STRING
    }

hh3cDot11APID OBJECT-TYPE
    SYNTAX      Hh3cDot11ObjectIDType
    MAX-ACCESS  read-only
    STATUS      current
    DESCRIPTION
        "To uniquely identify each AP, and relation-ship between hh3cDot11APID
        and AP device will be static."
    ::= { hh3cDot11APObjectStatusEntry 1 }

hh3cDot11APIPAddress OBJECT-TYPE
    SYNTAX      IpAddress
    MAX-ACCESS  read-only
    STATUS      current
    DESCRIPTION
        "Represents the IP address of an AP."
    ::= { hh3cDot11APObjectStatusEntry 2 }

hh3cDot11APMacAddress OBJECT-TYPE
    SYNTAX      MacAddress
    MAX-ACCESS  read-only
    STATUS      current
    DESCRIPTION
        "Represents the MAC address of an AP."
    ::= { hh3cDot11APObjectStatusEntry 3 }

hh3cDot11APOperationStatus OBJECT-TYPE
    SYNTAX      INTEGER
        {
            join(1),
            joinConfirm(2),
            download(3),
            config(4),
            run(5)
        }
    MAX-ACCESS  read-only
    STATUS      current
    DESCRIPTION
        "Represents operational status of AP.
        The following values are supported:
        join         - AP is joining to AC.
        joinConfirm  - AC confirm whether permit AP to join.
        download     - AP is downloading software from AC.
        config       - AP and AC exchange configuration before AP
        - provide WLAN service.
        run          - The WLAN service is ready."
    ::= { hh3cDot11APObjectStatusEntry 4 }

hh3cDot11APTemplateNameOfAP OBJECT-TYPE
    SYNTAX      OCTET STRING
    MAX-ACCESS  read-only
    STATUS      current
    DESCRIPTION
        "Represents the name of current AP template configured for AP."
    ::= { hh3cDot11APObjectStatusEntry 5 }

hh3cDot11APReset OBJECT-TYPE
    SYNTAX      TruthValue
    MAX-ACCESS  read-write
    STATUS      current
    DESCRIPTION
        "When read the value from the node
        2: Represents the AP cannot be reset.
        1: Represents the AP can be reset.
        When write the value to the node
        1: Represents resetting the AP.  Other values are not supported"
    ::= { hh3cDot11APObjectStatusEntry 6 }

hh3cDot11APCpuUsage OBJECT-TYPE
    SYNTAX      Integer32(0..100)
    UNITS       "onepercent"
    MAX-ACCESS  read-only
    STATUS      current
    DESCRIPTION
        "Represents the current CPU usage for AP."
    ::= { hh3cDot11APObjectStatusEntry 7 }

hh3cDot11APConnectionType OBJECT-TYPE
    SYNTAX      INTEGER
        {
            master(1),
            slave(2),
            notAvailable(3)
        }
    MAX-ACCESS  read-only
    STATUS      current
    DESCRIPTION
        "Represents the current connection type."
    ::= { hh3cDot11APObjectStatusEntry 8 }

hh3cDot11APLastImgDownloadTime OBJECT-TYPE
    SYNTAX      DateAndTime
    MAX-ACCESS  read-only
    STATUS      current
    DESCRIPTION
        "Represents the time at which the device last downloaded image."
    ::= { hh3cDot11APObjectStatusEntry 9 }

hh3cDot11APIPv6Address OBJECT-TYPE
    SYNTAX      OCTET STRING
    MAX-ACCESS  read-only
    STATUS      current
    DESCRIPTION
        "Represents the IPv6 address of AP."
    ::= { hh3cDot11APObjectStatusEntry 10 }

hh3cDot11APLastRegisterTime OBJECT-TYPE
    SYNTAX      DateAndTime
    MAX-ACCESS  read-only
    STATUS      current
    DESCRIPTION
        "Represents the time at which the device last registered with AC."
    ::= { hh3cDot11APObjectStatusEntry 11 }

hh3cDot11APResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { hh3cDot11APObjectStatusEntry 12 }

hh3cDot11APIPv6PrefixLen OBJECT-TYPE
    SYNTAX      Integer32
    MAX-ACCESS  read-only
    STATUS      current
    DESCRIPTION
        "Represents the prefix length of an AP IPv6 address."
    ::= { hh3cDot11APObjectStatusEntry 13 }

hh3cDot11APFactoryDataResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { hh3cDot11APObjectStatusEntry 14 }

hh3cDot11APGpsLongitude OBJECT-TYPE
    SYNTAX      OCTET STRING
    MAX-ACCESS  read-only
    STATUS      current
    DESCRIPTION
        "Get the current longitudes of online APs by GPS."
    ::= { hh3cDot11APObjectStatusEntry 15 }

hh3cDot11APGpsLatitude OBJECT-TYPE
    SYNTAX      OCTET STRING
    MAX-ACCESS  read-only
    STATUS      current
    DESCRIPTION
        "Get the current latitudes of online APs by GPS."
    ::= { hh3cDot11APObjectStatusEntry 16 }

hh3cDot11APGpsVelocity OBJECT-TYPE
    SYNTAX      OCTET STRING
    MAX-ACCESS  read-only
    STATUS      current
    DESCRIPTION
        "Get the current velocities of online APs by GPS."
    ::= { hh3cDot11APObjectStatusEntry 17 }

hh3cDot11APGpsOrientation OBJECT-TYPE
    SYNTAX      OCTET STRING
    MAX-ACCESS  read-only
    STATUS      current
    DESCRIPTION
        "Get the current orientations of online APs by GPS."
    ::= { hh3cDot11APObjectStatusEntry 18 }

hh3cDot11APGpsElevation OBJECT-TYPE
    SYNTAX      OCTET STRING
    MAX-ACCESS  read-only
    STATUS      current
    DESCRIPTION
        "Get the current elevations of online APs by GPS."
    ::= { hh3cDot11APObjectStatusEntry 19 }

hh3cDot11APGpsObtainTime OBJECT-TYPE
    SYNTAX      DateAndTime
    MAX-ACCESS  read-only
    STATUS      current
    DESCRIPTION
        "Get the current online AP time by GPS."
    ::= { hh3cDot11APObjectStatusEntry 20 }

hh3cDot11APGateWayIPv4 OBJECT-TYPE
    SYNTAX      IpAddress
    MAX-ACCESS  read-only
    STATUS      current
    DESCRIPTION
        "Represents the gateway IPv4 address of APs."
    ::= { hh3cDot11APObjectStatusEntry 21 }

hh3cDot11APGateWayIPv6 OBJECT-TYPE
    SYNTAX      OCTET STRING
    MAX-ACCESS  read-only
    STATUS      current
    DESCRIPTION
        "Represents the gateway IPv6 address of APs."
    ::= { hh3cDot11APObjectStatusEntry 22 }

-- *****************************************************************************
-- *  End of Hh3cDot11APObjectStatusTable Definition
-- *****************************************************************************

-- *****************************************************************************
-- *  hh3cDot11APObjectTable Definition
-- *****************************************************************************
hh3cDot11APObjectTable OBJECT-TYPE
    SYNTAX      SEQUENCE OF Hh3cDot11APObjectEntry
    MAX-ACCESS  not-accessible
    STATUS      current
    DESCRIPTION
        "The table will provide information for APs in the running status."
    ::= { hh3cDot11APObjectGroup 2 }

hh3cDot11APObjectEntry OBJECT-TYPE
    SYNTAX      Hh3cDot11APObjectEntry
    MAX-ACCESS  not-accessible
    STATUS      current
    DESCRIPTION
        "Each entry contains information of an AP in run status."
    INDEX
        {
            hh3cDot11APObjID
        }
    ::= { hh3cDot11APObjectTable 1 }

Hh3cDot11APObjectEntry ::= SEQUENCE
    {
        hh3cDot11APObjID                    Hh3cDot11ObjectIDType,
        hh3cDot11CurrAPIPAddress            IpAddress,
        hh3cDot11CurrAPMacAddress           MacAddress,
        hh3cDot11CurrACPortIndex            Integer32,
        hh3cDot11CurrAPMACMode              Hh3cDot11MACModeType,
        hh3cDot11CurrAPTemplateName         OCTET STRING,
        hh3cDot11CurrAPStationAssocCount    Integer32,
        hh3cDot11CurrAPName                 OCTET STRING,
        hh3cDot11CurrAPModelName            OCTET STRING,
        hh3cDot11CurrAPImageName            OCTET STRING,
        hh3cDot11CurrAPSoftwareVersion      OCTET STRING,
        hh3cDot11CurrAPIPNetMask            IpAddress,
        hh3cDot11CurrRadioModeSupport       Integer32,
        hh3cDot11CurrIfNumber               Integer32,
        hh3cDot11CurrAPElementID            Integer32,
        hh3cDot11CurrAPMode                 INTEGER,
        hh3cDot11CurrAPIPv6Address          OCTET STRING,
        hh3cDot11CurrAPSSIDNumber           Integer32,
        hh3cDot11CurrAPManufacturer         OCTET STRING,
        hh3cDot11CurrAPMemorySize           Integer32,
        hh3cDot11CurrAPMemSizeInBytes       Integer32,
        hh3cDot11CurrAPFlashSize            Integer32,
        hh3cDot11CurrAPFlashSizeInBytes     Integer32,
        hh3cDot11CurrAPReleasedVersion      OCTET STRING,
        hh3cDot11CurrRadioModeSupport2      Integer32,
        hh3cDot11CurrAPCPUTypeCM            OCTET STRING,
        hh3cDot11CurrAPMemoryTypeCM         OCTET STRING,
        hh3cDot11CurrAPBSSIDNumberCM        Integer32,
        hh3cDot11CurrAPIPv6PrefixLen        Integer32
    }

hh3cDot11APObjID OBJECT-TYPE
    SYNTAX      Hh3cDot11ObjectIDType
    MAX-ACCESS  read-only
    STATUS      current
    DESCRIPTION
        "To uniquely identify each AP, and relation-ship between hh3cDot11APObjID
        and AP device will be static."
    ::= { hh3cDot11APObjectEntry 1 }

hh3cDot11CurrAPIPAddress OBJECT-TYPE
    SYNTAX      IpAddress
    MAX-ACCESS  read-only
    STATUS      current
    DESCRIPTION
        "Represents the IP address of an AP."
    ::= { hh3cDot11APObjectEntry 2 }

hh3cDot11CurrAPMacAddress OBJECT-TYPE
    SYNTAX      MacAddress
    MAX-ACCESS  read-only
    STATUS      current
    DESCRIPTION
        "Represents the MAC address of an AP."
    ::= { hh3cDot11APObjectEntry 3 }

hh3cDot11CurrACPortIndex OBJECT-TYPE
    SYNTAX      Integer32
    MAX-ACCESS  read-only
    STATUS      current
    DESCRIPTION
        "Represents the port on the AC, by which the traffic of this AP comes
        through.  NMS could refer it to access information kept in the
        MIB-2."
    ::= { hh3cDot11APObjectEntry 4 }

hh3cDot11CurrAPMACMode OBJECT-TYPE
    SYNTAX      Hh3cDot11MACModeType
    MAX-ACCESS  read-only
    STATUS      current
    DESCRIPTION
        "Represents what MAC mode defined in the CAPWAP is applied.
        For fat AP, the value will be fatap."
    ::= { hh3cDot11APObjectEntry 5 }

hh3cDot11CurrAPTemplateName OBJECT-TYPE
    SYNTAX      OCTET STRING
    MAX-ACCESS  read-only
    STATUS      current
    DESCRIPTION
        "Represents the name of current AP template."
    ::= { hh3cDot11APObjectEntry 6 }

hh3cDot11CurrAPStationAssocCount OBJECT-TYPE
    SYNTAX      Integer32
    MAX-ACCESS  read-only
    STATUS      current
    DESCRIPTION
        "Represents the total number of stations which are associating
        to AP."
    ::= { hh3cDot11APObjectEntry 7 }

hh3cDot11CurrAPName OBJECT-TYPE
    SYNTAX      OCTET STRING
    MAX-ACCESS  read-only
    STATUS      current
    DESCRIPTION
        "Represents the name of AP."
    ::= { hh3cDot11APObjectEntry 8 }

hh3cDot11CurrAPModelName OBJECT-TYPE
    SYNTAX      OCTET STRING
    MAX-ACCESS  read-only
    STATUS      current
    DESCRIPTION
        "Represents index of WTP model,with it to get AP model information."
    ::= { hh3cDot11APObjectEntry 9 }

hh3cDot11CurrAPImageName OBJECT-TYPE
    SYNTAX      OCTET STRING
    MAX-ACCESS  read-only
    STATUS      current
    DESCRIPTION
        "Represents the image file name of AP."
    ::= { hh3cDot11APObjectEntry 10 }

hh3cDot11CurrAPSoftwareVersion OBJECT-TYPE
    SYNTAX      OCTET STRING
    MAX-ACCESS  read-only
    STATUS      current
    DESCRIPTION
        "Represents the software version of AP."
    ::= { hh3cDot11APObjectEntry 11 }

hh3cDot11CurrAPIPNetMask OBJECT-TYPE
    SYNTAX      IpAddress
    MAX-ACCESS  read-only
    STATUS      current
    DESCRIPTION
        "Represents the IP netmask of AP."
    ::= { hh3cDot11APObjectEntry 12 }

hh3cDot11CurrRadioModeSupport OBJECT-TYPE
    SYNTAX      Integer32
    MAX-ACCESS  read-only
    STATUS      current
    DESCRIPTION
        "Represents which radio type supported by the AP.
        The WLAN system support the following possible radio type.
        dot11a(1),
        dot11b(2),
        dot11g(4),
        dot11n(8),
        dot11an(16),
        dot11gn(32),
        dot11ac(64),
        dot11gac(128)
        For a AP,it could support multiple radio types at
        the same time.So the value of object could combine multiple value
        of radio type above.
        For example:
        For one AP which support both b and g mode radio, when getting the value
        from the node, the value is 6(2 + 4)."
    ::= { hh3cDot11APObjectEntry 13 }

hh3cDot11CurrIfNumber OBJECT-TYPE
    SYNTAX      Integer32
    MAX-ACCESS  read-only
    STATUS      current
    DESCRIPTION
        "Represents number of interface of the AP."
    ::= { hh3cDot11APObjectEntry 14 }

hh3cDot11CurrAPElementID OBJECT-TYPE
    SYNTAX      Integer32
    MAX-ACCESS  read-only
    STATUS      current
    DESCRIPTION
    "Represents the AP element ID."
    ::= { hh3cDot11APObjectEntry 15 }

hh3cDot11CurrAPMode OBJECT-TYPE
    SYNTAX      INTEGER
        {
            bridge(1),
            route(2)
        }
    MAX-ACCESS  read-only
    STATUS      current
    DESCRIPTION
        "Represents the forward mode of the AP."
    ::= { hh3cDot11APObjectEntry 16 }

hh3cDot11CurrAPIPv6Address OBJECT-TYPE
    SYNTAX      OCTET STRING
    MAX-ACCESS  read-only
    STATUS      current
    DESCRIPTION
        "Represents the IPv6 address of AP."
    ::= { hh3cDot11APObjectEntry 17 }

hh3cDot11CurrAPSSIDNumber OBJECT-TYPE
    SYNTAX      Integer32
    MAX-ACCESS  read-only
    STATUS      current
    DESCRIPTION
        "Represents the number of SSID configured on AP."
    ::= { hh3cDot11APObjectEntry 18 }

hh3cDot11CurrAPManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { hh3cDot11APObjectEntry 19 }

hh3cDot11CurrAPMemorySize OBJECT-TYPE
    SYNTAX      Integer32
    UNITS       "kbytes"
    MAX-ACCESS  read-only
    STATUS      current
    DESCRIPTION
        "Represents the size of AP memory."
    ::= { hh3cDot11APObjectEntry 20 }

hh3cDot11CurrAPMemSizeInBytes OBJECT-TYPE
    SYNTAX      Integer32
    UNITS       "bytes"
    MAX-ACCESS  read-only
    STATUS      current
    DESCRIPTION
        "Represents the size of AP memory."
    ::= { hh3cDot11APObjectEntry 21 }

hh3cDot11CurrAPFlashSize OBJECT-TYPE
    SYNTAX      Integer32
    UNITS       "Kbytes"
    MAX-ACCESS  read-only
    STATUS      current
    DESCRIPTION
        "Represents the size of AP flash."
    ::= { hh3cDot11APObjectEntry 22 }

hh3cDot11CurrAPFlashSizeInBytes OBJECT-TYPE
    SYNTAX      Integer32
    UNITS       "bytes"
    MAX-ACCESS  read-only
    STATUS      current
    DESCRIPTION
        "This object represents the size of AP flash."
    ::= { hh3cDot11APObjectEntry 23 }

hh3cDot11CurrAPReleasedVersion OBJECT-TYPE
    SYNTAX      OCTET STRING
    MAX-ACCESS  read-only
    STATUS      current
    DESCRIPTION
        "Represents the released version of AP."
    ::= { hh3cDot11APObjectEntry 24 }

hh3cDot11CurrRadioModeSupport2 OBJECT-TYPE
    SYNTAX      Integer32
    MAX-ACCESS  read-only
    STATUS      current
    DESCRIPTION
        "Represents which radio type supported by the AP.
        The WLAN system support the following possible radio type.
        dot11a(1),
        dot11b(2),
        dot11g(4),
        dot11an(8),
        dot11gn(16),
        dot11gac(32),
        dot11ac(64)
        For a AP,it could support multiple radio types at
        the same time.So the value of object could combine multiple value
        of radio type above.
        For example:
        For one AP which support both b and g mode radio, when getting the value
        from the node, the value is 6(2 + 4)."
    ::= { hh3cDot11APObjectEntry 25 }

hh3cDot11CurrAPCPUTypeCM OBJECT-TYPE
    SYNTAX      OCTET STRING
    MAX-ACCESS  read-only
    STATUS      current
    DESCRIPTION
        "Represents the CPU type of AP."
    ::= { hh3cDot11APObjectEntry 26 }

hh3cDot11CurrAPMemoryTypeCM OBJECT-TYPE
    SYNTAX      OCTET STRING
    MAX-ACCESS  read-only
    STATUS      current
    DESCRIPTION
        "Represents the memory card type of AP."
    ::= { hh3cDot11APObjectEntry 27 }

hh3cDot11CurrAPBSSIDNumberCM OBJECT-TYPE
    SYNTAX      Integer32
    MAX-ACCESS  read-only
    STATUS      current
    DESCRIPTION
        "Represents the number of BSSID configured on AP."
    ::= { hh3cDot11APObjectEntry 28 }

hh3cDot11CurrAPIPv6PrefixLen OBJECT-TYPE
    SYNTAX      Integer32
    MAX-ACCESS  read-only
    STATUS      current
    DESCRIPTION
        "Represents the prefix length of an AP IPv6 address."
    ::= { hh3cDot11APObjectEntry 29 }
-- *****************************************************************************
-- *  End of hh3cDot11APObjectTable Definition
-- *****************************************************************************

-- *****************************************************************************
-- *  hh3cDot11APRadioTable Definition
-- *****************************************************************************
hh3cDot11APRadioTable OBJECT-TYPE
    SYNTAX      SEQUENCE OF Hh3cDot11APRadioEntry
    MAX-ACCESS  not-accessible
    STATUS      current
    DESCRIPTION
        "The table will describe the radio information of AP.  The AP here will
        be in running status."
    ::= { hh3cDot11APObjectGroup 3 }

hh3cDot11APRadioEntry OBJECT-TYPE
    SYNTAX      Hh3cDot11APRadioEntry
    MAX-ACCESS  not-accessible
    STATUS      current
    DESCRIPTION
        "Each entry contains the information of each radio of a specific AP."
    INDEX
        {
            hh3cDot11CurAPID,
            hh3cDot11RadioID
        }
    ::= { hh3cDot11APRadioTable 1 }

Hh3cDot11APRadioEntry ::= SEQUENCE
    {
        hh3cDot11CurAPID            OCTET STRING,
        hh3cDot11RadioID            Integer32,
        hh3cDot11AdminStatus        TruthValue,
        hh3cDot11OperStatus         TruthValue,
        hh3cDot11Channel            Hh3cDot11ChannelScopeType,
        hh3cDot11TxPowerLevel       Hh3cDot11TxPwrLevelScopeType,
        hh3cDot11APRadioIfIndex     Integer32,
        hh3cDot11AntennaGain        Integer32,
        hh3cDot11MaxBandwidth       Integer32,
        hh3cDot11ResourceUseRatio   Integer32,
        hh3cDot11RadioModeSupport   Unsigned32,
        hh3cDot11TxPowerLevel2      Integer32,
        hh3cDot11PowerMgmtStatus    TruthValue,
        hh3cDot11ChannelSwitchTimes Counter32,
        hh3cDot11AntennaType        OCTET STRING,
        hh3cDot11DiversitySelectionRx     TruthValue,
        hh3cDot11MaxTxPwrLvl              OCTET STRING,
        hh3cDot11PwrAttRange              Integer32,
        hh3cDot11AvgRxSignalStrength      Integer32,
        hh3cDot11HighestRxSignalStrength  Integer32,
        hh3cDot11LowestRxSignalStrength   Integer32,
        hh3cDot11RadioIfUpdownTimes       Counter32,
        hh3cDot11RadioIfLastChange        TimeTicks,
        hh3cDot11RadioModeSupport2        Unsigned32,
        hh3cDot11OperStatusCM             INTEGER,
        hh3cDot11AirPrimChnlBusy          Integer32,
        hh3cDot11AirPrimChnlTxBusy        Integer32,
        hh3cDot11AirPrimChnlRxBusy        Integer32,
        hh3cDot11AirExtChnlBusy           Integer32,
        hh3cDot11RadioType                Integer32,
        hh3cDot11RadioOper                Integer32,
        hh3cDot11BindSSID                 OCTET STRING,
        hh3cDot11RadioAverageSignalStrength Integer32,
        hh3cDot11RadioMaxSignalStrength   Integer32,
        hh3cDot11RadioMinSignalStrength   Integer32,
        hh3cDot11CurrRadioMode            Integer32
    }

hh3cDot11CurAPID OBJECT-TYPE
    SYNTAX      OCTET STRING(SIZE(0..64))
    MAX-ACCESS  read-only
    STATUS      current
    DESCRIPTION
        "To uniquely identify a AP in running status."
    ::= { hh3cDot11APRadioEntry 1 }

hh3cDot11RadioID OBJECT-TYPE
    SYNTAX      Integer32(0..2147483647)
    MAX-ACCESS  read-only
    STATUS      current
    DESCRIPTION
        "Represents each radio."
    ::= { hh3cDot11APRadioEntry 2 }

hh3cDot11AdminStatus OBJECT-TYPE
    SYNTAX      TruthValue
    MAX-ACCESS  read-only
    STATUS      current
    DESCRIPTION
        "Represents the administrator status of radio."
    ::= { hh3cDot11APRadioEntry 3 }

hh3cDot11OperStatus OBJECT-TYPE
    SYNTAX      TruthValue
    MAX-ACCESS  read-only
    STATUS      current
    DESCRIPTION
        "Represents the operational status of radio."
    ::= { hh3cDot11APRadioEntry 4 }

hh3cDot11Channel OBJECT-TYPE
    SYNTAX      Hh3cDot11ChannelScopeType
    MAX-ACCESS  read-only
    STATUS      current
    DESCRIPTION
        "Represents the current channel allocation for radio."
    ::= { hh3cDot11APRadioEntry 5 }

hh3cDot11TxPowerLevel OBJECT-TYPE
    SYNTAX      Hh3cDot11TxPwrLevelScopeType
    UNITS       "dbm"
    MAX-ACCESS  read-only
    STATUS      current
    DESCRIPTION
        "Represents the current transmit power level for radio."
    ::= { hh3cDot11APRadioEntry 6 }

hh3cDot11APRadioIfIndex OBJECT-TYPE
    SYNTAX      Integer32
    MAX-ACCESS  read-only
    STATUS      current
    DESCRIPTION
        "Represents the interface index for the radio."
    ::= { hh3cDot11APRadioEntry 7 }

hh3cDot11AntennaGain OBJECT-TYPE
    SYNTAX      Integer32
    UNITS       "dBi"
    MAX-ACCESS  read-only
    STATUS      current
    DESCRIPTION
        "Represents the current gain for antenna."
    ::= { hh3cDot11APRadioEntry 8 }

hh3cDot11MaxBandwidth OBJECT-TYPE
    SYNTAX      Integer32
    UNITS       "Mbps"
    MAX-ACCESS  read-only
    STATUS      current
    DESCRIPTION
        "Represents the maximum bandwidth for the radio."
    ::= { hh3cDot11APRadioEntry 9 }

hh3cDot11ResourceUseRatio OBJECT-TYPE
    SYNTAX      Integer32
    UNITS       "onepercent"
    MAX-ACCESS  read-only
    STATUS      current
    DESCRIPTION
        "Represents the ratio of radio resource usage."
    ::= { hh3cDot11APRadioEntry 10 }

hh3cDot11RadioModeSupport OBJECT-TYPE
    SYNTAX      Unsigned32
    MAX-ACCESS  read-only
    STATUS      current
    DESCRIPTION
        "Represents radio type supported by the radio.
        The WLAN system supports the following possible radio type:
        dot11a(1),
        dot11b(2),
        dot11g(4),
        dot11gn(16),
        dot11an(32),
        dot11ac(64),
        dot11gac(128)
        For the radio, it could support multiple radio types at
        the same time.  So the value of this object could combine multiple
        values of radio type above.
        For example:
        For one radio which supports both dot11b and dot11g mode, when get
        value from the object, the value is 6(2 + 4)."
    ::= { hh3cDot11APRadioEntry 11 }

hh3cDot11TxPowerLevel2 OBJECT-TYPE
    SYNTAX      Integer32(1..8)
    MAX-ACCESS  read-only
    STATUS      current
    DESCRIPTION
        "The TxPowerLevel N currently being used to transmit data."
    ::= { hh3cDot11APRadioEntry 12 }

hh3cDot11PowerMgmtStatus OBJECT-TYPE
    SYNTAX      TruthValue
    MAX-ACCESS  read-only
    STATUS      current
    DESCRIPTION
        "Represents status of power management of the radio."
    ::= { hh3cDot11APRadioEntry 13 }

hh3cDot11ChannelSwitchTimes OBJECT-TYPE
    SYNTAX      Counter32
    MAX-ACCESS  read-only
    STATUS      current
    DESCRIPTION
        "Represents the channel switch times."
    ::= { hh3cDot11APRadioEntry 14 }

hh3cDot11AntennaType OBJECT-TYPE
    SYNTAX      OCTET STRING
    MAX-ACCESS  read-only
    STATUS      current
    DESCRIPTION
        "Represents type of the antenna which radio used."
    ::= { hh3cDot11APRadioEntry 15 }

hh3cDot11DiversitySelectionRx OBJECT-TYPE
    SYNTAX      TruthValue
    MAX-ACCESS  read-only
    STATUS      current
    DESCRIPTION
        "Represents the diversity selection received."
    ::= { hh3cDot11APRadioEntry 16 }

hh3cDot11MaxTxPwrLvl OBJECT-TYPE
    SYNTAX      OCTET STRING
    MAX-ACCESS  read-only
    STATUS      current
    DESCRIPTION
        "Represents the maximum transmit power."
    ::= { hh3cDot11APRadioEntry 17 }

hh3cDot11PwrAttRange OBJECT-TYPE
    SYNTAX      Integer32
    MAX-ACCESS  read-only
    STATUS      current
    DESCRIPTION
        "Represents the range of power attenuation."
    ::= { hh3cDot11APRadioEntry 18 }

hh3cDot11AvgRxSignalStrength OBJECT-TYPE
    SYNTAX      Integer32
    UNITS       "dBm"
    MAX-ACCESS  read-only
    STATUS      current
    DESCRIPTION
        "Represents the average received signal strength."
    ::= { hh3cDot11APRadioEntry 19 }

hh3cDot11HighestRxSignalStrength OBJECT-TYPE
    SYNTAX      Integer32
    UNITS       "dBm"
    MAX-ACCESS  read-only
    STATUS      current
    DESCRIPTION
        "Represents the highest received signal strength."
    ::= { hh3cDot11APRadioEntry 20 }

hh3cDot11LowestRxSignalStrength OBJECT-TYPE
    SYNTAX      Integer32
    UNITS       "dBm"
    MAX-ACCESS  read-only
    STATUS      current
    DESCRIPTION
        "Represents the lowest received signal strength."
    ::= { hh3cDot11APRadioEntry 21 }

hh3cDot11RadioIfUpdownTimes OBJECT-TYPE
    SYNTAX      Counter32
    MAX-ACCESS  read-only
    STATUS      current
    DESCRIPTION
        "Represents the up/down times on radio interface."
    ::= { hh3cDot11APRadioEntry 22 }

hh3cDot11RadioIfLastChange OBJECT-TYPE
    SYNTAX      TimeTicks
    MAX-ACCESS  read-only
    STATUS      current
    DESCRIPTION
        "Represents time at last change that occurred on radio interface."
    ::= { hh3cDot11APRadioEntry 23 }

hh3cDot11RadioModeSupport2 OBJECT-TYPE
    SYNTAX      Unsigned32
    MAX-ACCESS  read-only
    STATUS      current
    DESCRIPTION
        "Represents radio type supported by the radio.
        The WLAN system supports the following possible radio type:
        dot11a(1),
        dot11b(2),
        dot11g(4),
        dot11an(8),
        dot11gn(16),
        dot11gac(32),
        dot11ac(64)
        For the radio, it could support multiple radio types at
        the same time.  So the value of this object could combine multiple
        values of radio type above.
        For example:
        For one radio which supports both dot11b and dot11g mode, when get
        value from the object, the value is 6(2 + 4)."
    ::= { hh3cDot11APRadioEntry 24 }

hh3cDot11OperStatusCM OBJECT-TYPE
    SYNTAX      INTEGER
        {
            up(1),
            down(2),
            testing(3),
            admindown(4)
        }
    MAX-ACCESS  read-only
    STATUS      current
    DESCRIPTION
        "Represents the operational status of radio."
    ::= { hh3cDot11APRadioEntry 25 }

hh3cDot11AirPrimChnlBusy OBJECT-TYPE
    SYNTAX      Integer32(0..100 | 255)
    MAX-ACCESS  read-only
    STATUS      current
    DESCRIPTION
    "Represents air interface utilization on the primary channel.
    The value 255 represents an invalid value."
    ::= { hh3cDot11APRadioEntry 26 }

hh3cDot11AirPrimChnlTxBusy OBJECT-TYPE
    SYNTAX      Integer32(0..100 | 255)
    MAX-ACCESS  read-only
    STATUS      current
    DESCRIPTION
    "Represents air interface utilization for signal sending on the
    primary channel.
    The value 255 represents an invalid value."
    ::= { hh3cDot11APRadioEntry 27 }

hh3cDot11AirPrimChnlRxBusy OBJECT-TYPE
    SYNTAX      Integer32(0..100 | 255)
    MAX-ACCESS  read-only
    STATUS      current
    DESCRIPTION
    "Represents air interface utilization for signal receiving on the
    primary channel.
    The value 255 represents an invalid value."
    ::= { hh3cDot11APRadioEntry 28 }

hh3cDot11AirExtChnlBusy OBJECT-TYPE
    SYNTAX      Integer32(0..100 | 255)
    MAX-ACCESS  read-only
    STATUS      current
    DESCRIPTION
    "Represents air interface utilization on the secondary channel.
    The value 255 represents an invalid value."
    ::= { hh3cDot11APRadioEntry 29 }

hh3cDot11RadioType OBJECT-TYPE
    SYNTAX      Integer32
    MAX-ACCESS  read-only
    STATUS      current
    DESCRIPTION
    "Represents the radio type of the radio."
    ::= { hh3cDot11APRadioEntry 30 }

hh3cDot11RadioOper OBJECT-TYPE
    SYNTAX      Integer32
    MAX-ACCESS  read-write
    STATUS      current
    DESCRIPTION
    "Set the status of the radio."
    ::= { hh3cDot11APRadioEntry 31 }

hh3cDot11BindSSID OBJECT-TYPE
    SYNTAX      OCTET STRING
    MAX-ACCESS  read-only
    STATUS      current
    DESCRIPTION
    "Represents all SSIDs of the radio."
    ::= { hh3cDot11APRadioEntry 32 }

hh3cDot11RadioAverageSignalStrength OBJECT-TYPE
    SYNTAX      Integer32
    UNITS       "dBm"
    MAX-ACCESS  read-only
    STATUS      current
    DESCRIPTION
        "Represents the average received signal strength."
    ::= { hh3cDot11APRadioEntry 33 }

hh3cDot11RadioMaxSignalStrength OBJECT-TYPE
    SYNTAX      Integer32
    UNITS       "dBm"
    MAX-ACCESS  read-only
    STATUS      current
    DESCRIPTION
        "Represents the highest received signal strength."
    ::= { hh3cDot11APRadioEntry 34 }

hh3cDot11RadioMinSignalStrength OBJECT-TYPE
    SYNTAX      Integer32
    UNITS       "dBm"
    MAX-ACCESS  read-only
    STATUS      current
    DESCRIPTION
        "Represents the lowest received signal strength."
    ::= { hh3cDot11APRadioEntry 35 }

hh3cDot11CurrRadioMode OBJECT-TYPE
    SYNTAX      Integer32
    MAX-ACCESS  read-only
    STATUS      current
    DESCRIPTION
        "Represents the current radio type.
        The possible radio type:
        1: dot11a(1),
        2: dot11b(2),
        3: dot11g(4),
        4: dot11n(8),
        5: dot11gn(16),
        6: dot11an(32),
        7: dot11ac(64),
        8: dot11gac(128),
        9: dot11ax(256),
        10: dot11gax(512),
        11: dot11eax(1024),
        12: dot11be(2048),
        13: dot11abe(4096),
        14: dot11gbe(8192)"
    ::= { hh3cDot11APRadioEntry 36 }

-- *****************************************************************************
-- *  End of hh3cDot11APRadioTable Definition
-- *****************************************************************************

-- *****************************************************************************
-- *  hh3cDot11APBSSTable Definition
-- *****************************************************************************
hh3cDot11APBSSTable OBJECT-TYPE
    SYNTAX      SEQUENCE OF Hh3cDot11APBSSEntry
    MAX-ACCESS  not-accessible
    STATUS      current
    DESCRIPTION
        "After AP connect to AC and get AP template configuration,
        it will create BSS data structure for each radio.
        The table will describe BSS information of AP and service
        policy as per BSS."
    ::= { hh3cDot11APObjectGroup 4 }

hh3cDot11APBSSEntry OBJECT-TYPE
    SYNTAX      Hh3cDot11APBSSEntry
    MAX-ACCESS  not-accessible
    STATUS      current
    DESCRIPTION
        "Each entry contains information of each BSS for specific radio."
    INDEX
        {
            hh3cDot11CurAPID,
            hh3cDot11RadioID,
            hh3cDot11WlanID
        }
    ::= { hh3cDot11APBSSTable 1 }

Hh3cDot11APBSSEntry ::= SEQUENCE
    {
        hh3cDot11WlanID             Integer32,
        hh3cDot11BSSID              MacAddress,
        hh3cDot11CurrSvcPolicyID    Hh3cDot11ServicePolicyIDType,
        hh3cDot11SSID               OCTET STRING,
        hh3cDot11CurrSSIDResourceUseRatio             Integer32,
        hh3cDot11APEssVlanId                          Integer32
    }

hh3cDot11WlanID OBJECT-TYPE
    SYNTAX      Integer32(0..2147483647)
    MAX-ACCESS  not-accessible
    STATUS      current
    DESCRIPTION
        "Represents ID of a specific ESS."
    ::= { hh3cDot11APBSSEntry 1 }

hh3cDot11BSSID OBJECT-TYPE
    SYNTAX      MacAddress
    MAX-ACCESS  read-only
    STATUS      current
    DESCRIPTION
        "As MAC Address format, it is to identify BSS."
    ::= { hh3cDot11APBSSEntry 2 }

hh3cDot11CurrSvcPolicyID OBJECT-TYPE
    SYNTAX      Hh3cDot11ServicePolicyIDType
    MAX-ACCESS  read-only
    STATUS      current
    DESCRIPTION
        "Represents the ID of each service policy used by the AP."
    ::= { hh3cDot11APBSSEntry 3 }

hh3cDot11SSID OBJECT-TYPE
    SYNTAX      OCTET STRING
    MAX-ACCESS  read-only
    STATUS      current
    DESCRIPTION
        "This object represents the SSID corresponding to this BSS."
    ::= { hh3cDot11APBSSEntry 4 }

hh3cDot11CurrSSIDResourceUseRatio OBJECT-TYPE
    SYNTAX      Integer32
    MAX-ACCESS  read-only
    STATUS      current
    DESCRIPTION
        "Represents the ratio of resource usage of curr SSID"
    ::= { hh3cDot11APBSSEntry 5 }

hh3cDot11APEssVlanId OBJECT-TYPE
    SYNTAX      Integer32
    MAX-ACCESS  read-only
    STATUS      current
    DESCRIPTION
        "This object represents the VlanID of the interface ESS
        corresponding to this BSS."
    ::= { hh3cDot11APBSSEntry 6 }
-- *****************************************************************************
-- *  End of hh3cDot11APBSSTable Definition
-- *****************************************************************************

-- *****************************************************************************
-- *  hh3cDot11APModelTable Definition
-- *****************************************************************************
hh3cDot11APModelTable OBJECT-TYPE
    SYNTAX      SEQUENCE OF Hh3cDot11APModelEntry
    MAX-ACCESS  not-accessible
    STATUS      current
    DESCRIPTION
        "The table defines the capability information for a specific
        kind of AP."
    ::= { hh3cDot11APObjectGroup 5 }

hh3cDot11APModelEntry OBJECT-TYPE
    SYNTAX      Hh3cDot11APModelEntry
    MAX-ACCESS  not-accessible
    STATUS      current
    DESCRIPTION
        "Each entry contains capability information for a specific kind
        of AP."
    INDEX
        {
            IMPLIED hh3cDot11APModelAlias
        }
    ::= { hh3cDot11APModelTable 1 }

Hh3cDot11APModelEntry ::= SEQUENCE
    {
        hh3cDot11APModelAlias         OCTET STRING,
        hh3cDot11APModelName          OCTET STRING,
        hh3cDot11RadioNumSupport      Hh3cDot11RadioScopeType,
        hh3cDot11StationNumSupport    Integer32,
        hh3cDot11MACModeSupport       Hh3cDot11MACModeType,
        hh3cDot11APManufacturer       OCTET STRING,
        hh3cDot11APCPUType            OCTET STRING,
        hh3cDot11APCPUClockSpeed      Unsigned32,
        hh3cDot11APMemoryType         OCTET STRING,
        hh3cDot11APMemorySize         Unsigned32,
        hh3cDot11APFlashType          OCTET STRING,
        hh3cDot11APFlashSize          Unsigned32,
        hh3cDot11APMemSize            Gauge32,
        hh3cDot11APFlashSizeInBytes   Unsigned32,
        hh3cDot11WsmAPLicenseType     INTEGER
    }

hh3cDot11APModelAlias OBJECT-TYPE
    SYNTAX      OCTET STRING(SIZE(0..127))
    MAX-ACCESS  not-accessible
    STATUS      current
    DESCRIPTION
        "Represents alias of AP model name."
    ::= { hh3cDot11APModelEntry 1 }

hh3cDot11APModelName OBJECT-TYPE
    SYNTAX      OCTET STRING
    MAX-ACCESS  read-only
    STATUS      current
    DESCRIPTION
        "Represents AP model name(like WA2100)."
    ::= { hh3cDot11APModelEntry 2 }

hh3cDot11RadioNumSupport OBJECT-TYPE
    SYNTAX      Hh3cDot11RadioScopeType
    MAX-ACCESS  read-only
    STATUS      current
    DESCRIPTION
        "Represents how many radios the specific AP model
        could support."
    ::= { hh3cDot11APModelEntry 3 }

hh3cDot11StationNumSupport OBJECT-TYPE
    SYNTAX      Integer32
    MAX-ACCESS  read-only
    STATUS      current
    DESCRIPTION
        "Represents how many station could be supported by a specific
        AP model."
    ::= { hh3cDot11APModelEntry 4 }

hh3cDot11MACModeSupport OBJECT-TYPE
    SYNTAX      Hh3cDot11MACModeType
    MAX-ACCESS  read-only
    STATUS      current
    DESCRIPTION
        "Represents the MAC mode type could be supported by a specific
        AP model."
    DEFVAL      { split }
    ::= { hh3cDot11APModelEntry 5 }

hh3cDot11APManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { hh3cDot11APModelEntry 6 }

hh3cDot11APCPUType OBJECT-TYPE
    SYNTAX      OCTET STRING
    MAX-ACCESS  read-only
    STATUS      current
    DESCRIPTION
        "Represents the CPU type of AP"
    ::= { hh3cDot11APModelEntry 7 }

hh3cDot11APCPUClockSpeed OBJECT-TYPE
    SYNTAX      Unsigned32
    UNITS       "Hz"
    MAX-ACCESS  read-only
    STATUS      current
    DESCRIPTION
        "Represents the clock speed of CPU."
    ::= { hh3cDot11APModelEntry 8 }

hh3cDot11APMemoryType OBJECT-TYPE
    SYNTAX      OCTET STRING
    MAX-ACCESS  read-only
    STATUS      current
    DESCRIPTION
        "Represents the memory card type of AP"
    ::= { hh3cDot11APModelEntry 9 }

hh3cDot11APMemorySize OBJECT-TYPE
    SYNTAX      Unsigned32
    UNITS       "kbytes"
    MAX-ACCESS  read-only
    STATUS      current
    DESCRIPTION
        "Represents the size of AP memory card."
    ::= { hh3cDot11APModelEntry 20 }

hh3cDot11APFlashType OBJECT-TYPE
    SYNTAX      OCTET STRING
    MAX-ACCESS  read-only
    STATUS      current
    DESCRIPTION
        "Represents the flash card type of AP"
    ::= { hh3cDot11APModelEntry 11 }

hh3cDot11APFlashSize OBJECT-TYPE
    SYNTAX      Unsigned32
    UNITS       "kbytes"
    MAX-ACCESS  read-only
    STATUS      current
    DESCRIPTION
        "Represents the size of AP flash card."
    ::= { hh3cDot11APModelEntry 12 }

hh3cDot11APMemSize OBJECT-TYPE
    SYNTAX      Gauge32
    UNITS       "bytes"
    MAX-ACCESS  read-only
    STATUS      current
    DESCRIPTION
        "Represents the size of AP memory card."
    ::= { hh3cDot11APModelEntry 13 }

hh3cDot11APFlashSizeInBytes OBJECT-TYPE
    SYNTAX      Unsigned32
    UNITS       "bytes"
    MAX-ACCESS  read-only
    STATUS      current
    DESCRIPTION
        "This object represents the size of AP flash card in bytes."
    ::= { hh3cDot11APModelEntry 14 }

hh3cDot11WsmAPLicenseType OBJECT-TYPE
    SYNTAX      INTEGER
        {
            normal(1),
            wtu(2),
            wt(3),
            iot(4),
            other(5)
        }
    MAX-ACCESS  read-only
    STATUS      current
    DESCRIPTION
        "Represents AP license type for iMc WSM."
    ::= { hh3cDot11APModelEntry 15 }


-- *****************************************************************************
-- *  End of hh3cDot11APModelTable Definition
-- *****************************************************************************

-- *****************************************************************************
-- *  hh3cDot11APIfTable Definition
-- *****************************************************************************
hh3cDot11APIfTable OBJECT-TYPE
    SYNTAX      SEQUENCE OF Hh3cDot11APIfEntry
    MAX-ACCESS  not-accessible
    STATUS      current
    DESCRIPTION
        "This table represents the AP interface information."
    ::= { hh3cDot11APObjectGroup 6 }

hh3cDot11APIfEntry OBJECT-TYPE
    SYNTAX      Hh3cDot11APIfEntry
    MAX-ACCESS  not-accessible
    STATUS      current
    DESCRIPTION
        "Each entry of the table will provide data for the interface of AP."
    INDEX
        {
            hh3cDot11APObjID,
            hh3cDot11APIfIndex
        }
    ::= { hh3cDot11APIfTable 1 }

Hh3cDot11APIfEntry ::= SEQUENCE
    {
        hh3cDot11APIfIndex         Integer32,
        hh3cDot11APIfDescr         OCTET STRING,
        hh3cDot11APIfType          Integer32,
        hh3cDot11APIfMtu           Integer32,
        hh3cDot11APIfPHYAddress    OCTET STRING,
        hh3cDot11APIfSpeed         Integer32,
        hh3cDot11APIfInDataRate    Integer32,
        hh3cDot11APIfOutDataRate   Integer32,
        hh3cDot11APIfSpeedKbps     Gauge32,
        hh3cDot11APIfTypeCM        Integer32
    }

hh3cDot11APIfIndex OBJECT-TYPE
    SYNTAX      Integer32
    MAX-ACCESS  not-accessible
    STATUS      current
    DESCRIPTION
        "Represents the index for an interface."
    ::= { hh3cDot11APIfEntry 1 }

hh3cDot11APIfDescr OBJECT-TYPE
    SYNTAX      OCTET STRING
    MAX-ACCESS  read-only
    STATUS      current
    DESCRIPTION
        "Represents the interface description for an interface."
    ::= { hh3cDot11APIfEntry 2 }

hh3cDot11APIfType OBJECT-TYPE
    SYNTAX      Integer32
    MAX-ACCESS  read-only
    STATUS      current
    DESCRIPTION
        "Represents the interface type for an interface."
    ::= { hh3cDot11APIfEntry 3 }

hh3cDot11APIfMtu OBJECT-TYPE
    SYNTAX      Integer32
    MAX-ACCESS  read-write
    STATUS      current
    DESCRIPTION
        "Represents size of the largest datagram which can
        be sent/received on the interface, specified in octets."
    ::= { hh3cDot11APIfEntry 4 }

hh3cDot11APIfPHYAddress OBJECT-TYPE
    SYNTAX      OCTET STRING
    MAX-ACCESS  read-only
    STATUS      current
    DESCRIPTION
        "Represents the PHY address of interface."
    ::= { hh3cDot11APIfEntry 5 }

hh3cDot11APIfSpeed OBJECT-TYPE
    SYNTAX      Integer32
    UNITS       "Mbps"
    MAX-ACCESS  read-only
    STATUS      current
    DESCRIPTION
        "Represents maximum bandwidth of this interface."
    ::= { hh3cDot11APIfEntry 6 }

hh3cDot11APIfInDataRate OBJECT-TYPE
    SYNTAX      Integer32
    UNITS       "Kbps"
    MAX-ACCESS  read-only
    STATUS      current
    DESCRIPTION
        "Represents the average input data rate of this interface in
        latest 300 seconds."
    ::= { hh3cDot11APIfEntry 7 }

hh3cDot11APIfOutDataRate OBJECT-TYPE
    SYNTAX      Integer32
    UNITS       "Kbps"
    MAX-ACCESS  read-only
    STATUS      current
    DESCRIPTION
        "Represents the average output data rate of this interface in
        latest 300 seconds."
    ::= { hh3cDot11APIfEntry 8 }

hh3cDot11APIfSpeedKbps OBJECT-TYPE
    SYNTAX      Gauge32
    UNITS       "kbps"
    MAX-ACCESS  read-only
    STATUS      current
    DESCRIPTION
        "Represents maximum bandwidth of this interface."
    ::= { hh3cDot11APIfEntry 9 }

hh3cDot11APIfTypeCM OBJECT-TYPE
    SYNTAX      Integer32
    MAX-ACCESS  read-only
    STATUS      current
    DESCRIPTION
        "Represents the interface type."
    ::= { hh3cDot11APIfEntry 10 }

-- *****************************************************************************
-- *  End of hh3cDot11APIfTable Definition
-- *****************************************************************************

-- *****************************************************************************
-- *  hh3cDot11APSSIDObjectTable Definition
-- *****************************************************************************
hh3cDot11APSSIDObjectTable OBJECT-TYPE
    SYNTAX      SEQUENCE OF Hh3cDot11APSSIDObjectEntry
    MAX-ACCESS  not-accessible
    STATUS      current
    DESCRIPTION
        "This table provides BSSID number configuration information
         based on SSID."
    ::= { hh3cDot11APObjectGroup 7 }

hh3cDot11APSSIDObjectEntry OBJECT-TYPE
    SYNTAX      Hh3cDot11APSSIDObjectEntry
    MAX-ACCESS  not-accessible
    STATUS      current
    DESCRIPTION
        "Each entry provides BSSID number configuration information
         of a SSID."
    INDEX
        {
            hh3cDot11APConfigSPID
        }
    ::= { hh3cDot11APSSIDObjectTable 1 }

Hh3cDot11APSSIDObjectEntry ::= SEQUENCE
    {
        hh3cDot11APConfigSPID              Hh3cDot11ServicePolicyIDType,
        hh3cDot11APConfigSSIDName          Hh3cDot11SSIDStringType,
        hh3cDot11APConfigBSSIDNum          Integer32,
        hh3cDot11APConfigPortalStaNum      Integer32,
        hh3cDot11APAssocStaNum             Integer32
    }

hh3cDot11APConfigSPID OBJECT-TYPE
    SYNTAX      Hh3cDot11ServicePolicyIDType
    MAX-ACCESS  not-accessible
    STATUS      current
    DESCRIPTION
        "Represents the service policy ID."
    ::= { hh3cDot11APSSIDObjectEntry 1 }

hh3cDot11APConfigSSIDName OBJECT-TYPE
    SYNTAX      Hh3cDot11SSIDStringType
    MAX-ACCESS  read-only
    STATUS      current
    DESCRIPTION
        "Represents the SSID name of this service policy."
    ::= { hh3cDot11APSSIDObjectEntry 2 }

hh3cDot11APConfigBSSIDNum OBJECT-TYPE
    SYNTAX      Integer32
    MAX-ACCESS  read-only
    STATUS      current
    DESCRIPTION
        "Represents the number of BSSID that be configured
         with current SSID."
    ::= { hh3cDot11APSSIDObjectEntry 3 }

hh3cDot11APConfigPortalStaNum OBJECT-TYPE
    SYNTAX      Integer32
    MAX-ACCESS  read-only
    STATUS      current
    DESCRIPTION
        "Represents the total number of associated protal
        stations with current SSID."
    ::= { hh3cDot11APSSIDObjectEntry 4 }

hh3cDot11APAssocStaNum OBJECT-TYPE
    SYNTAX      Integer32
    MAX-ACCESS  read-only
    STATUS      current
    DESCRIPTION
        "Represents the total number of associated stations with current SSID."
    ::= { hh3cDot11APSSIDObjectEntry 5 }

-- *****************************************************************************
-- *  End of hh3cDot11APSSIDObjectTable Definition
-- *****************************************************************************

-- *****************************************************************************
-- *  hh3cDot11APSysInfoTable Definition
-- *****************************************************************************
hh3cDot11APSysInfoTable OBJECT-TYPE
    SYNTAX      SEQUENCE OF Hh3cDot11APSysInfoEntry
    MAX-ACCESS  not-accessible
    STATUS      current
    DESCRIPTION
        "The table provides the system information of the AP."
    ::= { hh3cDot11APObjectGroup 8 }

hh3cDot11APSysInfoEntry OBJECT-TYPE
    SYNTAX      Hh3cDot11APSysInfoEntry
    MAX-ACCESS  not-accessible
    STATUS      current
    DESCRIPTION
        "Each entry provides system information of an AP."
    INDEX
        {
            hh3cDot11APElementIndex
        }
    ::= { hh3cDot11APSysInfoTable 1 }

Hh3cDot11APSysInfoEntry ::= SEQUENCE
    {
        hh3cDot11APSysUpTime           TimeTicks,
        hh3cDot11APCPURTUsage          Integer32,
        hh3cDot11APCPUAvgUsage         Integer32,
        hh3cDot11APMemRTUsage          Integer32,
        hh3cDot11APMemAvgUsage         Integer32,
        hh3cDot11APIPAddressGateway    IpAddress,
        hh3cDot11APACAssociateStatus   INTEGER,
        hh3cDot11APManuBuildInfo       OCTET STRING,
        hh3cDot11APFlashFreeSize       Unsigned32,
        hh3cDot11APTemperature         Integer32
    }

hh3cDot11APSysUpTime OBJECT-TYPE
    SYNTAX      TimeTicks
    MAX-ACCESS  read-only
    STATUS      current
    DESCRIPTION
        "Represents how long AP has been powered on."
    ::= { hh3cDot11APSysInfoEntry 1 }

hh3cDot11APCPURTUsage OBJECT-TYPE
    SYNTAX      Integer32(0..100)
    UNITS       "onepercent"
    MAX-ACCESS  read-only
    STATUS      current
    DESCRIPTION
        "Represents the CPU real time usage for AP."
    ::= { hh3cDot11APSysInfoEntry 2 }

hh3cDot11APCPUAvgUsage OBJECT-TYPE
    SYNTAX      Integer32(0..100)
    UNITS       "onepercent"
    MAX-ACCESS  read-only
    STATUS      current
    DESCRIPTION
        "Represents the CPU average usage for AP."
    ::= { hh3cDot11APSysInfoEntry 3 }

hh3cDot11APMemRTUsage OBJECT-TYPE
    SYNTAX      Integer32(0..100)
    UNITS       "onepercent"
    MAX-ACCESS  read-only
    STATUS      current
    DESCRIPTION
        "Represents the memory real time usage for AP."
    ::= { hh3cDot11APSysInfoEntry 4 }

hh3cDot11APMemAvgUsage OBJECT-TYPE
    SYNTAX      Integer32(0..100)
    UNITS       "onepercent"
    MAX-ACCESS  read-only
    STATUS      current
    DESCRIPTION
        "Represents the average memory usage for AP."
    ::= { hh3cDot11APSysInfoEntry 5 }

hh3cDot11APIPAddressGateway OBJECT-TYPE
    SYNTAX      IpAddress
    MAX-ACCESS  read-only
    STATUS      current
    DESCRIPTION
        "Represents the IP address gateway for AP."
    ::= { hh3cDot11APSysInfoEntry 6 }

hh3cDot11APACAssociateStatus OBJECT-TYPE
    SYNTAX      INTEGER
        {
            associated(1),
            deassociated(2),
            downloadingImage(3)
        }
    MAX-ACCESS  read-only
    STATUS      current
    DESCRIPTION
        "Represents associate status of AP and AC."
    ::= { hh3cDot11APSysInfoEntry 7 }

hh3cDot11APManuBuildInfo OBJECT-TYPE
    SYNTAX      OCTET STRING(SIZE(0..255))
    MAX-ACCESS  read-only
    STATUS      current
    DESCRIPTION
        "Represents the device version information for AP."
    ::= { hh3cDot11APSysInfoEntry 8 }

hh3cDot11APFlashFreeSize OBJECT-TYPE
    SYNTAX      Unsigned32
    UNITS       "bytes"
    MAX-ACCESS  read-only
    STATUS      current
    DESCRIPTION
        "Represents the free size of AP flash card."
    ::= { hh3cDot11APSysInfoEntry 9 }

hh3cDot11APTemperature OBJECT-TYPE
    SYNTAX      Integer32
    MAX-ACCESS  read-only
    STATUS      current
    DESCRIPTION
        "Represents the device temperature information for AP."
    ::= { hh3cDot11APSysInfoEntry 10 }

-- *****************************************************************************
-- *  End of hh3cDot11APSysInfoTable Definition
-- *****************************************************************************

-- *****************************************************************************
-- *  hh3cDot11APIdleListTable Definition
-- *****************************************************************************
hh3cDot11APIdleListTable OBJECT-TYPE
    SYNTAX      SEQUENCE OF Hh3cDot11APIdleListEntry
    MAX-ACCESS  not-accessible
    STATUS      current
    DESCRIPTION
        "This table provides the list of idle AP."
    ::= { hh3cDot11APObjectGroup 9 }

hh3cDot11APIdleListEntry OBJECT-TYPE
    SYNTAX      Hh3cDot11APIdleListEntry
    MAX-ACCESS  not-accessible
    STATUS      current
    DESCRIPTION
        "Each entry provides information of a idle AP."
    INDEX
        {
            hh3cDot11APIdleTemplateName
        }
    ::= { hh3cDot11APIdleListTable 1 }

Hh3cDot11APIdleListEntry ::= SEQUENCE
    {
        hh3cDot11APIdleTemplateName OCTET STRING,
        hh3cDot11APIdleSerialID     OCTET STRING
    }

hh3cDot11APIdleTemplateName OBJECT-TYPE
    SYNTAX      OCTET STRING(SIZE(0..127))
    MAX-ACCESS  not-accessible
    STATUS      current
    DESCRIPTION
        "Represents the name of idle AP template."
    ::= { hh3cDot11APIdleListEntry 1 }

hh3cDot11APIdleSerialID    OBJECT-TYPE
    SYNTAX      OCTET STRING
    MAX-ACCESS  read-only
    STATUS      current
    DESCRIPTION
        "Represents AP serial ID."
    ::= { hh3cDot11APIdleListEntry 2 }

-- *****************************************************************************
-- *  End of hh3cDot11APIdleListTable Definition
-- *****************************************************************************

-- *****************************************************************************
-- *  hh3cDot11APSysInfoByAPIDTable Definition
-- *****************************************************************************
hh3cDot11APSysInfoByAPIDTable OBJECT-TYPE
    SYNTAX      SEQUENCE OF Hh3cDot11APSysInfoByAPIDEntry
    MAX-ACCESS  not-accessible
    STATUS      current
    DESCRIPTION
        "The table provides the system information of the AP."
    ::= { hh3cDot11APObjectGroup 10 }

hh3cDot11APSysInfoByAPIDEntry OBJECT-TYPE
    SYNTAX      Hh3cDot11APSysInfoByAPIDEntry
    MAX-ACCESS  not-accessible
    STATUS      current
    DESCRIPTION
        "Each entry provides system information of an AP."
    INDEX
        {
            hh3cDot11APObjID
        }
    ::= { hh3cDot11APSysInfoByAPIDTable 1 }

Hh3cDot11APSysInfoByAPIDEntry ::= SEQUENCE
    {
        hh3cDot11APSysUpTime2           TimeTicks,
        hh3cDot11APCPURTUsage2          Integer32,
        hh3cDot11APCPUAvgUsage2         Integer32,
        hh3cDot11APMemRTUsage2          Integer32,
        hh3cDot11APMemAvgUsage2         Integer32,
        hh3cDot11APIPAddressGateway2    IpAddress,
        hh3cDot11APACAssociateStatus2   INTEGER,
        hh3cDot11APManuBuildInfo2       OCTET STRING,
        hh3cDot11APFlashFreeSize2       Unsigned32,
        hh3cDot11APTemperature2         Integer32,
        hh3cDot11APMacAddress2          MacAddress,
        hh3cDot11APACAssociateStatusCM  INTEGER
    }

hh3cDot11APSysUpTime2 OBJECT-TYPE
    SYNTAX      TimeTicks
    MAX-ACCESS  read-only
    STATUS      current
    DESCRIPTION
        "Represents how long AP has been powered on."
    ::= { hh3cDot11APSysInfoByAPIDEntry 1 }

hh3cDot11APCPURTUsage2 OBJECT-TYPE
    SYNTAX      Integer32(0..100)
    UNITS       "onepercent"
    MAX-ACCESS  read-only
    STATUS      current
    DESCRIPTION
        "Represents the CPU real time usage for AP."
    ::= { hh3cDot11APSysInfoByAPIDEntry 2 }

hh3cDot11APCPUAvgUsage2 OBJECT-TYPE
    SYNTAX      Integer32(0..100)
    UNITS       "onepercent"
    MAX-ACCESS  read-only
    STATUS      current
    DESCRIPTION
        "Represents the CPU average usage for AP."
    ::= { hh3cDot11APSysInfoByAPIDEntry 3 }

hh3cDot11APMemRTUsage2 OBJECT-TYPE
    SYNTAX      Integer32(0..100)
    UNITS       "onepercent"
    MAX-ACCESS  read-only
    STATUS      current
    DESCRIPTION
        "Represents the memory real time usage for AP."
    ::= { hh3cDot11APSysInfoByAPIDEntry 4 }

hh3cDot11APMemAvgUsage2 OBJECT-TYPE
    SYNTAX      Integer32(0..100)
    UNITS       "onepercent"
    MAX-ACCESS  read-only
    STATUS      current
    DESCRIPTION
        "Represents the average memory usage for AP."
    ::= { hh3cDot11APSysInfoByAPIDEntry 5 }

hh3cDot11APIPAddressGateway2 OBJECT-TYPE
    SYNTAX      IpAddress
    MAX-ACCESS  read-only
    STATUS      current
    DESCRIPTION
        "Represents the IP address gateway for AP."
    ::= { hh3cDot11APSysInfoByAPIDEntry 6 }

hh3cDot11APACAssociateStatus2 OBJECT-TYPE
    SYNTAX      INTEGER
        {
            associated(1),
            deassociated(2),
            downloadingImage(3)
        }
    MAX-ACCESS  read-only
    STATUS      current
    DESCRIPTION
        "Represents associate status of AP and AC."
    ::= { hh3cDot11APSysInfoByAPIDEntry 7 }

hh3cDot11APManuBuildInfo2 OBJECT-TYPE
    SYNTAX      OCTET STRING(SIZE(0..255))
    MAX-ACCESS  read-only
    STATUS      current
    DESCRIPTION
        "Represents the device version information for AP."
    ::= { hh3cDot11APSysInfoByAPIDEntry 8 }

hh3cDot11APFlashFreeSize2 OBJECT-TYPE
    SYNTAX      Unsigned32
    UNITS       "bytes"
    MAX-ACCESS  read-only
    STATUS      current
    DESCRIPTION
        "Represents the free size of AP flash card."
    ::= { hh3cDot11APSysInfoByAPIDEntry 9 }

hh3cDot11APTemperature2 OBJECT-TYPE
    SYNTAX      Integer32
    MAX-ACCESS  read-only
    STATUS      current
    DESCRIPTION
        "Represents the device temperature information for AP."
    ::= { hh3cDot11APSysInfoByAPIDEntry 10 }

hh3cDot11APMacAddress2 OBJECT-TYPE
    SYNTAX      MacAddress
    MAX-ACCESS  read-only
    STATUS      current
    DESCRIPTION
        "Represents the MAC address of AP."
    ::= { hh3cDot11APSysInfoByAPIDEntry 11 }

hh3cDot11APACAssociateStatusCM OBJECT-TYPE
    SYNTAX      INTEGER
        {
            deassociated(0),
            associated(1)
        }
    MAX-ACCESS  read-only
    STATUS      current
    DESCRIPTION
        "Represents associate status of AP and AC."
    ::= { hh3cDot11APSysInfoByAPIDEntry 12 }

-- *****************************************************************************
-- *  End of hh3cDot11APSysInfoByAPIDTable Definition
-- *****************************************************************************

-- *****************************************************************************
-- *  hh3cDot11WTUAPInfoTable Definition
-- *****************************************************************************
hh3cDot11WTUAPInfoTable OBJECT-TYPE
    SYNTAX      SEQUENCE OF Hh3cDot11WTUAPInfoEntry
    MAX-ACCESS  not-accessible
    STATUS      current
    DESCRIPTION
        "The table provides relationship information between wireless terminator units (WTUs) and WTs."
    ::= { hh3cDot11APObjectGroup 11 }

hh3cDot11WTUAPInfoEntry OBJECT-TYPE
    SYNTAX      Hh3cDot11WTUAPInfoEntry
    MAX-ACCESS  not-accessible
    STATUS      current
    DESCRIPTION
        "Each entry provides relationship information between a WTU and a WT."
    INDEX
        {
            hh3cDot11ContainerSerialID,
            hh3cDot11WTUAPSerialID
        }
    ::= { hh3cDot11WTUAPInfoTable 1 }

Hh3cDot11WTUAPInfoEntry ::= SEQUENCE
    {
        hh3cDot11ContainerSerialID    Hh3cDot11ObjectIDType,
        hh3cDot11WTUAPSerialID        Hh3cDot11ObjectIDType,
        hh3cDot11WTUAPSubSlotID       Unsigned32
    }

hh3cDot11ContainerSerialID OBJECT-TYPE
    SYNTAX      Hh3cDot11ObjectIDType
    MAX-ACCESS  not-accessible
    STATUS      current
    DESCRIPTION
        "Serial ID that uniquely identifies a WT."
    ::= { hh3cDot11WTUAPInfoEntry 1 }

hh3cDot11WTUAPSerialID OBJECT-TYPE
    SYNTAX      Hh3cDot11ObjectIDType
    MAX-ACCESS  not-accessible
    STATUS      current
    DESCRIPTION
        "Serial ID that uniquely identifies a WTU."
    ::= { hh3cDot11WTUAPInfoEntry 2 }

hh3cDot11WTUAPSubSlotID OBJECT-TYPE
    SYNTAX      Unsigned32
    MAX-ACCESS  read-only
    STATUS      current
    DESCRIPTION
        "Represents the sub-slot ID of a WTU."
    ::= { hh3cDot11WTUAPInfoEntry 3 }

-- *****************************************************************************
-- *  End of hh3cDot11WTUAPInfoTable Definition
-- *****************************************************************************

-- *****************************************************************************
-- *  hh3cDot11ApBriefInfoTable Definition
-- *****************************************************************************
hh3cDot11ApBriefInfoTable OBJECT-TYPE
    SYNTAX      SEQUENCE OF Hh3cDot11ApBriefInfoEntry
    MAX-ACCESS  not-accessible
    STATUS      current
    DESCRIPTION
        "The table provides AP information."
    ::= { hh3cDot11APObjectGroup 12 }

hh3cDot11ApBriefInfoEntry OBJECT-TYPE
    SYNTAX      Hh3cDot11ApBriefInfoEntry
    MAX-ACCESS  not-accessible
    STATUS      current
    DESCRIPTION
        "Each entry contains information about an AP."
    INDEX
        {
            hh3cDot11BrfAPName
        }
    ::= { hh3cDot11ApBriefInfoTable 1 }

Hh3cDot11ApBriefInfoEntry ::= SEQUENCE
    {
        hh3cDot11BrfAPName                 OCTET STRING,
        hh3cDot11BrfAPSerialID             OCTET STRING,
        hh3cDot11BrfAPModelName            OCTET STRING,
        hh3cDot11BrfAPDescription          OCTET STRING,
        hh3cDot11BrfAPStatisInterv         Integer32,
        hh3cDot11BrfAPStaIdleInterv        Integer32,
        hh3cDot11BrfAPStaKeepAliveInterv   Integer32,
        hh3cDot11BrfAPCir                  Integer32,
        hh3cDot11BrfAPCbs                  Integer32,
        hh3cDot11BrfAPPriorityLevel        Integer32,
        hh3cDot11BrfAPElementID            Integer32,
        hh3cDot11BrfAPSupportRadioMode     Integer32,
        hh3cDot11BrfAPControlAddressState  INTEGER,
        hh3cDot11BrfAPControlAddressIPv4   IpAddress,
        hh3cDot11BrfAPLocalACName          OCTET STRING,
        hh3cDot11BrfAPIPAddress            IpAddress,
        hh3cDot11BrfAPMacAddress           MacAddress,
        hh3cDot11BrfAPConnectType          INTEGER,
        hh3cDot11BrfAPIPv6Address          OCTET STRING,
        hh3cDot11BrfAPACPortIndex          Integer32,
        hh3cDot11BrfAPStaAssocCount        Integer32,
        hh3cDot11BrfAPImageName            OCTET STRING,
        hh3cDot11BrfAPSoftwareVersion      OCTET STRING,
        hh3cDot11BrfAPIPNetMask            IpAddress,
        hh3cDot11BrfAPOperationStatus      INTEGER
    }

hh3cDot11BrfAPName OBJECT-TYPE
    SYNTAX      OCTET STRING(SIZE(1..127))
    MAX-ACCESS  not-accessible
    STATUS      current
    DESCRIPTION
        "Represents the name of an AP template."
    ::= { hh3cDot11ApBriefInfoEntry 1 }

hh3cDot11BrfAPSerialID OBJECT-TYPE
    SYNTAX      OCTET STRING
    MAX-ACCESS  read-only
    STATUS      current
    DESCRIPTION
        "Represents an AP serial ID."
    ::= { hh3cDot11ApBriefInfoEntry 2 }

hh3cDot11BrfAPModelName OBJECT-TYPE
    SYNTAX      OCTET STRING
    MAX-ACCESS  read-only
    STATUS      current
    DESCRIPTION
        "Represents an AP model."
    ::= { hh3cDot11ApBriefInfoEntry 3 }

hh3cDot11BrfAPDescription OBJECT-TYPE
    SYNTAX      OCTET STRING
    MAX-ACCESS  read-only
    STATUS      current
    DESCRIPTION
        "Represents an AP description. The administrator can use
         the description to specify the location, owner, or other
         information of an AP."
    ::= { hh3cDot11ApBriefInfoEntry 4 }

hh3cDot11BrfAPStatisInterv OBJECT-TYPE
    SYNTAX      Integer32
    UNITS       "second"
    MAX-ACCESS  read-only
    STATUS      current
    DESCRIPTION
        "Represents the interval for collecting radio statistics."
    ::= { hh3cDot11ApBriefInfoEntry 5 }

hh3cDot11BrfAPStaIdleInterv OBJECT-TYPE
    SYNTAX      Integer32
    UNITS       "second"
    MAX-ACCESS  read-only
    STATUS      current
    DESCRIPTION
        "Represents the idle timeout for AP-client connections."
    ::= { hh3cDot11ApBriefInfoEntry 6 }

hh3cDot11BrfAPStaKeepAliveInterv OBJECT-TYPE
    SYNTAX      Integer32
    UNITS       "second"
    MAX-ACCESS  read-only
    STATUS      current
    DESCRIPTION
        "Represents the keepalive interval between AP and client."
    ::= { hh3cDot11ApBriefInfoEntry 7 }

hh3cDot11BrfAPCir OBJECT-TYPE
    SYNTAX      Integer32
    UNITS       "Kbps"
    MAX-ACCESS  read-only
    STATUS      current
    DESCRIPTION
        "Represents the committed information rate between AP and AC."
    ::= { hh3cDot11ApBriefInfoEntry 8 }

hh3cDot11BrfAPCbs OBJECT-TYPE
    SYNTAX      Integer32
    UNITS       "Bytes"
    MAX-ACCESS  read-only
    STATUS      current
    DESCRIPTION
        "Represents the committed burst size between AP and AC."
    ::= { hh3cDot11ApBriefInfoEntry 9 }

hh3cDot11BrfAPPriorityLevel OBJECT-TYPE
    SYNTAX      Integer32
    MAX-ACCESS  read-only
    STATUS      current
    DESCRIPTION
        "Represents the connection priority of an AP.
        If the connection priority is 7, the AC is considered as the
        primary AC for the AP."
    DEFVAL      { 4 }
    ::= { hh3cDot11ApBriefInfoEntry 10 }

hh3cDot11BrfAPElementID OBJECT-TYPE
    SYNTAX      Integer32
    MAX-ACCESS  read-only
    STATUS      current
    DESCRIPTION
        "Represents the AP element ID."
    ::= { hh3cDot11ApBriefInfoEntry 11 }

hh3cDot11BrfAPSupportRadioMode OBJECT-TYPE
    SYNTAX      Integer32
    MAX-ACCESS  read-only
    STATUS      current
    DESCRIPTION
        "Represents radio types supported by an AP.
        The WLAN system supports the following radio types:
        dot11b(1),
        dot11a(2),
        dot11g(4),
        dot11gn(8),
        dot11an(16),
        dot11gac(32),
        dot11ac(64),
        dot11gax(128),
        dot11ax(256)
        An AP can support multiple radio types at
        the same time. This field displays the sum of radio type values supported by an AP.
        For example:
        If an AP support both 802.11b and 802.11g, the value is 6, which is 2 plus 4."
    ::= { hh3cDot11ApBriefInfoEntry 12 }

hh3cDot11BrfAPControlAddressState OBJECT-TYPE
    SYNTAX      INTEGER
        {
            enable(1),
            disable(2)
        }
    MAX-ACCESS  read-only
    STATUS      current
    DESCRIPTION
        "Represents the status of control address for an AP.
        The following values are supported:
        enable      - AC rediscovery will be enabled.
        disable     - AC rediscovery will be disabled."
        DEFVAL      { disable }
    ::= { hh3cDot11ApBriefInfoEntry 13 }

hh3cDot11BrfAPControlAddressIPv4 OBJECT-TYPE
    SYNTAX      IpAddress
    MAX-ACCESS  read-only
    STATUS      current
    DESCRIPTION
        "Represents the AC IPv4 address for AC rediscovery."
    ::= { hh3cDot11ApBriefInfoEntry 14 }

hh3cDot11BrfAPLocalACName OBJECT-TYPE
    SYNTAX      OCTET STRING
    MAX-ACCESS  read-only
    STATUS      current
    DESCRIPTION
        "Represents the local AC name for an AP."
    ::= { hh3cDot11ApBriefInfoEntry 15 }

hh3cDot11BrfAPIPAddress OBJECT-TYPE
    SYNTAX      IpAddress
    MAX-ACCESS  read-only
    STATUS      current
    DESCRIPTION
        "Represents the IP address of an AP."
    ::= { hh3cDot11ApBriefInfoEntry 16 }

hh3cDot11BrfAPMacAddress OBJECT-TYPE
    SYNTAX      MacAddress
    MAX-ACCESS  read-only
    STATUS      current
    DESCRIPTION
        "Represents the MAC address of an AP."
    ::= { hh3cDot11ApBriefInfoEntry 17 }

hh3cDot11BrfAPConnectType OBJECT-TYPE
    SYNTAX      INTEGER
        {
            master(1),
            standBy(2),
            notAvailable(3)
        }
    MAX-ACCESS  read-only
    STATUS      current
    DESCRIPTION
        "Represents the current connection type."
    ::= { hh3cDot11ApBriefInfoEntry 18 }

hh3cDot11BrfAPIPv6Address OBJECT-TYPE
    SYNTAX      OCTET STRING
    MAX-ACCESS  read-only
    STATUS      current
    DESCRIPTION
        "Represents the IPv6 address of an AP."
    ::= { hh3cDot11ApBriefInfoEntry 19 }

hh3cDot11BrfAPACPortIndex OBJECT-TYPE
    SYNTAX      Integer32
    MAX-ACCESS  read-only
    STATUS      current
    DESCRIPTION
        "Represents the port on the AC, through which the traffic of an AP is transmitted.
         NMS might use the value as access information in MIB-2."
    ::= { hh3cDot11ApBriefInfoEntry 20 }

hh3cDot11BrfAPStaAssocCount OBJECT-TYPE
    SYNTAX      Integer32
    MAX-ACCESS  read-only
    STATUS      current
    DESCRIPTION
        "Represents the total number of stations associated with an AP."
    ::= { hh3cDot11ApBriefInfoEntry 21 }

hh3cDot11BrfAPImageName OBJECT-TYPE
    SYNTAX      OCTET STRING
    MAX-ACCESS  read-only
    STATUS      current
    DESCRIPTION
        "Represents the image file name of an AP."
    ::= { hh3cDot11ApBriefInfoEntry 22 }

hh3cDot11BrfAPSoftwareVersion OBJECT-TYPE
    SYNTAX      OCTET STRING
    MAX-ACCESS  read-only
    STATUS      current
    DESCRIPTION
        "Represents the software version of an AP."
    ::= { hh3cDot11ApBriefInfoEntry 23 }

hh3cDot11BrfAPIPNetMask OBJECT-TYPE
    SYNTAX      IpAddress
    MAX-ACCESS  read-only
    STATUS      current
    DESCRIPTION
        "Represents the IP address mask of an AP."
    ::= { hh3cDot11ApBriefInfoEntry 24 }

hh3cDot11BrfAPOperationStatus OBJECT-TYPE
    SYNTAX      INTEGER
        {
            run(1),
            idle(2)
        }
    MAX-ACCESS  read-only
    STATUS      current
    DESCRIPTION
        "Represent the status of an AP. Options include:
        2: Idle.
        1: Run."
    ::= { hh3cDot11ApBriefInfoEntry 25 }

-- *****************************************************************************
-- *  End of hh3cDot11ApBriefInfoTable Definition
-- *****************************************************************************

-- *****************************************************************************
-- *  hh3cDot11MaxPowerCapaTable Definition
-- *****************************************************************************
hh3cDot11MaxPowerCapaTable OBJECT-TYPE
    SYNTAX      SEQUENCE OF Hh3cDot11MaxPowerCapaEntry
    MAX-ACCESS  not-accessible
    STATUS      current
    DESCRIPTION
        "The table provides max power capabilities of APs."
    ::= { hh3cDot11APObjectGroup 13 }

hh3cDot11MaxPowerCapaEntry OBJECT-TYPE
    SYNTAX      Hh3cDot11MaxPowerCapaEntry
    MAX-ACCESS  not-accessible
    STATUS      current
    DESCRIPTION
        "Each entry of the table provides max power information for an AP."
    INDEX
        {
            hh3cDot11MaxPowerCapaApName,
            hh3cDot11MaxPowerCapaRadioId,
            hh3cDot11MaxPowerCapaRadioType,
            hh3cDot11MaxPowerCapaChl
        }
    ::= { hh3cDot11MaxPowerCapaTable 1 }

Hh3cDot11MaxPowerCapaEntry ::= SEQUENCE
    {
        hh3cDot11MaxPowerCapaApName        OCTET STRING,
        hh3cDot11MaxPowerCapaRadioId       Integer32,
        hh3cDot11MaxPowerCapaRadioType     Integer32,
        hh3cDot11MaxPowerCapaChl           Integer32,
        hh3cDot11MaxPowerCapability        Integer32
    }

hh3cDot11MaxPowerCapaApName OBJECT-TYPE
    SYNTAX      OCTET STRING
    MAX-ACCESS  not-accessible
    STATUS      current
    DESCRIPTION
        "Represents the name of an AP."
    ::= { hh3cDot11MaxPowerCapaEntry 1 }

hh3cDot11MaxPowerCapaRadioId OBJECT-TYPE
    SYNTAX      Integer32
    MAX-ACCESS  not-accessible
    STATUS      current
    DESCRIPTION
        "Represents radio ID of an AP."
    ::= { hh3cDot11MaxPowerCapaEntry 2 }

hh3cDot11MaxPowerCapaRadioType OBJECT-TYPE
    SYNTAX      Integer32
    MAX-ACCESS  not-accessible
    STATUS      current
    DESCRIPTION
        "Represents the radio type."
    ::= { hh3cDot11MaxPowerCapaEntry 3 }

hh3cDot11MaxPowerCapaChl OBJECT-TYPE
    SYNTAX      Integer32
    MAX-ACCESS  not-accessible
    STATUS      current
    DESCRIPTION
        "Represents the channel number of an AP."
    ::= { hh3cDot11MaxPowerCapaEntry 4 }

hh3cDot11MaxPowerCapability OBJECT-TYPE
    SYNTAX      Integer32
    MAX-ACCESS  read-only
    STATUS      current
    DESCRIPTION
        "Represents the max power."
    ::= { hh3cDot11MaxPowerCapaEntry 5 }

-- *****************************************************************************
-- *  End of hh3cDot11MaxPowerTable Definition
-- *****************************************************************************

-- *****************************************************************************
-- *  hh3cDot11APRxStatisTable Definition
-- *****************************************************************************
hh3cDot11APRxStatisTable OBJECT-TYPE
    SYNTAX      SEQUENCE OF Hh3cDot11APRxStatisEntry
    MAX-ACCESS  not-accessible
    STATUS      current
    DESCRIPTION
        "The table will provide the receiving statistic for a specific
        radio of AP."
    ::= { hh3cDot11APStatisGroup 1 }

hh3cDot11APRxStatisEntry OBJECT-TYPE
    SYNTAX      Hh3cDot11APRxStatisEntry
    MAX-ACCESS  not-accessible
    STATUS      current
    DESCRIPTION
        "Each entry of the table will provide the statistic data for
        each radio of a specific AP."
    INDEX
        {
            hh3cDot11CurAPID,
            hh3cDot11RadioID
        }
    ::= { hh3cDot11APRxStatisTable 1 }

Hh3cDot11APRxStatisEntry ::= SEQUENCE
    {
        hh3cDot11RxFrameDupCnt          Counter32,
        hh3cDot11RxFrameCnt             Counter32,
        hh3cDot11RxUcastFrameCnt        Counter32,
        hh3cDot11RxBcastFrameCnt        Counter32,
        hh3cDot11RxMcastFrameCnt        Counter32,
        hh3cDot11RxDiscardFrameCnt      Counter32,
        hh3cDot11RxFragCnt              Counter32,
        hh3cDot11RxFcsErrCnt            Counter32,
        hh3cDot11RxFrameBytes           Counter32,
        hh3cDot11RxUcastFrameBytes      Counter32,
        hh3cDot11RxBcastFrameBytes      Counter32,
        hh3cDot11RxMcastFrameBytes      Counter32,
        hh3cDot11RxDiscardFrameBytes    Counter32,
        hh3cDot11RxMgmtFrameCnt         Counter32,
        hh3cDot11RxCtrlFrameCnt         Counter32,
        hh3cDot11RxDataFrameCnt         Counter32,
        hh3cDot11RxDecryptErrorCnt      Counter32,
        hh3cDot11RxAuthenFrameCnt       Counter32,
        hh3cDot11RxAssociateFrameCnt    Counter32,
        hh3cDot11RxFrameErrorRatio      Integer32,
        hh3cDot11RxPhyErrorCnt          Counter32,
        hh3cDot11RxMICErrorCnt          Counter32,
        hh3cDot11RxDataFrameBytes       Counter32,
        hh3cDot11RadioRxAverSnr         Integer32,
        hh3cDot11RxPayloadBytes         Counter32,
        hh3cDot11RxTrafficSpeed         Integer32,
        hh3cDot11RxUcastDataFrameCnt    Counter64,
        hh3cDot11RxNUcastDataFrameCnt   Counter64,
        hh3cDot11RxTotalDiscardFrameCnt Counter64,
        hh3cDot11RxTotalIPCheckErrPacketCnt    Counter64,
        hh3cDot11RxSignalStrengthPacketCntCM   OCTET STRING,
        hh3cDot11RxDataFrameCntCM              Counter32,
        hh3cDot11RxTotalFrameCnt               Counter64
    }

hh3cDot11RxFrameDupCnt OBJECT-TYPE
    SYNTAX      Counter32
    MAX-ACCESS  read-only
    STATUS      current
    DESCRIPTION
        "Represents the number of duplicate frames reception."
    ::= { hh3cDot11APRxStatisEntry 1 }

hh3cDot11RxFrameCnt OBJECT-TYPE
    SYNTAX      Counter32
    MAX-ACCESS  read-only
    STATUS      current
    DESCRIPTION
        "Represents the number of frames reception."
    ::= { hh3cDot11APRxStatisEntry 2 }

hh3cDot11RxUcastFrameCnt OBJECT-TYPE
    SYNTAX      Counter32
    MAX-ACCESS  read-only
    STATUS      current
    DESCRIPTION
        "Represents the number of unicast frames reception."
    ::= { hh3cDot11APRxStatisEntry 3 }

hh3cDot11RxBcastFrameCnt OBJECT-TYPE
    SYNTAX      Counter32
    MAX-ACCESS  read-only
    STATUS      current
    DESCRIPTION
        "Represents the number of broadcast frames reception."
    ::= { hh3cDot11APRxStatisEntry 4 }

hh3cDot11RxMcastFrameCnt OBJECT-TYPE
    SYNTAX      Counter32
    MAX-ACCESS  read-only
    STATUS      current
    DESCRIPTION
        "Represents the number of multicast frames reception."
    ::= { hh3cDot11APRxStatisEntry 5 }

hh3cDot11RxDiscardFrameCnt OBJECT-TYPE
    SYNTAX      Counter32
    MAX-ACCESS  read-only
    STATUS      current
    DESCRIPTION
        "Represents the number of frames discarded by AP."
    ::= { hh3cDot11APRxStatisEntry 6 }

hh3cDot11RxFragCnt OBJECT-TYPE
    SYNTAX      Counter32
    MAX-ACCESS  read-only
    STATUS      current
    DESCRIPTION
        "Represents the number of frame fragments reception."
    ::= { hh3cDot11APRxStatisEntry 7 }

hh3cDot11RxFcsErrCnt OBJECT-TYPE
    SYNTAX      Counter32
    MAX-ACCESS  read-only
    STATUS      current
    DESCRIPTION
        "Represents the number of FCS error frames reception."
    ::= { hh3cDot11APRxStatisEntry 8 }

hh3cDot11RxFrameBytes OBJECT-TYPE
    SYNTAX      Counter32
    MAX-ACCESS  read-only
    STATUS      current
    DESCRIPTION
        "Represents the bytes of frames reception."
    ::= { hh3cDot11APRxStatisEntry 9 }

hh3cDot11RxUcastFrameBytes OBJECT-TYPE
    SYNTAX      Counter32
    MAX-ACCESS  read-only
    STATUS      current
    DESCRIPTION
        "Represents the bytes of unicast frames reception."
    ::= { hh3cDot11APRxStatisEntry 10 }

hh3cDot11RxBcastFrameBytes OBJECT-TYPE
    SYNTAX      Counter32
    MAX-ACCESS  read-only
    STATUS      current
    DESCRIPTION
        "Represents the bytes of broadcast frames reception."
    ::= { hh3cDot11APRxStatisEntry 11 }

hh3cDot11RxMcastFrameBytes OBJECT-TYPE
    SYNTAX      Counter32
    MAX-ACCESS  read-only
    STATUS      current
    DESCRIPTION
        "Represents the bytes of multicast frames reception."
    ::= { hh3cDot11APRxStatisEntry 12 }

hh3cDot11RxDiscardFrameBytes OBJECT-TYPE
    SYNTAX      Counter32
    MAX-ACCESS  read-only
    STATUS      current
    DESCRIPTION
        "Represents the bytes of frames discarded by AP."
    ::= { hh3cDot11APRxStatisEntry 13 }

hh3cDot11RxMgmtFrameCnt OBJECT-TYPE
    SYNTAX      Counter32
    MAX-ACCESS  read-only
    STATUS      current
    DESCRIPTION
        "Represents the number of management frames reception."
    ::= { hh3cDot11APRxStatisEntry 14 }

hh3cDot11RxCtrlFrameCnt OBJECT-TYPE
    SYNTAX      Counter32
    MAX-ACCESS  read-only
    STATUS      current
    DESCRIPTION
        "Represents the number of control frames reception."
    ::= { hh3cDot11APRxStatisEntry 15 }

hh3cDot11RxDataFrameCnt OBJECT-TYPE
    SYNTAX      Counter32
    MAX-ACCESS  read-only
    STATUS      current
    DESCRIPTION
        "Represents the number of data frames reception."
    ::= { hh3cDot11APRxStatisEntry 16 }

hh3cDot11RxDecryptErrorCnt OBJECT-TYPE
    SYNTAX      Counter32
    MAX-ACCESS  read-only
    STATUS      current
    DESCRIPTION
        "Represents the number of decryption error."
    ::= { hh3cDot11APRxStatisEntry 17 }

hh3cDot11RxAuthenFrameCnt OBJECT-TYPE
    SYNTAX      Counter32
    MAX-ACCESS  read-only
    STATUS      current
    DESCRIPTION
        "Represents the number of authentication frame reception."
    ::= { hh3cDot11APRxStatisEntry 18 }

hh3cDot11RxAssociateFrameCnt OBJECT-TYPE
    SYNTAX      Counter32
    MAX-ACCESS  read-only
    STATUS      current
    DESCRIPTION
        "Represents the number of associate frame reception."
    ::= { hh3cDot11APRxStatisEntry 19 }

hh3cDot11RxFrameErrorRatio OBJECT-TYPE
    SYNTAX      Integer32
    UNITS       "onepercent"
    MAX-ACCESS  read-only
    STATUS      current
    DESCRIPTION
        "Represents the ratio of error frame."
    ::= { hh3cDot11APRxStatisEntry 20 }

hh3cDot11RxPhyErrorCnt OBJECT-TYPE
    SYNTAX      Counter32
    MAX-ACCESS  read-only
    STATUS      current
    DESCRIPTION
        "Represents the number of physical reception error."
    ::= { hh3cDot11APRxStatisEntry 21 }

hh3cDot11RxMICErrorCnt OBJECT-TYPE
    SYNTAX      Counter32
    MAX-ACCESS  read-only
    STATUS      current
    DESCRIPTION
        "Represents the number of MIC verification error."
    ::= { hh3cDot11APRxStatisEntry 22 }

hh3cDot11RxDataFrameBytes OBJECT-TYPE
    SYNTAX      Counter32
    MAX-ACCESS  read-only
    STATUS      current
    DESCRIPTION
        "Represents the bytes of data frames reception."
    ::= { hh3cDot11APRxStatisEntry 23 }

hh3cDot11RadioRxAverSnr OBJECT-TYPE
    SYNTAX      Integer32
    MAX-ACCESS  read-only
    STATUS      current
    DESCRIPTION
        "Represents the average signal noise rate of this radio."
    ::= { hh3cDot11APRxStatisEntry 24 }

hh3cDot11RxPayloadBytes OBJECT-TYPE
    SYNTAX      Counter32
    MAX-ACCESS  read-only
    STATUS      current
    DESCRIPTION
        "Represents the payload bytes of data frames reception."
    ::= { hh3cDot11APRxStatisEntry 25 }

hh3cDot11RxTrafficSpeed OBJECT-TYPE
    SYNTAX      Integer32
    UNITS       "byte/s"
    MAX-ACCESS  read-only
    STATUS      current
    DESCRIPTION
        "Represents the bytes of frames reception per second."
    ::= { hh3cDot11APRxStatisEntry 26 }

hh3cDot11RxUcastDataFrameCnt OBJECT-TYPE
    SYNTAX      Counter64
    MAX-ACCESS  read-only
    STATUS      current
    DESCRIPTION
        "Represents the number of unicast data frames reception."
    ::= { hh3cDot11APRxStatisEntry 27 }

hh3cDot11RxNUcastDataFrameCnt OBJECT-TYPE
    SYNTAX      Counter64
    MAX-ACCESS  read-only
    STATUS      current
    DESCRIPTION
        "Represents the number of non-unicast data frames reception."
    ::= { hh3cDot11APRxStatisEntry 28 }

hh3cDot11RxTotalDiscardFrameCnt OBJECT-TYPE
    SYNTAX      Counter64
    MAX-ACCESS  read-only
    STATUS      current
    DESCRIPTION
        "Represents the number of total frames discarded by radio."
    ::= { hh3cDot11APRxStatisEntry 29 }

hh3cDot11RxTotalIPCheckErrPacketCnt OBJECT-TYPE
    SYNTAX      Counter64
    MAX-ACCESS  read-only
    STATUS      current
    DESCRIPTION
        "Represents the total number of IP checksum error packets
        received through the current radio."
    ::= { hh3cDot11APRxStatisEntry 30 }

hh3cDot11RxSignalStrengthPacketCntCM OBJECT-TYPE
    SYNTAX      OCTET STRING
    MAX-ACCESS  read-only
    STATUS      current
    DESCRIPTION
        "Represents the count of received packets according to signal strength."
    ::= { hh3cDot11APRxStatisEntry 31 }

hh3cDot11RxDataFrameCntCM OBJECT-TYPE
    SYNTAX      Counter32
    MAX-ACCESS  read-only
    STATUS      current
    DESCRIPTION
        "Represents the number of received data frames, excluding retransmitted
        frames."
    ::= { hh3cDot11APRxStatisEntry 32 }

hh3cDot11RxTotalFrameCnt OBJECT-TYPE
    SYNTAX      Counter64
    MAX-ACCESS  read-only
    STATUS      current
    DESCRIPTION
        "Represents the total number of packets
        received through the current radio."
    ::= { hh3cDot11APRxStatisEntry 33 }

-- *****************************************************************************
-- *  End of hh3cDot11APRxStatisTable Definition
-- *****************************************************************************

-- *****************************************************************************
-- *  hh3cDot11APTxStatisTable Definition
-- *****************************************************************************
hh3cDot11APTxStatisTable OBJECT-TYPE
    SYNTAX      SEQUENCE OF Hh3cDot11APTxStatisEntry
    MAX-ACCESS  not-accessible
    STATUS      current
    DESCRIPTION
        "The table will provide the transmission statistic for a
        specific radio of AP."
    ::= { hh3cDot11APStatisGroup 2 }

hh3cDot11APTxStatisEntry OBJECT-TYPE
    SYNTAX      Hh3cDot11APTxStatisEntry
    MAX-ACCESS  not-accessible
    STATUS      current
    DESCRIPTION
        "Each entry of the table will provide the statistic data for
        each radio of a specific AP."
    INDEX
        {
            hh3cDot11CurAPID,
            hh3cDot11RadioID
        }
    ::= { hh3cDot11APTxStatisTable 1 }

Hh3cDot11APTxStatisEntry ::= SEQUENCE
    {
        hh3cDot11TxFragCnt              Counter32,
        hh3cDot11FailedCnt              Counter32,
        hh3cDot11RetryCnt               Counter32,
        hh3cDot11MultiRetryCnt          Counter32,
        hh3cDot11RtsSuccessCnt          Counter32,
        hh3cDot11RtsFailCnt             Counter32,
        hh3cDot11AckFailCnt             Counter32,
        hh3cDot11TxFrameCnt             Counter32,
        hh3cDot11TxUcastFrameCnt        Counter32,
        hh3cDot11TxBcastFrameCnt        Counter32,
        hh3cDot11TxMcastFrameCnt        Counter32,
        hh3cDot11TxDiscardFrameCnt      Counter32,
        hh3cDot11TxFrameBytes           Counter32,
        hh3cDot11TxUcastFrameBytes      Counter32,
        hh3cDot11TxBcastFrameBytes      Counter32,
        hh3cDot11TxMcastFrameBytes      Counter32,
        hh3cDot11TxDiscardFrameBytes    Counter32,
        hh3cDot11TxAuthenFrameCnt       Counter32,
        hh3cDot11TxAssociateFrameCnt    Counter32,
        hh3cDot11TxFrameRetryRatio      Integer32,
        hh3cDot11TxDataFrameCnt         Counter32,
        hh3cDot11TxDataFrameBytes       Counter32,
        hh3cDot11TxMSDUCnt              Counter32,
        hh3cDot11TxDiscardMSDUCnt       Counter32,
        hh3cDot11RetryMSDUCnt           Counter32,
        hh3cDot11TxPayloadBytes         Counter32,
        hh3cDot11TxTrafficSpeed         Integer32,
        hh3cDot11TxErrFrameRatio        Integer32,
        hh3cDot11TxFrameRate            Integer32,
        hh3cDot11TxMgtFrameCnt          Counter32,
        hh3cDot11TxCtrlFrameCnt         Counter32,
        hh3cDot11TxMACErrCnt            Counter32,
        hh3cDot11TxErrFrameCnt          Counter32,
        hh3cDot11TxUcastDataFrameCnt    Counter64,
        hh3cDot11TxNUcastDataFrameCnt   Counter64,
        hh3cDot11TxTotalFrameCnt        Counter64
    }

hh3cDot11TxFragCnt OBJECT-TYPE
    SYNTAX      Counter32
    MAX-ACCESS  read-only
    STATUS      current
    DESCRIPTION
        "Represents the number of fragmented frames transmission."
    ::= { hh3cDot11APTxStatisEntry 1 }

hh3cDot11FailedCnt OBJECT-TYPE
    SYNTAX      Counter32
    MAX-ACCESS  read-only
    STATUS      current
    DESCRIPTION
        "Represents the number of transmission failures."
    ::= { hh3cDot11APTxStatisEntry 2 }

hh3cDot11RetryCnt OBJECT-TYPE
    SYNTAX      Counter32
    MAX-ACCESS  read-only
    STATUS      current
    DESCRIPTION
        "Represents the number of transmit retries."
    ::= { hh3cDot11APTxStatisEntry 3 }

hh3cDot11MultiRetryCnt OBJECT-TYPE
    SYNTAX      Counter32
    MAX-ACCESS  read-only
    STATUS      current
    DESCRIPTION
        "Represents the number of transmits that required more than
        one retry."
    ::= { hh3cDot11APTxStatisEntry 4 }

hh3cDot11RtsSuccessCnt OBJECT-TYPE
    SYNTAX      Counter32
    MAX-ACCESS  read-only
    STATUS      current
    DESCRIPTION
        "Represents the number of successful RTS (Request to send)
        transmission."
    ::= { hh3cDot11APTxStatisEntry 5 }

hh3cDot11RtsFailCnt OBJECT-TYPE
    SYNTAX      Counter32
    MAX-ACCESS  read-only
    STATUS      current
    DESCRIPTION
        "Represents the number of RTS transmission failures."
    ::= { hh3cDot11APTxStatisEntry 6 }

hh3cDot11AckFailCnt OBJECT-TYPE
    SYNTAX      Counter32
    MAX-ACCESS  read-only
    STATUS      current
    DESCRIPTION
        "Represents the number of acknowledgement failures."
    ::= { hh3cDot11APTxStatisEntry 7 }

hh3cDot11TxFrameCnt OBJECT-TYPE
    SYNTAX      Counter32
    MAX-ACCESS  read-only
    STATUS      current
    DESCRIPTION
        "Represents the total number of frames transmission."
    ::= { hh3cDot11APTxStatisEntry 8 }

hh3cDot11TxUcastFrameCnt OBJECT-TYPE
    SYNTAX      Counter32
    MAX-ACCESS  read-only
    STATUS      current
    DESCRIPTION
        "Represents the number of unicast frames transmission."
    ::= { hh3cDot11APTxStatisEntry 9 }

hh3cDot11TxBcastFrameCnt OBJECT-TYPE
    SYNTAX      Counter32
    MAX-ACCESS  read-only
    STATUS      current
    DESCRIPTION
        "Represents the number of broadcast frames transmission."
    ::= { hh3cDot11APTxStatisEntry 10 }

hh3cDot11TxMcastFrameCnt OBJECT-TYPE
    SYNTAX      Counter32
    MAX-ACCESS  read-only
    STATUS      current
    DESCRIPTION
        "Represents the number of multicast frames transmission."
    ::= { hh3cDot11APTxStatisEntry 11 }

hh3cDot11TxDiscardFrameCnt OBJECT-TYPE
    SYNTAX      Counter32
    MAX-ACCESS  read-only
    STATUS      current
    DESCRIPTION
        "Represents the number of frames discarded by AP."
    ::= { hh3cDot11APTxStatisEntry 12 }

hh3cDot11TxFrameBytes OBJECT-TYPE
    SYNTAX      Counter32
    MAX-ACCESS  read-only
    STATUS      current
    DESCRIPTION
        "Represents the total bytes of frames transmission."
    ::= { hh3cDot11APTxStatisEntry 13 }

hh3cDot11TxUcastFrameBytes OBJECT-TYPE
    SYNTAX      Counter32
    MAX-ACCESS  read-only
    STATUS      current
    DESCRIPTION
        "Represents the bytes of unicast frames transmission."
    ::= { hh3cDot11APTxStatisEntry 14 }

hh3cDot11TxBcastFrameBytes OBJECT-TYPE
    SYNTAX      Counter32
    MAX-ACCESS  read-only
    STATUS      current
    DESCRIPTION
        "Represents the bytes of broadcast frames transmission."
    ::= { hh3cDot11APTxStatisEntry 15 }

hh3cDot11TxMcastFrameBytes OBJECT-TYPE
    SYNTAX      Counter32
    MAX-ACCESS  read-only
    STATUS      current
    DESCRIPTION
        "Represents the bytes of multicast frames transmission."
    ::= { hh3cDot11APTxStatisEntry 16 }

hh3cDot11TxDiscardFrameBytes OBJECT-TYPE
    SYNTAX      Counter32
    MAX-ACCESS  read-only
    STATUS      current
    DESCRIPTION
        "Represents the bytes of discarded frames transmission."
    ::= { hh3cDot11APTxStatisEntry 17 }

hh3cDot11TxAuthenFrameCnt OBJECT-TYPE
    SYNTAX      Counter32
    MAX-ACCESS  read-only
    STATUS      current
    DESCRIPTION
        "Represents the number of authentication frame transmission."
    ::= { hh3cDot11APTxStatisEntry 18 }

hh3cDot11TxAssociateFrameCnt OBJECT-TYPE
    SYNTAX      Counter32
    MAX-ACCESS  read-only
    STATUS      current
    DESCRIPTION
        "Represents the number of associate frame transmission."
    ::= { hh3cDot11APTxStatisEntry 19 }

hh3cDot11TxFrameRetryRatio OBJECT-TYPE
    SYNTAX      Integer32
    UNITS       "onepercent"
    MAX-ACCESS  read-only
    STATUS      current
    DESCRIPTION
        "Represents the ratio of retry frame."
    ::= { hh3cDot11APTxStatisEntry 20 }

hh3cDot11TxDataFrameCnt OBJECT-TYPE
    SYNTAX      Counter32
    MAX-ACCESS  read-only
    STATUS      current
    DESCRIPTION
        "Represents the number of data frame transmission."
    ::= { hh3cDot11APTxStatisEntry 21 }

hh3cDot11TxDataFrameBytes OBJECT-TYPE
    SYNTAX      Counter32
    MAX-ACCESS  read-only
    STATUS      current
    DESCRIPTION
        "Represents the bytes of data frame transmission."
    ::= { hh3cDot11APTxStatisEntry 22 }

hh3cDot11TxMSDUCnt OBJECT-TYPE
    SYNTAX      Counter32
    MAX-ACCESS  read-only
    STATUS      current
    DESCRIPTION
        "Represents the total number of MSDU transmission."
    ::= { hh3cDot11APTxStatisEntry 23 }

hh3cDot11TxDiscardMSDUCnt OBJECT-TYPE
    SYNTAX      Counter32
    MAX-ACCESS  read-only
    STATUS      current
    DESCRIPTION
        "Represents the number of discarded MSDU transmission."
    ::= { hh3cDot11APTxStatisEntry 24 }

hh3cDot11RetryMSDUCnt OBJECT-TYPE
    SYNTAX      Counter32
    MAX-ACCESS  read-only
    STATUS      current
    DESCRIPTION
        "Represents the number of retransfer MSDU."
    ::= { hh3cDot11APTxStatisEntry 25 }

hh3cDot11TxPayloadBytes OBJECT-TYPE
    SYNTAX      Counter32
    MAX-ACCESS  read-only
    STATUS      current
    DESCRIPTION
        "Represents the payload bytes of data frames transmission."
    ::= { hh3cDot11APTxStatisEntry 26 }

hh3cDot11TxTrafficSpeed OBJECT-TYPE
    SYNTAX      Integer32
    UNITS       "byte/s"
    MAX-ACCESS  read-only
    STATUS      current
    DESCRIPTION
        "Represents the bytes of frames transmission per second."
    ::= { hh3cDot11APTxStatisEntry 27 }

hh3cDot11TxErrFrameRatio OBJECT-TYPE
    SYNTAX      Integer32
    UNITS       "onepercent"
    MAX-ACCESS  read-only
    STATUS      current
    DESCRIPTION
        "Represents the ratio of error frame."
    ::= { hh3cDot11APTxStatisEntry 28 }

hh3cDot11TxFrameRate OBJECT-TYPE
    SYNTAX      Integer32
    MAX-ACCESS  read-only
    STATUS      current
    DESCRIPTION
        "Represents the count of frames transmission per second."
    ::= { hh3cDot11APTxStatisEntry 29 }

hh3cDot11TxMgtFrameCnt OBJECT-TYPE
    SYNTAX      Counter32
    MAX-ACCESS  read-only
    STATUS      current
    DESCRIPTION
        "Represents the number of transmitted management frames."
    ::= { hh3cDot11APTxStatisEntry 30 }

hh3cDot11TxCtrlFrameCnt OBJECT-TYPE
    SYNTAX      Counter32
    MAX-ACCESS  read-only
    STATUS      current
    DESCRIPTION
        "Represents the number of transmission control frames."
    ::= { hh3cDot11APTxStatisEntry 31 }
hh3cDot11TxMACErrCnt OBJECT-TYPE
    SYNTAX      Counter32
    MAX-ACCESS  read-only
    STATUS      current
    DESCRIPTION
        "Represents the count of MAC error frame."
    ::= { hh3cDot11APTxStatisEntry 32 }

hh3cDot11TxErrFrameCnt OBJECT-TYPE
    SYNTAX      Counter32
    MAX-ACCESS  read-only
    STATUS      current
    DESCRIPTION
        "Represents the count of error frame."
    ::= { hh3cDot11APTxStatisEntry 33 }

hh3cDot11TxUcastDataFrameCnt OBJECT-TYPE
    SYNTAX      Counter64
    MAX-ACCESS  read-only
    STATUS      current
    DESCRIPTION
        "Represents the number of unicast data frames transmission."
    ::= { hh3cDot11APTxStatisEntry 34 }

hh3cDot11TxNUcastDataFrameCnt OBJECT-TYPE
    SYNTAX      Counter64
    MAX-ACCESS  read-only
    STATUS      current
    DESCRIPTION
        "Represents the number of non-unicast data frames transmission."
    ::= { hh3cDot11APTxStatisEntry 35 }

hh3cDot11TxTotalFrameCnt OBJECT-TYPE
    SYNTAX      Counter64
    MAX-ACCESS  read-only
    STATUS      current
    DESCRIPTION
        "Represents the number of total frames transmission."
    ::= { hh3cDot11APTxStatisEntry 36 }

-- *****************************************************************************
-- *  End of hh3cDot11APTxStatisTable Definition
-- *****************************************************************************

-- *****************************************************************************
-- *  hh3cDot11APAssocStatisTable Definition
-- *****************************************************************************
hh3cDot11APAssocStatisTable OBJECT-TYPE
    SYNTAX      SEQUENCE OF Hh3cDot11APAssocStatisEntry
    MAX-ACCESS  not-accessible
    STATUS      current
    DESCRIPTION
        "The table will provide the station association statistic for AP."
    ::= { hh3cDot11APStatisGroup 3 }

hh3cDot11APAssocStatisEntry OBJECT-TYPE
    SYNTAX      Hh3cDot11APAssocStatisEntry
    MAX-ACCESS  not-accessible
    STATUS      current
    DESCRIPTION
        "Each entry of the table will provide the statistic data of station
        association for AP."
    INDEX
        {
            hh3cDot11CurAPID
        }
    ::= { hh3cDot11APAssocStatisTable 1 }

Hh3cDot11APAssocStatisEntry ::= SEQUENCE
    {
        hh3cDot11ApStationAssocSum          Counter32,
        hh3cDot11ApStationAssocFailSum      Counter32,
        hh3cDot11ApStationReassocSum        Counter32,
        hh3cDot11ApStationAssocRejectSum    Counter32,
        hh3cDot11ApStationExDeAuthenSum     Counter32,
        hh3cDot11ApStationCurAssocSum       Integer32,
        hh3cDot11ApStaCurAuthSuccSum        Integer32,
        hh3cDot11AllStationUpSumTime        Counter32,
        hh3cDot11ApStationAssocReqSum       Counter32,
        hh3cDot11AllStationUpSumTimeTicks   TimeTicks,
        hh3cDot11ApStationReassocReqSum     Counter32,
        hh3cDot11ApStationReassocFailSum    Counter32,
        hh3cDot11ApStationAssocRespSum       Counter32
    }

hh3cDot11ApStationAssocSum OBJECT-TYPE
    SYNTAX      Counter32
    MAX-ACCESS  read-only
    STATUS      current
    DESCRIPTION
        "Represents the total number of station association
        with this AP."
    ::= { hh3cDot11APAssocStatisEntry 1 }

hh3cDot11ApStationAssocFailSum OBJECT-TYPE
    SYNTAX      Counter32
    MAX-ACCESS  read-only
    STATUS      current
    DESCRIPTION
        "Represents the total number of station
        association failure with this AP."
    ::= { hh3cDot11APAssocStatisEntry 2 }

hh3cDot11ApStationReassocSum OBJECT-TYPE
    SYNTAX      Counter32
    MAX-ACCESS  read-only
    STATUS      current
    DESCRIPTION
        "Represents the total number of station reassociation with this AP."
    ::= { hh3cDot11APAssocStatisEntry 3 }

hh3cDot11ApStationAssocRejectSum OBJECT-TYPE
    SYNTAX      Counter32
    MAX-ACCESS  read-only
    STATUS      current
    DESCRIPTION
        "Represents the total number of station association rejected
        on account of resource limit with this AP."
    ::= { hh3cDot11APAssocStatisEntry 4 }

hh3cDot11ApStationExDeAuthenSum OBJECT-TYPE
    SYNTAX      Counter32
    MAX-ACCESS  read-only
    STATUS      current
    DESCRIPTION
        "Represents the total number of exceptional station deauthentication
        (Without sending a deauthentication to AP) with this AP."
    ::= { hh3cDot11APAssocStatisEntry 5 }

hh3cDot11ApStationCurAssocSum OBJECT-TYPE
    SYNTAX      Integer32
    MAX-ACCESS  read-only
    STATUS      current
    DESCRIPTION
        "Represents the total number of current associated stations
        with this AP."
    ::= { hh3cDot11APAssocStatisEntry 6 }

hh3cDot11ApStaCurAuthSuccSum OBJECT-TYPE
    SYNTAX      Integer32
    MAX-ACCESS  read-only
    STATUS      current
    DESCRIPTION
        "Represents the successful number of station authentication
        with this AP."
    ::= { hh3cDot11APAssocStatisEntry 7 }

hh3cDot11AllStationUpSumTime OBJECT-TYPE
    SYNTAX      Counter32
    UNITS       "minute"
    MAX-ACCESS  read-only
    STATUS      current
    DESCRIPTION
        "Represents the sum of duration of all stations which associate with
         this AP."
    ::= { hh3cDot11APAssocStatisEntry 8 }

hh3cDot11ApStationAssocReqSum OBJECT-TYPE
    SYNTAX      Counter32
    MAX-ACCESS  read-only
    STATUS      current
    DESCRIPTION
        "Represents the number of station association request with this AP."
    ::= { hh3cDot11APAssocStatisEntry 9 }

hh3cDot11AllStationUpSumTimeTicks OBJECT-TYPE
    SYNTAX      TimeTicks
    MAX-ACCESS  read-only
    STATUS      current
    DESCRIPTION
        "Represents the sum of duration of all stations which associate with
         this AP."
    ::= { hh3cDot11APAssocStatisEntry 10 }

hh3cDot11ApStationReassocReqSum OBJECT-TYPE
    SYNTAX      Counter32
    MAX-ACCESS  read-only
    STATUS      current
    DESCRIPTION
        "Represents the total number of station reassociation request
        with this AP."
    ::= { hh3cDot11APAssocStatisEntry 11 }

hh3cDot11ApStationReassocFailSum OBJECT-TYPE
    SYNTAX      Counter32
    MAX-ACCESS  read-only
    STATUS      current
    DESCRIPTION
        "Represents the total number of station reassociation failure
        with this AP."
    ::= { hh3cDot11APAssocStatisEntry 12 }

hh3cDot11ApStationAssocRespSum OBJECT-TYPE
    SYNTAX      Counter32
    MAX-ACCESS  read-only
    STATUS      current
    DESCRIPTION
        "Represents the number of this AP response with station association."
    ::= { hh3cDot11APAssocStatisEntry 13 }

-- *****************************************************************************
-- *  End of hh3cDot11APAssocStatisTable Definition
-- *****************************************************************************

-- *****************************************************************************
-- *  hh3cDot11BSSRxStatisTable Definition
-- *****************************************************************************
hh3cDot11BSSRxStatisTable OBJECT-TYPE
    SYNTAX      SEQUENCE OF Hh3cDot11BSSRxStatisEntry
    MAX-ACCESS  not-accessible
    STATUS      current
    DESCRIPTION
        "The table will provide the reception statistic for a
        specific BSS on a radio."
    ::= { hh3cDot11APStatisGroup 4 }

hh3cDot11BSSRxStatisEntry OBJECT-TYPE
    SYNTAX      Hh3cDot11BSSRxStatisEntry
    MAX-ACCESS  not-accessible
    STATUS      current
    DESCRIPTION
        "Each entry of the table will provide the statistic data for
        each BSS on a specific radio."
    INDEX
        {
            hh3cDot11CurAPID,
            hh3cDot11RadioID,
            hh3cDot11WlanID
        }
    ::= { hh3cDot11BSSRxStatisTable 1 }

Hh3cDot11BSSRxStatisEntry ::= SEQUENCE
    {
        hh3cDot11BSSRxFrameCnt             Counter32,
        hh3cDot11BSSRxFrameBytes           Counter32,
        hh3cDot11BSSRxDataFrameCnt         Counter32,
        hh3cDot11BSSRxDataFrameBytes       Counter32,
        hh3cDot11BSSRxAssociateFrameCnt    Counter32,
        hh3cDot11BSSRxFrameErrorRatio      Integer32,
        hh3cDot11BSSRxPayloadBytes         Counter32,
        hh3cDot11BSSRxUniFrameCnt          Counter32,
        hh3cDot11BSSRxNonUniFrameCnt       Integer32,
        hh3cDot11BSSRxAuthenFrameCnt       Counter32,
        hh3cDot11BSSRxFrameErrCntCM        Counter32
    }

hh3cDot11BSSRxFrameCnt OBJECT-TYPE
    SYNTAX      Counter32
    MAX-ACCESS  read-only
    STATUS      current
    DESCRIPTION
        "Represents the number of frames reception with this BSS."
    ::= { hh3cDot11BSSRxStatisEntry 1 }

hh3cDot11BSSRxFrameBytes OBJECT-TYPE
    SYNTAX      Counter32
    MAX-ACCESS  read-only
    STATUS      current
    DESCRIPTION
        "Represents the bytes of frames reception with this BSS."
    ::= { hh3cDot11BSSRxStatisEntry 2 }

hh3cDot11BSSRxDataFrameCnt OBJECT-TYPE
    SYNTAX      Counter32
    MAX-ACCESS  read-only
    STATUS      current
    DESCRIPTION
        "Represents the number of data frames reception with this BSS."
    ::= { hh3cDot11BSSRxStatisEntry 3 }

hh3cDot11BSSRxDataFrameBytes OBJECT-TYPE
    SYNTAX      Counter32
    MAX-ACCESS  read-only
    STATUS      current
    DESCRIPTION
        "Represents the bytes of data frames reception with this BSS."
    ::= { hh3cDot11BSSRxStatisEntry 4 }

hh3cDot11BSSRxAssociateFrameCnt OBJECT-TYPE
    SYNTAX      Counter32
    MAX-ACCESS  read-only
    STATUS      current
    DESCRIPTION
        "Represents the number of associate frames reception with this BSS."
    ::= { hh3cDot11BSSRxStatisEntry 5 }

hh3cDot11BSSRxFrameErrorRatio OBJECT-TYPE
    SYNTAX      Integer32
    UNITS       "percent"
    MAX-ACCESS  read-only
    STATUS      current
    DESCRIPTION
        "Represents the ratio of error frames reception with this BSS."
    ::= { hh3cDot11BSSRxStatisEntry 6 }

hh3cDot11BSSRxPayloadBytes OBJECT-TYPE
    SYNTAX      Counter32
    MAX-ACCESS  read-only
    STATUS      current
    DESCRIPTION
        "Represents the payload bytes of data frames reception with this BSS."
    ::= { hh3cDot11BSSRxStatisEntry 7 }

hh3cDot11BSSRxUniFrameCnt OBJECT-TYPE
    SYNTAX      Counter32
    MAX-ACCESS  read-only
    STATUS      current
    DESCRIPTION
        "Represents the count of unicast frames received."
    ::= { hh3cDot11BSSRxStatisEntry 8 }

hh3cDot11BSSRxNonUniFrameCnt  OBJECT-TYPE
    SYNTAX      Integer32
    MAX-ACCESS  read-only
    STATUS      current
    DESCRIPTION
        "Represents the count of non-unicast frames received."
    ::= { hh3cDot11BSSRxStatisEntry 9 }

hh3cDot11BSSRxAuthenFrameCnt OBJECT-TYPE
    SYNTAX      Counter32
    MAX-ACCESS  read-only
    STATUS      current
    DESCRIPTION
        "Represents the count of authentication frames received."
    ::= { hh3cDot11BSSRxStatisEntry 10 }

hh3cDot11BSSRxFrameErrCntCM OBJECT-TYPE
    SYNTAX      Counter32
    MAX-ACCESS  read-only
    STATUS      current
    DESCRIPTION
        "Represents the count of error authentication frames received."
    ::= { hh3cDot11BSSRxStatisEntry 11 }

-- *****************************************************************************
-- *  End of hh3cDot11BSSRxStatisTable Definition
-- *****************************************************************************

-- *****************************************************************************
-- *  hh3cDot11BSSTxStatisTable Definition
-- *****************************************************************************
hh3cDot11BSSTxStatisTable OBJECT-TYPE
    SYNTAX      SEQUENCE OF Hh3cDot11BSSTxStatisEntry
    MAX-ACCESS  not-accessible
    STATUS      current
    DESCRIPTION
        "The table will provide the transmission statistic for a
        specific BSS on a radio."
    ::= { hh3cDot11APStatisGroup 5 }

hh3cDot11BSSTxStatisEntry OBJECT-TYPE
    SYNTAX      Hh3cDot11BSSTxStatisEntry
    MAX-ACCESS  not-accessible
    STATUS      current
    DESCRIPTION
        "Each entry of the table will provide the statistic data for
        each BSS on a specific radio."
    INDEX
        {
            hh3cDot11CurAPID,
            hh3cDot11RadioID,
            hh3cDot11WlanID
        }
    ::= { hh3cDot11BSSTxStatisTable 1 }

Hh3cDot11BSSTxStatisEntry ::= SEQUENCE
    {
        hh3cDot11BSSTxFrameCnt             Counter32,
        hh3cDot11BSSTxFrameBytes           Counter32,
        hh3cDot11BSSTxDataFrameCnt         Counter32,
        hh3cDot11BSSTxDataFrameBytes       Counter32,
        hh3cDot11BSSTxAssociateFrameCnt    Counter32,
        hh3cDot11BSSTxPayloadBytes         Counter32,
        hh3cDot11BSSTxRetryCnt             Counter32,
        hh3cDot11BSSTxUniFrameCnt          Counter32,
        hh3cDot11BSSTxNonUniFrameCnt       Integer32,
        hh3cDot11BSSTxAuthenFrameCnt       Counter32,
        hh3cDot11BSSTxFrameErrCntCM        Counter32
    }

hh3cDot11BSSTxFrameCnt OBJECT-TYPE
    SYNTAX      Counter32
    MAX-ACCESS  read-only
    STATUS      current
    DESCRIPTION
        "Represents the total number of frames transmission with this BSS."
    ::= { hh3cDot11BSSTxStatisEntry 1 }

hh3cDot11BSSTxFrameBytes OBJECT-TYPE
    SYNTAX      Counter32
    MAX-ACCESS  read-only
    STATUS      current
    DESCRIPTION
        "Represents the total number of bytes transmission with this BSS."
    ::= { hh3cDot11BSSTxStatisEntry 2 }

hh3cDot11BSSTxDataFrameCnt OBJECT-TYPE
    SYNTAX      Counter32
    MAX-ACCESS  read-only
    STATUS      current
    DESCRIPTION
        "Represents the number of data frame transmission with this BSS."
    ::= { hh3cDot11BSSTxStatisEntry 3 }

hh3cDot11BSSTxDataFrameBytes OBJECT-TYPE
    SYNTAX      Counter32
    MAX-ACCESS  read-only
    STATUS      current
    DESCRIPTION
        "Represents the bytes of data frame transmission with this BSS."
    ::= { hh3cDot11BSSTxStatisEntry 4 }

hh3cDot11BSSTxAssociateFrameCnt OBJECT-TYPE
    SYNTAX      Counter32
    MAX-ACCESS  read-only
    STATUS      current
    DESCRIPTION
        "Represents the number of associate frame transmission with this BSS."
    ::= { hh3cDot11BSSTxStatisEntry 5 }

hh3cDot11BSSTxPayloadBytes OBJECT-TYPE
    SYNTAX      Counter32
    MAX-ACCESS  read-only
    STATUS      current
    DESCRIPTION
        "Represents the payload bytes of data frame transmission with this BSS."
    ::= { hh3cDot11BSSTxStatisEntry 6 }

hh3cDot11BSSTxRetryCnt   OBJECT-TYPE
    SYNTAX      Counter32
    MAX-ACCESS  read-only
    STATUS      current
    DESCRIPTION
        "Represents the count of bytes retransmitted with this BSS."
    ::= { hh3cDot11BSSTxStatisEntry 7 }

hh3cDot11BSSTxUniFrameCnt OBJECT-TYPE
    SYNTAX      Counter32
    MAX-ACCESS  read-only
    STATUS      current
    DESCRIPTION
        "Represents the count of unicast frames transmission with this BSS."
    ::= { hh3cDot11BSSTxStatisEntry 8 }

hh3cDot11BSSTxNonUniFrameCnt OBJECT-TYPE
    SYNTAX      Integer32
    MAX-ACCESS  read-only
    STATUS      current
    DESCRIPTION
        "Represents the number of non-unicast frames transmission with this BSS."
    ::= { hh3cDot11BSSTxStatisEntry 9 }

hh3cDot11BSSTxAuthenFrameCnt OBJECT-TYPE
    SYNTAX      Counter32
    MAX-ACCESS  read-only
    STATUS      current
    DESCRIPTION
        "Represents the count of authentication frames transmission with this BSS."
    ::= { hh3cDot11BSSTxStatisEntry 10 }

hh3cDot11BSSTxFrameErrCntCM OBJECT-TYPE
    SYNTAX      Counter32
    MAX-ACCESS  read-only
    STATUS      current
    DESCRIPTION
        "Represents the count of error authentication frames transmission with this BSS."
    ::= { hh3cDot11BSSTxStatisEntry 11 }

-- *****************************************************************************
-- *  End of hh3cDot11BSSTxStatisTable Definition
-- *****************************************************************************

-- *****************************************************************************
-- *  hh3cDot11BSSAssocStatisTable Definition
-- *****************************************************************************
hh3cDot11BSSAssocStatisTable OBJECT-TYPE
    SYNTAX      SEQUENCE OF Hh3cDot11BSSAssocStatisEntry
    MAX-ACCESS  not-accessible
    STATUS      current
    DESCRIPTION
        "The table will provide the station association statistic for BSS."
    ::= { hh3cDot11APStatisGroup 6 }

hh3cDot11BSSAssocStatisEntry OBJECT-TYPE
    SYNTAX      Hh3cDot11BSSAssocStatisEntry
    MAX-ACCESS  not-accessible
    STATUS      current
    DESCRIPTION
        "Each entry of the table will provide the statistic data of station
        association for BSS."
    INDEX
        {
            hh3cDot11CurAPID,
            hh3cDot11RadioID,
            hh3cDot11WlanID
        }
    ::= { hh3cDot11BSSAssocStatisTable 1 }

Hh3cDot11BSSAssocStatisEntry ::= SEQUENCE
    {
        hh3cDot11BSSStationAssocSum          Counter32,
        hh3cDot11BSSStationAssocFailSum      Counter32,
        hh3cDot11BSSStationReassocSum        Counter32,
        hh3cDot11BSSStationAssocRejectSum    Counter32,
        hh3cDot11BSSStationExDeAssocSum      Counter32,
        hh3cDot11BSSStationCurAssocSum       Integer32,
        hh3cDot11BSSStationAssocReqSum       Counter32,
        hh3cDot11BSSStationCurAuthSum        Integer32
    }

hh3cDot11BSSStationAssocSum OBJECT-TYPE
    SYNTAX      Counter32
    MAX-ACCESS  read-only
    STATUS      current
    DESCRIPTION
        "Represents the total number of station association
        with this BSS."
    ::= { hh3cDot11BSSAssocStatisEntry 1 }

hh3cDot11BSSStationAssocFailSum OBJECT-TYPE
    SYNTAX      Counter32
    MAX-ACCESS  read-only
    STATUS      current
    DESCRIPTION
        "Represents the total number of station
        association failure with this BSS."
    ::= { hh3cDot11BSSAssocStatisEntry 2 }

hh3cDot11BSSStationReassocSum OBJECT-TYPE
    SYNTAX      Counter32
    MAX-ACCESS  read-only
    STATUS      current
    DESCRIPTION
        "Represents the total number of station reassociation
        with this BSS."
    ::= { hh3cDot11BSSAssocStatisEntry 3 }

hh3cDot11BSSStationAssocRejectSum OBJECT-TYPE
    SYNTAX      Counter32
    MAX-ACCESS  read-only
    STATUS      current
    DESCRIPTION
        "Represents the total number of station association rejected
        on account of resource limit with this BSS."
    ::= { hh3cDot11BSSAssocStatisEntry 4 }

hh3cDot11BSSStationExDeAssocSum OBJECT-TYPE
    SYNTAX      Counter32
    MAX-ACCESS  read-only
    STATUS      current
    DESCRIPTION
        "Represents the total number of exceptional station deauthentication
        (Without sending a deauthentication to AP) with this BSS."
    ::= { hh3cDot11BSSAssocStatisEntry 5 }

hh3cDot11BSSStationCurAssocSum OBJECT-TYPE
    SYNTAX      Integer32
    MAX-ACCESS  read-only
    STATUS      current
    DESCRIPTION
        "Represents the total number of current associated stations
        with this BSS."
    ::= { hh3cDot11BSSAssocStatisEntry 6 }

hh3cDot11BSSStationAssocReqSum OBJECT-TYPE
    SYNTAX      Counter32
    MAX-ACCESS  read-only
    STATUS      current
    DESCRIPTION
        "Represents the total number of station association request with
         this BSS."
    ::= { hh3cDot11BSSAssocStatisEntry 7 }

hh3cDot11BSSStationCurAuthSum OBJECT-TYPE
    SYNTAX      Integer32
    MAX-ACCESS  read-only
    STATUS      current
    DESCRIPTION
        "Represents the total number of current associated stations which have
        passed portal or 1x authentication with this BSS."
    ::= { hh3cDot11BSSAssocStatisEntry 8 }

-- *****************************************************************************
-- *  End of hh3cDot11BSSAssocStatisTable Definition
-- *****************************************************************************

-- *****************************************************************************
-- *  hh3cDot11APLinkStatisTable Definition
-- *****************************************************************************
hh3cDot11APLinkStatisTable OBJECT-TYPE
    SYNTAX      SEQUENCE OF Hh3cDot11APLinkStatisEntry
    MAX-ACCESS  not-accessible
    STATUS      current
    DESCRIPTION
        "The table will provide the link statistic for AP."
    ::= { hh3cDot11APStatisGroup 7 }

hh3cDot11APLinkStatisEntry OBJECT-TYPE
    SYNTAX      Hh3cDot11APLinkStatisEntry
    MAX-ACCESS  not-accessible
    STATUS      current
    DESCRIPTION
        "Each entry provides the link statistic of the AP."
    INDEX
        {
            hh3cDot11CurAPID
        }
    ::= { hh3cDot11APLinkStatisTable 1 }

Hh3cDot11APLinkStatisEntry ::= SEQUENCE
    {
        hh3cDot11UpLinkUpDownTimes          Counter32,
        hh3cDot11DownLinkUpDownTimes        Counter32,
        hh3cDot11PrivateSrvRxFrameBytes     Counter64,
        hh3cDot11PrivateSrvTxFrameBytes     Counter64,
        hh3cDot11APInternetAllRxBytes       Counter64,
        hh3cDot11APInternetAllTxBytes       Counter64,
        hh3cDot11APLocalAllRxBytes          Counter64,
        hh3cDot11APLocalAllTxBytes          Counter64
    }

hh3cDot11UpLinkUpDownTimes OBJECT-TYPE
    SYNTAX      Counter32
    MAX-ACCESS  read-only
    STATUS      current
    DESCRIPTION
        "Represents up/down times of uplink interface of the AP."
    ::= { hh3cDot11APLinkStatisEntry 1 }

hh3cDot11DownLinkUpDownTimes OBJECT-TYPE
    SYNTAX      Counter32
    MAX-ACCESS  read-only
    STATUS      current
    DESCRIPTION
        "Represents up/down times of downlink interface of the AP."
    ::= { hh3cDot11APLinkStatisEntry 2 }

hh3cDot11PrivateSrvRxFrameBytes OBJECT-TYPE
    SYNTAX      Counter64
    MAX-ACCESS  read-only
    STATUS      current
    DESCRIPTION
        "Traffic bytes received from private services."
    ::= { hh3cDot11APLinkStatisEntry 3 }

hh3cDot11PrivateSrvTxFrameBytes OBJECT-TYPE
    SYNTAX      Counter64
    MAX-ACCESS  read-only
    STATUS      current
    DESCRIPTION
        "Traffic bytes sent to private services."
    ::= { hh3cDot11APLinkStatisEntry 4 }

hh3cDot11APInternetAllRxBytes OBJECT-TYPE
    SYNTAX      Counter64
    MAX-ACCESS  read-only
    STATUS      current
    DESCRIPTION
        "Internet traffic bytes received from stations."
    ::= { hh3cDot11APLinkStatisEntry 5 }

hh3cDot11APInternetAllTxBytes OBJECT-TYPE
    SYNTAX      Counter64
    MAX-ACCESS  read-only
    STATUS      current
    DESCRIPTION
        "Internet traffic bytes sent to stations."
    ::= { hh3cDot11APLinkStatisEntry 6 }

hh3cDot11APLocalAllRxBytes OBJECT-TYPE
    SYNTAX      Counter64
    MAX-ACCESS  read-only
    STATUS      current
    DESCRIPTION
        "Local traffic bytes received from stations."
    ::= { hh3cDot11APLinkStatisEntry 7 }

hh3cDot11APLocalAllTxBytes OBJECT-TYPE
    SYNTAX      Counter64
    MAX-ACCESS  read-only
    STATUS      current
    DESCRIPTION
        "Local traffic bytes sent to stations."
    ::= { hh3cDot11APLinkStatisEntry 8 }
-- *****************************************************************************
-- *  End of hh3cDot11APLinkStatisTable Definition
-- *****************************************************************************

-- *****************************************************************************
-- *  hh3cDot11RadioAssocStatisTable Definition
-- *****************************************************************************
hh3cDot11RadioAssocStatisTable OBJECT-TYPE
    SYNTAX      SEQUENCE OF Hh3cDot11RadioAssocStatisEntry
    MAX-ACCESS  not-accessible
    STATUS      current
    DESCRIPTION
        "The table will provide the station association statistic for radio."
    ::= { hh3cDot11APStatisGroup 8 }

hh3cDot11RadioAssocStatisEntry OBJECT-TYPE
    SYNTAX      Hh3cDot11RadioAssocStatisEntry
    MAX-ACCESS  not-accessible
    STATUS      current
    DESCRIPTION
        "Each entry of the table will provide the statistic data of station
        association for radio."
    INDEX
        {
            hh3cDot11CurAPID,
            hh3cDot11RadioID
        }
    ::= { hh3cDot11RadioAssocStatisTable 1 }

Hh3cDot11RadioAssocStatisEntry ::= SEQUENCE
    {
        hh3cDot11RadioStaAssocSum          Counter32,
        hh3cDot11RadioStaAssocFailSum      Counter32,
        hh3cDot11RadioStaReassocSum        Counter32,
        hh3cDot11RadioStaAssocRejectSum    Counter32,
        hh3cDot11RadioStaExDeAssocSum      Counter32,
        hh3cDot11RadioStaCurAssocSum       Integer32
    }

hh3cDot11RadioStaAssocSum OBJECT-TYPE
    SYNTAX      Counter32
    MAX-ACCESS  read-only
    STATUS      current
    DESCRIPTION
        "Represents the total number of station association
        with this radio."
    ::= { hh3cDot11RadioAssocStatisEntry 1 }

hh3cDot11RadioStaAssocFailSum OBJECT-TYPE
    SYNTAX      Counter32
    MAX-ACCESS  read-only
    STATUS      current
    DESCRIPTION
        "Represents the total number of station
        association failure with this radio."
    ::= { hh3cDot11RadioAssocStatisEntry 2 }

hh3cDot11RadioStaReassocSum OBJECT-TYPE
    SYNTAX      Counter32
    MAX-ACCESS  read-only
    STATUS      current
    DESCRIPTION
        "Represents the total number of station re-association
        with this radio."
    ::= { hh3cDot11RadioAssocStatisEntry 3 }

hh3cDot11RadioStaAssocRejectSum OBJECT-TYPE
    SYNTAX      Counter32
    MAX-ACCESS  read-only
    STATUS      current
    DESCRIPTION
        "Represents the total number of station association rejected
        on account of resource limit with this radio."
    ::= { hh3cDot11RadioAssocStatisEntry 4 }

hh3cDot11RadioStaExDeAssocSum OBJECT-TYPE
    SYNTAX      Counter32
    MAX-ACCESS  read-only
    STATUS      current
    DESCRIPTION
        "Represents the total number of exceptional station de-authentication
        (Without sending a de-authentication to AP) with this radio."
    ::= { hh3cDot11RadioAssocStatisEntry 5 }

hh3cDot11RadioStaCurAssocSum OBJECT-TYPE
    SYNTAX      Integer32
    MAX-ACCESS  read-only
    STATUS      current
    DESCRIPTION
        "Represents the total number of current associated stations
        with this radio."
    ::= { hh3cDot11RadioAssocStatisEntry 6 }
-- *****************************************************************************
-- *  End of hh3cDot11RadioAssocStatisTable Definition
-- *****************************************************************************

-- *****************************************************************************
-- *  hh3cDot11RadioMngFrameStatisTable Definition
-- *****************************************************************************
hh3cDot11RadioMngFrameStatisTable OBJECT-TYPE
    SYNTAX      SEQUENCE OF Hh3cDot11RadioMngFrameStatisEntry
    MAX-ACCESS  not-accessible
    STATUS      current
    DESCRIPTION
        "The table will provide the management frame statistic for this radio."
    ::= { hh3cDot11APStatisGroup 9 }

hh3cDot11RadioMngFrameStatisEntry OBJECT-TYPE
    SYNTAX      Hh3cDot11RadioMngFrameStatisEntry
    MAX-ACCESS  not-accessible
    STATUS      current
    DESCRIPTION
        "Each entry of the table will provide the management
        frame statistic for this radio."
    INDEX
        {
            hh3cDot11RadioStatisIndex,
            hh3cDot11MngFrameType
        }
    ::= { hh3cDot11RadioMngFrameStatisTable 1 }

Hh3cDot11RadioMngFrameStatisEntry ::= SEQUENCE
    {
        hh3cDot11RadioStatisIndex            Hh3cDot11RadioElementIndex,
        hh3cDot11MngFrameType                INTEGER,
        hh3cDot11MngFrameCnt                 Counter32
    }

hh3cDot11RadioStatisIndex OBJECT-TYPE
    SYNTAX      Hh3cDot11RadioElementIndex
    MAX-ACCESS  not-accessible
    STATUS      current
    DESCRIPTION
        "Represents index of radio."
    ::= { hh3cDot11RadioMngFrameStatisEntry 1 }

hh3cDot11MngFrameType   OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { hh3cDot11RadioMngFrameStatisEntry 2 }

hh3cDot11MngFrameCnt OBJECT-TYPE
    SYNTAX      Counter32
    MAX-ACCESS  read-only
    STATUS      current
    DESCRIPTION
        "Represents the total number of each type for management frame on this
        radio."
    ::= { hh3cDot11RadioMngFrameStatisEntry 3 }

-- *****************************************************************************
-- *  End of hh3cDot11RadioMngFrameStatisTable Definition
-- *****************************************************************************

-- *****************************************************************************
-- *  hh3cDot11APAuthFailStatisTable Definition
-- *****************************************************************************
hh3cDot11APAuthFailStatisTable OBJECT-TYPE
    SYNTAX      SEQUENCE OF Hh3cDot11APAuthFailStatisEntry
    MAX-ACCESS  not-accessible
    STATUS      current
    DESCRIPTION
        "The table will provide the authentication failure statistic for this
         AP."
    ::= { hh3cDot11APStatisGroup 10 }

hh3cDot11APAuthFailStatisEntry OBJECT-TYPE
    SYNTAX      Hh3cDot11APAuthFailStatisEntry
    MAX-ACCESS  not-accessible
    STATUS      current
    DESCRIPTION
        "Each entry of the table will provide the authentication failure
         statistic for this AP."
    INDEX
        {
            hh3cDot11CurAPID,
            hh3cDot11APAuthFailStatisType
        }
    ::= { hh3cDot11APAuthFailStatisTable 1 }

Hh3cDot11APAuthFailStatisEntry ::= SEQUENCE
    {
        hh3cDot11APAuthFailStatisType                 INTEGER,
        hh3cDot11APAuthFailStatisCnt                  Counter32
    }

hh3cDot11APAuthFailStatisType OBJECT-TYPE
    SYNTAX      INTEGER
        {
            invalidation(1),
            overtime(2),
            rejected(3),
            other(4)
        }
    MAX-ACCESS  not-accessible
    STATUS      current
    DESCRIPTION
        "Represents the type of authentication
        failure with this AP."
    ::= { hh3cDot11APAuthFailStatisEntry 1 }

hh3cDot11APAuthFailStatisCnt   OBJECT-TYPE
    SYNTAX      Counter32
    MAX-ACCESS  read-only
    STATUS      current
    DESCRIPTION
        "Represents the total number of each type for authentication
        failure on this AP."
    ::= { hh3cDot11APAuthFailStatisEntry 2 }

-- *****************************************************************************
-- *  End of hh3cDot11APAuthFailStatisTable Definition
-- *****************************************************************************

-- *****************************************************************************
-- *  hh3cDot11APAssocFailStatisTable Definition
-- *****************************************************************************
hh3cDot11APAssocFailStatisTable OBJECT-TYPE
    SYNTAX      SEQUENCE OF Hh3cDot11APAssocFailStatisEntry
    MAX-ACCESS  not-accessible
    STATUS      current
    DESCRIPTION
        "The table will provide the association failure statistic for
        this AP."
    ::= { hh3cDot11APStatisGroup 11 }

hh3cDot11APAssocFailStatisEntry OBJECT-TYPE
    SYNTAX      Hh3cDot11APAssocFailStatisEntry
    MAX-ACCESS  not-accessible
    STATUS      current
    DESCRIPTION
        "Each entry of the table will provide the association failure statistic
         for this AP."
    INDEX
        {
            hh3cDot11CurAPID,
            hh3cDot11APAssocFailStatisType
        }
    ::= { hh3cDot11APAssocFailStatisTable 1 }

Hh3cDot11APAssocFailStatisEntry ::= SEQUENCE
    {
        hh3cDot11APAssocFailStatisType                 INTEGER,
        hh3cDot11APAssocFailStatisCnt                  Counter32
    }

hh3cDot11APAssocFailStatisType OBJECT-TYPE
    SYNTAX      INTEGER
        {
            invalidation(1),
            overtime(2),
            rejected(3),
            other(4)
        }
    MAX-ACCESS  not-accessible
    STATUS      current
    DESCRIPTION
        "Represents the type of association failure
        with this AP."
    ::= { hh3cDot11APAssocFailStatisEntry 1 }

hh3cDot11APAssocFailStatisCnt   OBJECT-TYPE
    SYNTAX      Counter32
    MAX-ACCESS  read-only
    STATUS      current
    DESCRIPTION
        "Represents the total number of each type for
        association failure on this AP."
    ::= { hh3cDot11APAssocFailStatisEntry 2 }

-- *****************************************************************************
-- *  End of hh3cDot11APAssocFailStatisTable Definition
-- *****************************************************************************

-- *****************************************************************************
-- *  hh3cDot11APReassocStatisTable Definition
-- *****************************************************************************
hh3cDot11APReassocStatisTable OBJECT-TYPE
    SYNTAX      SEQUENCE OF Hh3cDot11APReassocStatisEntry
    MAX-ACCESS  not-accessible
    STATUS      current
    DESCRIPTION
        "The table will provide the re-association statistic for this AP."
    ::= { hh3cDot11APStatisGroup 12 }

hh3cDot11APReassocStatisEntry OBJECT-TYPE
    SYNTAX      Hh3cDot11APReassocStatisEntry
    MAX-ACCESS  not-accessible
    STATUS      current
    DESCRIPTION
        "Each entry of the table will provide the re-association statistic
        for this AP."
    INDEX
        {
            hh3cDot11CurAPID,
            hh3cDot11APReassocStatisType
        }
    ::= { hh3cDot11APReassocStatisTable 1 }

Hh3cDot11APReassocStatisEntry ::= SEQUENCE
    {
        hh3cDot11APReassocStatisType                 INTEGER,
        hh3cDot11APReassocStatisCnt                  Counter32
    }

hh3cDot11APReassocStatisType OBJECT-TYPE
    SYNTAX      INTEGER
        {
            total(1),
            success(2),
            invalidation(3),
            overtime(4),
            rejected(5),
            other(6)
        }
    MAX-ACCESS  not-accessible
    STATUS      current
    DESCRIPTION
        "Represents the type of re-association with this AP."
    ::= { hh3cDot11APReassocStatisEntry 1 }

hh3cDot11APReassocStatisCnt   OBJECT-TYPE
    SYNTAX      Counter32
    MAX-ACCESS  read-only
    STATUS      current
    DESCRIPTION
        "Represents the total number of each type for re-association with
        this AP."
    ::= { hh3cDot11APReassocStatisEntry 2 }

-- *****************************************************************************
-- *  End of hh3cDot11APReassocStatisTable Definition
-- *****************************************************************************

-- *****************************************************************************
-- *  hh3cDot11APUserAuthStatisTable Definition
-- *****************************************************************************
hh3cDot11APUserAuthStatisTable OBJECT-TYPE
    SYNTAX      SEQUENCE OF Hh3cDot11APUserAuthStatisEntry
    MAX-ACCESS  not-accessible
    STATUS      current
    DESCRIPTION
        "The table will provide the user authentication statistic for this AP."
    ::= { hh3cDot11APStatisGroup 13 }

hh3cDot11APUserAuthStatisEntry OBJECT-TYPE
    SYNTAX      Hh3cDot11APUserAuthStatisEntry
    MAX-ACCESS  not-accessible
    STATUS      current
    DESCRIPTION
        "Each entry of the table will provide the user authentication statistic
        for this AP."
    INDEX
        {
            hh3cDot11CurAPID,
            hh3cDot11UserAuthStatisType
        }
    ::= { hh3cDot11APUserAuthStatisTable 1 }

Hh3cDot11APUserAuthStatisEntry ::= SEQUENCE
    {
        hh3cDot11UserAuthStatisType                 INTEGER,
        hh3cDot11UserAuthStatisCnt                  Counter32
    }

hh3cDot11UserAuthStatisType OBJECT-TYPE
    SYNTAX      INTEGER
        {
            total(1),
            success(2),
            keyError(3),
            invalidation(4),
            overtime(5),
            rejected(6),
            other(7)
        }
    MAX-ACCESS  not-accessible
    STATUS      current
    DESCRIPTION
        "Represents the type of user authentication with this AP."
    ::= { hh3cDot11APUserAuthStatisEntry 1 }

hh3cDot11UserAuthStatisCnt   OBJECT-TYPE
    SYNTAX      Counter32
    MAX-ACCESS  read-only
    STATUS      current
    DESCRIPTION
        "Represents the total number of each type for user authentication with
        this AP."
    ::= { hh3cDot11APUserAuthStatisEntry 2 }

-- *****************************************************************************
-- *  End of hh3cDot11APUserAuthStatisTable Definition
-- *****************************************************************************

-- *****************************************************************************
-- *  hh3cDot11APDeauthStatisTable Definition
-- *****************************************************************************
hh3cDot11APDeauthStatisTable OBJECT-TYPE
    SYNTAX      SEQUENCE OF Hh3cDot11APDeauthStatisEntry
    MAX-ACCESS  not-accessible
    STATUS      current
    DESCRIPTION
        "The table will provide the de-authentication statistic for this AP."
    ::= { hh3cDot11APStatisGroup 14 }

hh3cDot11APDeauthStatisEntry OBJECT-TYPE
    SYNTAX      Hh3cDot11APDeauthStatisEntry
    MAX-ACCESS  not-accessible
    STATUS      current
    DESCRIPTION
        "Each entry of the table will provide the de-authentication statistic
         for this AP."
    INDEX
        {
            hh3cDot11CurAPID,
            hh3cDot11APDeauthStatisType
        }
    ::= { hh3cDot11APDeauthStatisTable 1 }

Hh3cDot11APDeauthStatisEntry ::= SEQUENCE
    {
        hh3cDot11APDeauthStatisType                 INTEGER,
        hh3cDot11APDeauthStatisCnt                  Counter32
    }

hh3cDot11APDeauthStatisType OBJECT-TYPE
    SYNTAX      INTEGER
        {
            total(1),
            stationLeaving(2),
            shortResource(3),
            exception(4),
            other(5)
        }
    MAX-ACCESS  not-accessible
    STATUS      current
    DESCRIPTION
        "Represents the type of de-authentication for this AP."
    ::= { hh3cDot11APDeauthStatisEntry 1 }

hh3cDot11APDeauthStatisCnt   OBJECT-TYPE
    SYNTAX      Counter32
    MAX-ACCESS  read-only
    STATUS      current
    DESCRIPTION
        "Represents the total number of each type for de-authentication
         with this AP."
    ::= { hh3cDot11APDeauthStatisEntry 2 }

-- *****************************************************************************
-- *  End of hh3cDot11APDeauthStatisTable Definition
-- *****************************************************************************

-- *****************************************************************************
-- *  hh3cDot11APDeassocStatisTable Definition
-- *****************************************************************************
hh3cDot11APDeassocStatisTable OBJECT-TYPE
    SYNTAX      SEQUENCE OF Hh3cDot11APDeassocStatisEntry
    MAX-ACCESS  not-accessible
    STATUS      current
    DESCRIPTION
        "The table will provide the de-association statistic for this AP."
    ::= { hh3cDot11APStatisGroup 15 }

hh3cDot11APDeassocStatisEntry OBJECT-TYPE
    SYNTAX      Hh3cDot11APDeassocStatisEntry
    MAX-ACCESS  not-accessible
    STATUS      current
    DESCRIPTION
        "Each entry of the table will provide the de-association statistic
         for this AP."
    INDEX
        {
            hh3cDot11CurAPID,
            hh3cDot11APDeassocStatisType
        }
    ::= { hh3cDot11APDeassocStatisTable 1 }

Hh3cDot11APDeassocStatisEntry ::= SEQUENCE
    {
        hh3cDot11APDeassocStatisType                 INTEGER,
        hh3cDot11APDeassocStatisCnt                  Counter32
    }

hh3cDot11APDeassocStatisType OBJECT-TYPE
    SYNTAX      INTEGER
        {
            total(1),
            stationLeaving(2),
            shortResource(3),
            exception(4),
            other(5)
        }
    MAX-ACCESS  not-accessible
    STATUS      current
    DESCRIPTION
        "Represents the type of de-association with this AP."
    ::= { hh3cDot11APDeassocStatisEntry 1 }

hh3cDot11APDeassocStatisCnt   OBJECT-TYPE
    SYNTAX      Counter32
    MAX-ACCESS  read-only
    STATUS      current
    DESCRIPTION
        "Represents the total number of each type for de-association
         with this AP."
    ::= { hh3cDot11APDeassocStatisEntry 2 }

-- *****************************************************************************
-- *  End of hh3cDot11APDeassocStatisTable Definition
-- *****************************************************************************
-- *****************************************************************************
-- *  hh3cDot11APAssocFailStatis2Table Definition
-- *****************************************************************************
hh3cDot11APAssocFailStatis2Table OBJECT-TYPE
    SYNTAX      SEQUENCE OF Hh3cDot11APAssocFailStatis2Entry
    MAX-ACCESS  not-accessible
    STATUS      current
    DESCRIPTION
        "This table will provide statistic of association fails for each ap."
    ::= { hh3cDot11APStatisGroup 16 }

hh3cDot11APAssocFailStatis2Entry OBJECT-TYPE
    SYNTAX      Hh3cDot11APAssocFailStatis2Entry
    MAX-ACCESS  not-accessible
    STATUS      current
    DESCRIPTION
        "Each entry will provide statistic of association fails for this ap."
    INDEX
        {
            hh3cDot11CurAPID,
            hh3cDot11APAssocFailStatis2Type
        }
    ::= { hh3cDot11APAssocFailStatis2Table 1 }

Hh3cDot11APAssocFailStatis2Entry ::= SEQUENCE
    {
        hh3cDot11APAssocFailStatis2Type                 INTEGER,
        hh3cDot11APAssocFailStatis2Cnt                  Counter32
    }

hh3cDot11APAssocFailStatis2Type OBJECT-TYPE
    SYNTAX      INTEGER
        {
            shortResource(1),
            notSupportRateSet(2),
            unknownReasonCode(3),
            other(4),
            rssiLowness(5)
        }
    MAX-ACCESS  not-accessible
    STATUS      current
    DESCRIPTION
        "Represents the type of association fails for this AP"
    ::= { hh3cDot11APAssocFailStatis2Entry 1 }

hh3cDot11APAssocFailStatis2Cnt   OBJECT-TYPE
    SYNTAX      Counter32
    MAX-ACCESS  read-only
    STATUS      current
    DESCRIPTION
        "Represents the total count of association fails for this AP."
    ::= { hh3cDot11APAssocFailStatis2Entry 2 }

-- *****************************************************************************
-- *  End of hh3cDot11APAssocFailStatis2Table Definition
-- *****************************************************************************
-- *****************************************************************************
-- *  hh3cDot11APIfStatisTable Definition
-- *****************************************************************************
hh3cDot11APIfStatisTable OBJECT-TYPE
    SYNTAX      SEQUENCE OF Hh3cDot11APIfStatisEntry
    MAX-ACCESS  not-accessible
    STATUS      current
    DESCRIPTION
        "The table will provide the statistics on the interface of the AP."
    ::= { hh3cDot11APStatisGroup 17 }

hh3cDot11APIfStatisEntry OBJECT-TYPE
    SYNTAX      Hh3cDot11APIfStatisEntry
    MAX-ACCESS  not-accessible
    STATUS      current
    DESCRIPTION
        "Each entry of the table will provide statistics on the interface of the AP."
    INDEX
        {
            hh3cDot11APElementIndex,
            hh3cDot11APIfIndex
        }
    ::= { hh3cDot11APIfStatisTable 1 }

Hh3cDot11APIfStatisEntry ::= SEQUENCE
    {
        hh3cDot11APIfInPkts              Counter32,
        hh3cDot11APIfInNormalPkts        Counter32,
        hh3cDot11APIfInErrorPkts         Counter32,
        hh3cDot11APIfOutPkts             Counter32,
        hh3cDot11APIfInOctets            Counter32,
        hh3cDot11APIfOutOctets           Counter32,
        hh3cDot11APIfFlowOut             Unsigned32,
        hh3cDot11APIfFlowIN              Unsigned32,
        hh3cDot11APIfInUcastPkts         Counter32,
        hh3cDot11APIfInNUcastPkts        Counter32,
        hh3cDot11APIfInDiscardPkts       Counter32,
        hh3cDot11APIfOutUcastPkts        Counter32,
        hh3cDot11APIfOutNUcastPkts       Counter32,
        hh3cDot11APIfOutDiscardPkts      Counter32,
        hh3cDot11APIfOutErrorPkts        Counter32,
        hh3cDot11APIfUpdownTimes         Counter32,
        hh3cDot11APIfStatusKeepTime      TimeTicks,
        hh3cDot11APIfOperStatus          INTEGER,
        hh3cDot11APIfInBrdcastPkts       Counter64,
        hh3cDot11APIfOutBrdcastPkts      Counter64,
        hh3cDot11APIfInMulcastPkts       Counter64,
        hh3cDot11APIfOutMulcastPkts      Counter64,
        hh3cDot11APIfInPayloadOctets     Counter64,
        hh3cDot11APIfOutPayloadOctets    Counter64
    }

hh3cDot11APIfInPkts OBJECT-TYPE
    SYNTAX      Counter32
    MAX-ACCESS  read-only
    STATUS      current
    DESCRIPTION
        "Represents the total number of packets received
         on the interface."
    ::= { hh3cDot11APIfStatisEntry 1 }

hh3cDot11APIfInNormalPkts OBJECT-TYPE
    SYNTAX      Counter32
    MAX-ACCESS  read-only
    STATUS      current
    DESCRIPTION
        "Represents the total number of correct
         packets received on the interface."
    ::= { hh3cDot11APIfStatisEntry 2 }

hh3cDot11APIfInErrorPkts OBJECT-TYPE
    SYNTAX      Counter32
    MAX-ACCESS  read-only
    STATUS      current
    DESCRIPTION
        "Represents the total number of error
         packets received on the interface."
    ::= { hh3cDot11APIfStatisEntry 3 }

hh3cDot11APIfOutPkts OBJECT-TYPE
    SYNTAX      Counter32
    MAX-ACCESS  read-only
    STATUS      current
    DESCRIPTION
        "Represents the total number of packets
         sent from the interface."
    ::= { hh3cDot11APIfStatisEntry 4 }

hh3cDot11APIfInOctets OBJECT-TYPE
    SYNTAX      Counter32
    MAX-ACCESS  read-only
    STATUS      current
    DESCRIPTION
        "Represents the total number of octets
         received on the interface."
    ::= { hh3cDot11APIfStatisEntry 5 }

hh3cDot11APIfOutOctets OBJECT-TYPE
    SYNTAX      Counter32
    MAX-ACCESS  read-only
    STATUS      current
    DESCRIPTION
        "Represents the total number of octets
         sent from the interface."
    ::= { hh3cDot11APIfStatisEntry 6 }

hh3cDot11APIfFlowOut OBJECT-TYPE
    SYNTAX      Unsigned32
    MAX-ACCESS  read-only
    STATUS      current
    DESCRIPTION
        "Represents the traffic rate (byte/s) on the uplink interface
         during a sampling period."
    ::= { hh3cDot11APIfStatisEntry 7 }

hh3cDot11APIfFlowIN OBJECT-TYPE
    SYNTAX      Unsigned32
    MAX-ACCESS  read-only
    STATUS      current
    DESCRIPTION
        "Represents the traffic rate (byte/s) on the downlink interface
         during a sampling period."
    ::= { hh3cDot11APIfStatisEntry 8 }

hh3cDot11APIfInUcastPkts OBJECT-TYPE
    SYNTAX      Counter32
    MAX-ACCESS  read-only
    STATUS      current
    DESCRIPTION
        "Represents the number of unicast packets received on the interface."
    ::= { hh3cDot11APIfStatisEntry 9 }

hh3cDot11APIfInNUcastPkts OBJECT-TYPE
    SYNTAX      Counter32
    MAX-ACCESS  read-only
    STATUS      current
    DESCRIPTION
        "Represents the number of non-unicast packets received on the wired
         interface."
    ::= { hh3cDot11APIfStatisEntry 10 }

hh3cDot11APIfInDiscardPkts OBJECT-TYPE
    SYNTAX      Counter32
    MAX-ACCESS  read-only
    STATUS      current
    DESCRIPTION
        "Represents the number of unicast packets discarded on the interface."
    ::= { hh3cDot11APIfStatisEntry 11 }

hh3cDot11APIfOutUcastPkts OBJECT-TYPE
    SYNTAX      Counter32
    MAX-ACCESS  read-only
    STATUS      current
    DESCRIPTION
        "Represents the number of unicast packets send on the interface."
    ::= { hh3cDot11APIfStatisEntry 12 }

hh3cDot11APIfOutNUcastPkts OBJECT-TYPE
    SYNTAX      Counter32
    MAX-ACCESS  read-only
    STATUS      current
    DESCRIPTION
        "Represents the number of non-unicast packets send on the interface."
    ::= { hh3cDot11APIfStatisEntry 13 }

hh3cDot11APIfOutDiscardPkts OBJECT-TYPE
    SYNTAX      Counter32
    MAX-ACCESS  read-only
    STATUS      current
    DESCRIPTION
        "Represents the number of discarded packets send on the interface."
    ::= { hh3cDot11APIfStatisEntry 14 }

hh3cDot11APIfOutErrorPkts OBJECT-TYPE
    SYNTAX      Counter32
    MAX-ACCESS  read-only
    STATUS      current
    DESCRIPTION
        "Represents the number of error packets send on the interface."
    ::= { hh3cDot11APIfStatisEntry 15 }

hh3cDot11APIfUpdownTimes OBJECT-TYPE
    SYNTAX      Counter32
    MAX-ACCESS  read-only
    STATUS      current
    DESCRIPTION
        "Represents the up/down times on the interface."
    ::= { hh3cDot11APIfStatisEntry 16 }

hh3cDot11APIfStatusKeepTime OBJECT-TYPE
    SYNTAX      TimeTicks
    MAX-ACCESS  read-only
    STATUS      current
    DESCRIPTION
        "Represents the last change time on the interface."
    ::= { hh3cDot11APIfStatisEntry 17 }

hh3cDot11APIfOperStatus OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { hh3cDot11APIfStatisEntry 18 }

hh3cDot11APIfInBrdcastPkts OBJECT-TYPE
    SYNTAX      Counter64
    MAX-ACCESS  read-only
    STATUS      current
    DESCRIPTION
        "Represents the number of broadcast packets received on the interface."
    ::= { hh3cDot11APIfStatisEntry 19 }

hh3cDot11APIfOutBrdcastPkts OBJECT-TYPE
    SYNTAX      Counter64
    MAX-ACCESS  read-only
    STATUS      current
    DESCRIPTION
        "Represents the number of broadcast packets sent on the interface."
    ::= { hh3cDot11APIfStatisEntry 20 }

hh3cDot11APIfInMulcastPkts OBJECT-TYPE
    SYNTAX      Counter64
    MAX-ACCESS  read-only
    STATUS      current
    DESCRIPTION
        "Represents the number of multicast packets received on the interface."
    ::= { hh3cDot11APIfStatisEntry 21 }

hh3cDot11APIfOutMulcastPkts OBJECT-TYPE
    SYNTAX      Counter64
    MAX-ACCESS  read-only
    STATUS      current
    DESCRIPTION
        "Represents the number of multicast packets sent on the interface."
    ::= { hh3cDot11APIfStatisEntry 22 }

hh3cDot11APIfInPayloadOctets OBJECT-TYPE
    SYNTAX      Counter64
    MAX-ACCESS  read-only
    STATUS      current
    DESCRIPTION
        "Represents the number of actual octets received on the interface."
    ::= { hh3cDot11APIfStatisEntry 23 }

hh3cDot11APIfOutPayloadOctets OBJECT-TYPE
    SYNTAX      Counter64
    MAX-ACCESS  read-only
    STATUS      current
    DESCRIPTION
        "Represents the number of actual octets sent on the interface."
    ::= { hh3cDot11APIfStatisEntry 24 }

-- *****************************************************************************
-- *  End of hh3cDot11APIfStatisTable Definition
-- *****************************************************************************

-- *****************************************************************************
-- *  hh3cDot11RadioMngFrmStatisTable Definition
-- *****************************************************************************
hh3cDot11RadioMngFrmStatisTable OBJECT-TYPE
    SYNTAX      SEQUENCE OF Hh3cDot11RadioMngFrmStatisEntry
    MAX-ACCESS  not-accessible
    STATUS      current
    DESCRIPTION
        "The table will provide the management frame statistic of this radio."
    ::= { hh3cDot11APStatisGroup 18 }

hh3cDot11RadioMngFrmStatisEntry OBJECT-TYPE
    SYNTAX      Hh3cDot11RadioMngFrmStatisEntry
    MAX-ACCESS  not-accessible
    STATUS      current
    DESCRIPTION
        "Each entry of the table will provide the management
         frame statistic of this radio."
    INDEX
        {
            hh3cDot11CurAPID,
            hh3cDot11RadioID,
            hh3cDot11MngFrmType
        }
    ::= { hh3cDot11RadioMngFrmStatisTable 1 }

Hh3cDot11RadioMngFrmStatisEntry ::= SEQUENCE
    {
        hh3cDot11MngFrmType                 INTEGER,
        hh3cDot11MngFrmCnt                  Counter32
    }

hh3cDot11MngFrmType  OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { hh3cDot11RadioMngFrmStatisEntry 1 }

hh3cDot11MngFrmCnt  OBJECT-TYPE
    SYNTAX      Counter32
    MAX-ACCESS  read-only
    STATUS      current
    DESCRIPTION
        "Represents the total number of each type of management frame on this
         radio."
    ::= { hh3cDot11RadioMngFrmStatisEntry 2 }
-- *****************************************************************************
-- *  End of hh3cDot11RadioMngFrmStatisTable Definition
-- *****************************************************************************


-- *****************************************************************************
-- *  hh3cDot11APPacketSizeStatisTable Definition
-- *****************************************************************************
hh3cDot11APPacketSizeStatisTable  OBJECT-TYPE
        SYNTAX        SEQUENCE OF Hh3cDot11APPacketSizeStatisEntry
        MAX-ACCESS    not-accessible
        STATUS        current
        DESCRIPTION
                "This table provides packets statistic base on size."
        ::= { hh3cDot11APStatisGroup 19 }

hh3cDot11APPacketSizeStatisEntry  OBJECT-TYPE
        SYNTAX        Hh3cDot11APPacketSizeStatisEntry
        MAX-ACCESS    not-accessible
        STATUS        current
        DESCRIPTION
                "Each entry provides packets statistic base on size for each radio
                 of a specific AP."
        INDEX
            {
                hh3cDot11CurAPID,
                hh3cDot11RadioID,
                hh3cDot11APPacketSize
            }
        ::= { hh3cDot11APPacketSizeStatisTable 1 }

Hh3cDot11APPacketSizeStatisEntry    ::=SEQUENCE
        {
            hh3cDot11APPacketSize          INTEGER,
            hh3cDot11APRXPacketSizeCount   Counter64,
            hh3cDot11APTXPacketSizeCount   Counter64
        }

hh3cDot11APPacketSize    OBJECT-TYPE
        SYNTAX    INTEGER
            {
                sizeLevel1(1),
                sizeLevel2(2),
                sizeLevel3(3),
                sizeLevel4(4)
            }
        MAX-ACCESS    not-accessible
        STATUS        current
        DESCRIPTION
            "This node represents packet size:
                    sizeLevel1 : size <= 128
                    sizeLevel2 : 128 < size <= 512
                    sizeLevel3 : 512 < size <= 1024
                    sizeLevel4 : size > 1024"
    ::= { hh3cDot11APPacketSizeStatisEntry 1 }

hh3cDot11APRXPacketSizeCount    OBJECT-TYPE
        SYNTAX        Counter64
        MAX-ACCESS    read-only
        STATUS        current
        DESCRIPTION
                "Represents the count of packets reception base on frame size."
    ::= { hh3cDot11APPacketSizeStatisEntry 2 }

hh3cDot11APTXPacketSizeCount    OBJECT-TYPE
        SYNTAX        Counter64
        MAX-ACCESS    read-only
        STATUS        current
        DESCRIPTION
                "Represents the count of packets transmission base on frame size."
    ::= { hh3cDot11APPacketSizeStatisEntry 3 }
-- *****************************************************************************
-- *  End of hh3cDot11APPacketSizeStatisTable Definition
-- *****************************************************************************

-- *****************************************************************************
-- *  hh3cDot11APPacketRateStatisTable Definition
-- *****************************************************************************
hh3cDot11APPacketRateStatisTable  OBJECT-TYPE
        SYNTAX        SEQUENCE OF Hh3cDot11APPacketRateStatisEntry
        MAX-ACCESS    not-accessible
        STATUS        current
        DESCRIPTION
                "This table provides packets statistic base on rate."
        ::= { hh3cDot11APStatisGroup 20 }

hh3cDot11APPacketRateStatisEntry  OBJECT-TYPE
        SYNTAX        Hh3cDot11APPacketRateStatisEntry
        MAX-ACCESS    not-accessible
        STATUS        current
        DESCRIPTION
                "Each entry provides packets statistic base on rate for each radio
                 of a specific AP."
        INDEX
            {
                hh3cDot11CurAPID,
                hh3cDot11RadioID,
                hh3cDot11APPacketRate
            }
        ::= { hh3cDot11APPacketRateStatisTable 1 }

Hh3cDot11APPacketRateStatisEntry    ::=SEQUENCE
        {
                hh3cDot11APPacketRate          Integer32,
                hh3cDot11APRXPacketRateCount   Counter64,
                hh3cDot11APTXPacketRateCount   Counter64
        }

hh3cDot11APPacketRate    OBJECT-TYPE
        SYNTAX        Integer32
        MAX-ACCESS    not-accessible
        STATUS        current
        DESCRIPTION
                "Represents transmit data rate(twice as actual rate)."
    ::= { hh3cDot11APPacketRateStatisEntry 1 }

hh3cDot11APRXPacketRateCount    OBJECT-TYPE
        SYNTAX        Counter64
        MAX-ACCESS    read-only
        STATUS        current
        DESCRIPTION
                "Represents the count of packets reception base on transmit data rate."
    ::= { hh3cDot11APPacketRateStatisEntry 2 }

hh3cDot11APTXPacketRateCount    OBJECT-TYPE
        SYNTAX        Counter64
        MAX-ACCESS    read-only
        STATUS        current
        DESCRIPTION
                "Represents the count of packets transmission base on transmit data rate."
    ::= { hh3cDot11APPacketRateStatisEntry 3 }

-- *****************************************************************************
-- *  End of hh3cDot11APPacketRateStatisTable Definition
-- *****************************************************************************

-- *****************************************************************************
-- *  hh3cDot11APPacketMCSRateStatisTable Definition
-- *****************************************************************************
hh3cDot11APPacketMCSRateStatisTable  OBJECT-TYPE
        SYNTAX        SEQUENCE OF Hh3cDot11APPacketMCSRateStatisEntry
        MAX-ACCESS    not-accessible
        STATUS        current
        DESCRIPTION
                "This table provides packets statistic base on MCS rate."
        ::= { hh3cDot11APStatisGroup 21 }

hh3cDot11APPacketMCSRateStatisEntry  OBJECT-TYPE
        SYNTAX        Hh3cDot11APPacketMCSRateStatisEntry
        MAX-ACCESS    not-accessible
        STATUS        current
        DESCRIPTION
                "Each entry provides packets statistic base on MCS rate for each radio
                 of a specific AP."
        INDEX
            {
                hh3cDot11CurAPID,
                hh3cDot11RadioID,
                hh3cDot11APPacketMCSRate
            }
        ::= { hh3cDot11APPacketMCSRateStatisTable 1 }

Hh3cDot11APPacketMCSRateStatisEntry  ::=SEQUENCE
        {
            hh3cDot11APPacketMCSRate          Integer32,
            hh3cDot11APRXPacketMCSRateCount   Counter64,
            hh3cDot11APTXPacketMCSRateCount   Counter64
        }

hh3cDot11APPacketMCSRate    OBJECT-TYPE
        SYNTAX        Integer32
        MAX-ACCESS    not-accessible
        STATUS        current
        DESCRIPTION
            "Represents transmit data rate(twice as actual rate)."
    ::= { hh3cDot11APPacketMCSRateStatisEntry 1 }

hh3cDot11APRXPacketMCSRateCount    OBJECT-TYPE
        SYNTAX        Counter64
        MAX-ACCESS    read-only
        STATUS        current
        DESCRIPTION
            "Represents the count of packets reception base on transmit data rate."
    ::= { hh3cDot11APPacketMCSRateStatisEntry 2 }

hh3cDot11APTXPacketMCSRateCount    OBJECT-TYPE
        SYNTAX        Counter64
        MAX-ACCESS    read-only
        STATUS        current
        DESCRIPTION
            "Represents the count of packets transmission base on transmit
             data rate."
    ::= { hh3cDot11APPacketMCSRateStatisEntry 3 }

-- *****************************************************************************
-- *  End of hh3cDot11APPacketMcsRateStatisTable Definition
-- *****************************************************************************

-- *****************************************************************************
-- *  hh3cDot11APAssocFailStatis3Table Definition
-- *****************************************************************************
hh3cDot11APAssocFailStatis3Table OBJECT-TYPE
    SYNTAX      SEQUENCE OF Hh3cDot11APAssocFailStatis3Entry
    MAX-ACCESS  not-accessible
    STATUS      current
    DESCRIPTION
        "This table will provide statistic of association fails for each AP."
    ::= { hh3cDot11APStatisGroup 22 }

hh3cDot11APAssocFailStatis3Entry OBJECT-TYPE
    SYNTAX      Hh3cDot11APAssocFailStatis3Entry
    MAX-ACCESS  not-accessible
    STATUS      current
    DESCRIPTION
        "Each entry will provide statistic of association failure with this AP
         because of different reasons."
    INDEX
        {
            hh3cDot11CurAPID
       }
    ::= { hh3cDot11APAssocFailStatis3Table 1 }

Hh3cDot11APAssocFailStatis3Entry ::= SEQUENCE
    {
        hh3cDot11APAssocFailStatis3SRCnt                 Counter32,
        hh3cDot11APAssocFailStatis3NSRCnt                Counter32,
        hh3cDot11APAssocFailStatis3URCCnt                Counter32,
        hh3cDot11APAssocFailStatis3RFCnt                 Counter32,
        hh3cDot11APAssocFailStatis3OtherCnt              Counter32,
        hh3cDot11APAssocFailStatis3RSSILowCntCM          Counter32
    }

hh3cDot11APAssocFailStatis3SRCnt OBJECT-TYPE
    SYNTAX      Counter32
    MAX-ACCESS  read-only
    STATUS      current
    DESCRIPTION
        "This object represents the count of association failure because of
         lack of resource."
    ::= { hh3cDot11APAssocFailStatis3Entry 1 }

hh3cDot11APAssocFailStatis3NSRCnt OBJECT-TYPE
    SYNTAX      Counter32
    MAX-ACCESS  read-only
    STATUS      current
    DESCRIPTION
        "This object represents the count of association failure because of
         not support rate set."
    ::= { hh3cDot11APAssocFailStatis3Entry 2 }

hh3cDot11APAssocFailStatis3URCCnt OBJECT-TYPE
    SYNTAX      Counter32
    MAX-ACCESS  read-only
    STATUS      current
    DESCRIPTION
        "This object represents the count of association failure because of
         unknown reason code."
    ::= { hh3cDot11APAssocFailStatis3Entry 3 }

hh3cDot11APAssocFailStatis3RFCnt OBJECT-TYPE
    SYNTAX      Counter32
    MAX-ACCESS  read-only
    STATUS      current
    DESCRIPTION
        "This object represents the count of association failure because of
         re-associate failed."
    ::= { hh3cDot11APAssocFailStatis3Entry 4 }

hh3cDot11APAssocFailStatis3OtherCnt OBJECT-TYPE
    SYNTAX      Counter32
    MAX-ACCESS  read-only
    STATUS      current
    DESCRIPTION
        "This object represents the count of association fails because of
         reason not in 802.11 the protocol."
    ::= { hh3cDot11APAssocFailStatis3Entry 5 }

hh3cDot11APAssocFailStatis3RSSILowCntCM OBJECT-TYPE
    SYNTAX      Counter32
    MAX-ACCESS  read-only
    STATUS      current
    DESCRIPTION
        "Represents the count of failed associations due to low RSSI."
    ::= { hh3cDot11APAssocFailStatis3Entry 6 }

-- *****************************************************************************
-- *  End of hh3cDot11APAssocFailStatis3Table Definition
-- *****************************************************************************

-- *****************************************************************************
-- *  hh3cDot11APIfStatisByAPIDTable Definition
-- *****************************************************************************
hh3cDot11APIfStatisByAPIDTable OBJECT-TYPE
    SYNTAX      SEQUENCE OF Hh3cDot11APIfStatisByAPIDEntry
    MAX-ACCESS  not-accessible
    STATUS      current
    DESCRIPTION
        "The table will provide the statistics on the interface of the AP."
    ::= { hh3cDot11APStatisGroup 23 }

hh3cDot11APIfStatisByAPIDEntry OBJECT-TYPE
    SYNTAX      Hh3cDot11APIfStatisByAPIDEntry
    MAX-ACCESS  not-accessible
    STATUS      current
    DESCRIPTION
        "Each entry of the table will provide statistics on the interface of the AP."
    INDEX
        {
            hh3cDot11CurAPID,
            hh3cDot11APIfIndex
        }
    ::= { hh3cDot11APIfStatisByAPIDTable 1 }

Hh3cDot11APIfStatisByAPIDEntry ::= SEQUENCE
    {
        hh3cDot11APIfInPkts2              Counter64,
        hh3cDot11APIfInNormalPkts2        Counter64,
        hh3cDot11APIfInErrorPkts2         Counter64,
        hh3cDot11APIfOutPkts2             Counter64,
        hh3cDot11APIfInOctets2            Counter64,
        hh3cDot11APIfOutOctets2           Counter64,
        hh3cDot11APIfFlowOut2             Unsigned32,
        hh3cDot11APIfFlowIN2              Unsigned32,
        hh3cDot11APIfInUcastPkts2         Counter64,
        hh3cDot11APIfInNUcastPkts2        Counter64,
        hh3cDot11APIfInDiscardPkts2       Counter64,
        hh3cDot11APIfOutUcastPkts2        Counter64,
        hh3cDot11APIfOutNUcastPkts2       Counter64,
        hh3cDot11APIfOutDiscardPkts2      Counter64,
        hh3cDot11APIfOutErrorPkts2        Counter64,
        hh3cDot11APIfUpdownTimes2         Counter32,
        hh3cDot11APIfStatusKeepTime2      TimeTicks,
        hh3cDot11APIfOperStatus2          INTEGER,
        hh3cDot11APIfInBrdcastPkts2       Counter64,
        hh3cDot11APIfOutBrdcastPkts2      Counter64,
        hh3cDot11APIfInMulcastPkts2       Counter64,
        hh3cDot11APIfOutMulcastPkts2      Counter64,
        hh3cDot11APIfInPayloadOctets2     Counter64,
        hh3cDot11APIfOutPayloadOctets2    Counter64,
        hh3cDot11APIfInDataOctets2        Counter64,
        hh3cDot11APIfOutDataOctets2       Counter64,
        hh3cDot11APIfAdminStatus          INTEGER,
        hh3cDot11APIfOperStatusCM         INTEGER
    }

hh3cDot11APIfInPkts2 OBJECT-TYPE
    SYNTAX      Counter64
    MAX-ACCESS  read-only
    STATUS      current
    DESCRIPTION
        "Represents the total number of packets received
         on the interface."
    ::= { hh3cDot11APIfStatisByAPIDEntry 1 }

hh3cDot11APIfInNormalPkts2 OBJECT-TYPE
    SYNTAX      Counter64
    MAX-ACCESS  read-only
    STATUS      current
    DESCRIPTION
        "Represents the total number of correct
         packets received on the interface."
    ::= { hh3cDot11APIfStatisByAPIDEntry 2 }

hh3cDot11APIfInErrorPkts2 OBJECT-TYPE
    SYNTAX      Counter64
    MAX-ACCESS  read-only
    STATUS      current
    DESCRIPTION
        "Represents the total number of error
         packets received on the interface."
    ::= { hh3cDot11APIfStatisByAPIDEntry 3 }

hh3cDot11APIfOutPkts2 OBJECT-TYPE
    SYNTAX      Counter64
    MAX-ACCESS  read-only
    STATUS      current
    DESCRIPTION
        "Represents the total number of packets
         sent from the interface."
    ::= { hh3cDot11APIfStatisByAPIDEntry 4 }

hh3cDot11APIfInOctets2 OBJECT-TYPE
    SYNTAX      Counter64
    MAX-ACCESS  read-only
    STATUS      current
    DESCRIPTION
        "Represents the total number of octets
         received on the interface."
    ::= { hh3cDot11APIfStatisByAPIDEntry 5 }

hh3cDot11APIfOutOctets2 OBJECT-TYPE
    SYNTAX      Counter64
    MAX-ACCESS  read-only
    STATUS      current
    DESCRIPTION
        "Represents the total number of octets
         sent from the interface."
    ::= { hh3cDot11APIfStatisByAPIDEntry 6 }

hh3cDot11APIfFlowOut2 OBJECT-TYPE
    SYNTAX      Unsigned32
    MAX-ACCESS  read-only
    STATUS      current
    DESCRIPTION
        "Represents the traffic rate (byte/s) on the uplink interface
         during a sampling period."
    ::= { hh3cDot11APIfStatisByAPIDEntry 7 }

hh3cDot11APIfFlowIN2 OBJECT-TYPE
    SYNTAX      Unsigned32
    MAX-ACCESS  read-only
    STATUS      current
    DESCRIPTION
        "Represents the traffic rate (byte/s) on the downlink interface
         during a sampling period."
    ::= { hh3cDot11APIfStatisByAPIDEntry 8 }

hh3cDot11APIfInUcastPkts2 OBJECT-TYPE
    SYNTAX      Counter64
    MAX-ACCESS  read-only
    STATUS      current
    DESCRIPTION
        "Represents the number of unicast packets received on the interface."
    ::= { hh3cDot11APIfStatisByAPIDEntry 9 }

hh3cDot11APIfInNUcastPkts2 OBJECT-TYPE
    SYNTAX      Counter64
    MAX-ACCESS  read-only
    STATUS      current
    DESCRIPTION
        "Represents the number of non-unicast packets received on the wired
         interface."
    ::= { hh3cDot11APIfStatisByAPIDEntry 10 }

hh3cDot11APIfInDiscardPkts2 OBJECT-TYPE
    SYNTAX      Counter64
    MAX-ACCESS  read-only
    STATUS      current
    DESCRIPTION
        "Represents the number of unicast packets discarded on the interface."
    ::= { hh3cDot11APIfStatisByAPIDEntry 11 }

hh3cDot11APIfOutUcastPkts2 OBJECT-TYPE
    SYNTAX      Counter64
    MAX-ACCESS  read-only
    STATUS      current
    DESCRIPTION
        "Represents the number of unicast packets send on the interface."
    ::= { hh3cDot11APIfStatisByAPIDEntry 12 }

hh3cDot11APIfOutNUcastPkts2 OBJECT-TYPE
    SYNTAX      Counter64
    MAX-ACCESS  read-only
    STATUS      current
    DESCRIPTION
        "Represents the number of non-unicast packets send on the interface."
    ::= { hh3cDot11APIfStatisByAPIDEntry 13 }

hh3cDot11APIfOutDiscardPkts2 OBJECT-TYPE
    SYNTAX      Counter64
    MAX-ACCESS  read-only
    STATUS      current
    DESCRIPTION
        "Represents the number of discarded packets send on the interface."
    ::= { hh3cDot11APIfStatisByAPIDEntry 14 }

hh3cDot11APIfOutErrorPkts2 OBJECT-TYPE
    SYNTAX      Counter64
    MAX-ACCESS  read-only
    STATUS      current
    DESCRIPTION
        "Represents the number of error packets send on the interface."
    ::= { hh3cDot11APIfStatisByAPIDEntry 15 }

hh3cDot11APIfUpdownTimes2 OBJECT-TYPE
    SYNTAX      Counter32
    MAX-ACCESS  read-only
    STATUS      current
    DESCRIPTION
        "Represents the up/down times on the interface."
    ::= { hh3cDot11APIfStatisByAPIDEntry 16 }

hh3cDot11APIfStatusKeepTime2 OBJECT-TYPE
    SYNTAX      TimeTicks
    MAX-ACCESS  read-only
    STATUS      current
    DESCRIPTION
        "Represents the last change time on the interface."
    ::= { hh3cDot11APIfStatisByAPIDEntry 17 }

hh3cDot11APIfOperStatus2 OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { hh3cDot11APIfStatisByAPIDEntry 18 }

hh3cDot11APIfInBrdcastPkts2 OBJECT-TYPE
    SYNTAX      Counter64
    MAX-ACCESS  read-only
    STATUS      current
    DESCRIPTION
        "Represents the number of broadcast packets received on the interface."
    ::= { hh3cDot11APIfStatisByAPIDEntry 19 }

hh3cDot11APIfOutBrdcastPkts2 OBJECT-TYPE
    SYNTAX      Counter64
    MAX-ACCESS  read-only
    STATUS      current
    DESCRIPTION
        "Represents the number of broadcast packets sent on the interface."
    ::= { hh3cDot11APIfStatisByAPIDEntry 20 }

hh3cDot11APIfInMulcastPkts2 OBJECT-TYPE
    SYNTAX      Counter64
    MAX-ACCESS  read-only
    STATUS      current
    DESCRIPTION
        "Represents the number of multicast packets received on the interface."
    ::= { hh3cDot11APIfStatisByAPIDEntry 21 }

hh3cDot11APIfOutMulcastPkts2 OBJECT-TYPE
    SYNTAX      Counter64
    MAX-ACCESS  read-only
    STATUS      current
    DESCRIPTION
        "Represents the number of multicast packets sent on the interface."
    ::= { hh3cDot11APIfStatisByAPIDEntry 22 }

hh3cDot11APIfInPayloadOctets2 OBJECT-TYPE
    SYNTAX      Counter64
    MAX-ACCESS  read-only
    STATUS      current
    DESCRIPTION
        "Represents the number of actual octets received on the interface."
    ::= { hh3cDot11APIfStatisByAPIDEntry 23 }

hh3cDot11APIfOutPayloadOctets2 OBJECT-TYPE
    SYNTAX      Counter64
    MAX-ACCESS  read-only
    STATUS      current
    DESCRIPTION
        "Represents the number of actual octets sent on the interface."
    ::= { hh3cDot11APIfStatisByAPIDEntry 24 }

hh3cDot11APIfInDataOctets2 OBJECT-TYPE
    SYNTAX      Counter64
    MAX-ACCESS  read-only
    STATUS      current
    DESCRIPTION
        "Represents the number of actual data octets received on the interface."
    ::= { hh3cDot11APIfStatisByAPIDEntry 25 }

hh3cDot11APIfOutDataOctets2 OBJECT-TYPE
    SYNTAX      Counter64
    MAX-ACCESS  read-only
    STATUS      current
    DESCRIPTION
        "Represents the number of actual data octets sent on the interface."
    ::= { hh3cDot11APIfStatisByAPIDEntry 26 }

hh3cDot11APIfAdminStatus OBJECT-TYPE
    SYNTAX  INTEGER {
                up(1),       -- ready to forward packets
                down(2),
                testing(3)   -- in a test mode
            }
    MAX-ACCESS  read-write
    STATUS      current
    DESCRIPTION
            "Expected state of the interface.  In testing state the
            interface does not forward any operational packets.  When
             a managed system is initialized, all interfaces start with
            hh3cDot11APIfAdminStatus in the down state.  As a result
            of either explicit management action or per configuration
            information retained by the managed system,
            hh3cDot11APIfAdminStatus is then changed to either the up
             or testing state or remains in the down state."
    ::= { hh3cDot11APIfStatisByAPIDEntry 27 }

hh3cDot11APIfOperStatusCM OBJECT-TYPE
    SYNTAX  INTEGER {
                       up(1),        -- ready to forward packets
                       down(2),
                       testing(3),   -- in a test mode
                       admindown(4)  -- shutdown by administrator
                    }
    MAX-ACCESS  read-only
    STATUS      current
    DESCRIPTION
        "Operational status of the interface."
    ::= { hh3cDot11APIfStatisByAPIDEntry 28 }

-- *****************************************************************************
-- *  End of hh3cDot11APIfStatisTable1 Definition
-- *****************************************************************************

-- *****************************************************************************
-- *  hh3cDot11APUserSecAuthStatisTable Definition
-- *****************************************************************************
hh3cDot11APUserSecAuthStatisTable OBJECT-TYPE
    SYNTAX      SEQUENCE OF Hh3cDot11APUserSecAuthStatisEntry
    MAX-ACCESS  not-accessible
    STATUS      current
    DESCRIPTION
        "The table will provide the user authentication statistic for this AP."
    ::= { hh3cDot11APStatisGroup 24 }

hh3cDot11APUserSecAuthStatisEntry OBJECT-TYPE
    SYNTAX      Hh3cDot11APUserSecAuthStatisEntry
    MAX-ACCESS  not-accessible
    STATUS      current
    DESCRIPTION
        "Each entry of the table will provide the user authentication statistic
        for this AP."
    INDEX
        {
            hh3cDot11CurAPID
       }
    ::= { hh3cDot11APUserSecAuthStatisTable 1 }

Hh3cDot11APUserSecAuthStatisEntry ::= SEQUENCE
    {
        hh3cDot11APUserAuthCurNumber             Integer32,
        hh3cDot11APUserConnFailCnt               Counter32,
        hh3cDot11APUserAuthReqCnt                Counter32,
        hh3cDot11APUserAuthSuccCnt               Counter32,
        hh3cDot11APUserAuthFailCnt               Counter32,
        hh3cDot11AllUserOnlineTime               TimeTicks
    }

hh3cDot11APUserAuthCurNumber OBJECT-TYPE
    SYNTAX      Integer32
    MAX-ACCESS  read-only
    STATUS      current
    DESCRIPTION
        "Represents the current number of user authenticated with this AP."
    ::= { hh3cDot11APUserSecAuthStatisEntry 1 }

hh3cDot11APUserConnFailCnt OBJECT-TYPE
    SYNTAX      Counter32
    MAX-ACCESS  read-only
    STATUS      current
    DESCRIPTION
        "Represents the total number of user disconnected with this AP."
    ::= { hh3cDot11APUserSecAuthStatisEntry 2 }

hh3cDot11APUserAuthReqCnt OBJECT-TYPE
    SYNTAX      Counter32
    MAX-ACCESS  read-only
    STATUS      current
    DESCRIPTION
        "Represents the total number of user authentication request with this AP."
    ::= { hh3cDot11APUserSecAuthStatisEntry 3 }

hh3cDot11APUserAuthSuccCnt OBJECT-TYPE
    SYNTAX      Counter32
    MAX-ACCESS  read-only
    STATUS      current
    DESCRIPTION
        "Represents the total number of successful authenticated users with this AP."
    ::= { hh3cDot11APUserSecAuthStatisEntry 4 }

hh3cDot11APUserAuthFailCnt OBJECT-TYPE
    SYNTAX      Counter32
    MAX-ACCESS  read-only
    STATUS      current
    DESCRIPTION
        "Represents the total number of user authentication failures with this AP."
    ::= { hh3cDot11APUserSecAuthStatisEntry 5 }

hh3cDot11AllUserOnlineTime OBJECT-TYPE
    SYNTAX      TimeTicks
    MAX-ACCESS  read-only
    STATUS      current
    DESCRIPTION
        "Represents the online time of all successful authenticated users with this AP."
    ::= { hh3cDot11APUserSecAuthStatisEntry 6 }

-- *****************************************************************************
-- *  End of hh3cDot11APUserSecAuthStatisEntry Definition
-- *****************************************************************************

-- *****************************************************************************
-- *  hh3cDot11APUserInfoStatisTable Definition
-- *****************************************************************************
hh3cDot11APUserInfoStatisTable OBJECT-TYPE
    SYNTAX      SEQUENCE OF Hh3cDot11APUserInfoStatisEntry
    MAX-ACCESS  not-accessible
    STATUS      current
    DESCRIPTION
        "The table will provide the user information statistic of this AP."
    ::= { hh3cDot11APStatisGroup 25 }

hh3cDot11APUserInfoStatisEntry OBJECT-TYPE
    SYNTAX      Hh3cDot11APUserInfoStatisEntry
    MAX-ACCESS  not-accessible
    STATUS      current
    DESCRIPTION
        "Each entry of the table will provide the user information statistic
        of this AP."
    INDEX
        {
            hh3cDot11CurAPID,
            hh3cDot11APUserMacAddr
        }
    ::= { hh3cDot11APUserInfoStatisTable 1 }

Hh3cDot11APUserInfoStatisEntry ::= SEQUENCE
    {
        hh3cDot11APUserMacAddr                  MacAddress,
        hh3cDot11APUserIpAddr                   IpAddress,
        hh3cDot11APUserLoginName                OCTET STRING,
        hh3cDot11APUserLoginTime                OCTET STRING,
        hh3cDot11APUserOnlineTime               TimeTicks,
        hh3cDot11APUserLoginNameCM              OCTET STRING,
        hh3cDot11APUserAuthTypeCM               INTEGER,
        hh3cDot11APUserTxPacketCntCM            Counter32,
        hh3cDot11APUserTxBytesCM                Counter64,
        hh3cDot11APUserRxPacketCntCM            Counter32,
        hh3cDot11APUserRxBytesCM                Counter64
    }

hh3cDot11APUserMacAddr OBJECT-TYPE
    SYNTAX      MacAddress
    MAX-ACCESS  not-accessible
    STATUS      current
    DESCRIPTION
        "Represents the mac address of user logging to this AP."
    ::= { hh3cDot11APUserInfoStatisEntry 1 }

hh3cDot11APUserIpAddr OBJECT-TYPE
    SYNTAX      IpAddress
    MAX-ACCESS  read-only
    STATUS      current
    DESCRIPTION
        "Represents the ip address of user logging to this AP."
    ::= { hh3cDot11APUserInfoStatisEntry 2 }

hh3cDot11APUserLoginName OBJECT-TYPE
    SYNTAX      OCTET STRING
    MAX-ACCESS  read-only
    STATUS      current
    DESCRIPTION
        "Represents the login name of user logging to this AP."
    ::= { hh3cDot11APUserInfoStatisEntry 3 }

hh3cDot11APUserLoginTime OBJECT-TYPE
    SYNTAX      OCTET STRING
    MAX-ACCESS  read-only
    STATUS      current
    DESCRIPTION
        "Represents the login time of user with this AP."
    ::= { hh3cDot11APUserInfoStatisEntry 4 }

hh3cDot11APUserOnlineTime OBJECT-TYPE
    SYNTAX      TimeTicks
    MAX-ACCESS  read-only
    STATUS      current
    DESCRIPTION
        "Represents the online time of user with this AP."
    ::= { hh3cDot11APUserInfoStatisEntry 5 }

hh3cDot11APUserLoginNameCM OBJECT-TYPE
    SYNTAX      OCTET STRING
    MAX-ACCESS  read-only
    STATUS      current
    DESCRIPTION
        "Represents the login name of user logging to this AP."
    ::= { hh3cDot11APUserInfoStatisEntry 6 }

hh3cDot11APUserAuthTypeCM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { hh3cDot11APUserInfoStatisEntry 7 }

hh3cDot11APUserTxPacketCntCM OBJECT-TYPE
    SYNTAX      Counter32
    MAX-ACCESS  read-only
    STATUS      current
    DESCRIPTION
        "Represents the total count of packets sent to online users."
    ::= { hh3cDot11APUserInfoStatisEntry 8 }

hh3cDot11APUserTxBytesCM OBJECT-TYPE
    SYNTAX      Counter64
    MAX-ACCESS  read-only
    STATUS      current
    DESCRIPTION
        "Represents the total bytes sent to online users."
    ::= { hh3cDot11APUserInfoStatisEntry 9 }

hh3cDot11APUserRxPacketCntCM OBJECT-TYPE
    SYNTAX      Counter32
    MAX-ACCESS  read-only
    STATUS      current
    DESCRIPTION
        "Represents the total count of packets received from online users."
    ::= { hh3cDot11APUserInfoStatisEntry 10 }

hh3cDot11APUserRxBytesCM OBJECT-TYPE
    SYNTAX      Counter64
    MAX-ACCESS  read-only
    STATUS      current
    DESCRIPTION
        "Represents the total bytes received from online users."
    ::= { hh3cDot11APUserInfoStatisEntry 11 }

-- *****************************************************************************
-- *  End of hh3cDot11APUserInfoStatisTable Definition
-- *****************************************************************************

-- *****************************************************************************
-- *  hh3cDot11APReassocStatis2Table Definition
-- *****************************************************************************
hh3cDot11APReassocStatis2Table OBJECT-TYPE
    SYNTAX      SEQUENCE OF Hh3cDot11APReassocStatis2Entry
    MAX-ACCESS  not-accessible
    STATUS      current
    DESCRIPTION
        "This table will provide statistic of reassociation for each AP."
    ::= { hh3cDot11APStatisGroup 26 }

hh3cDot11APReassocStatis2Entry OBJECT-TYPE
    SYNTAX      Hh3cDot11APReassocStatis2Entry
    MAX-ACCESS  not-accessible
    STATUS      current
    DESCRIPTION
        "Each entry will provide statistic of reassociation with this AP
         because of different reasons."
    INDEX
        {
            hh3cDot11CurAPID
        }
    ::= { hh3cDot11APReassocStatis2Table 1 }

Hh3cDot11APReassocStatis2Entry ::= SEQUENCE
    {
        hh3cDot11APReassocFailStatis2Cnt                 Counter32
    }

hh3cDot11APReassocFailStatis2Cnt OBJECT-TYPE
    SYNTAX      Counter32
    MAX-ACCESS  read-only
    STATUS      current
    DESCRIPTION
        "This object represents the count of reassociation failure because of
         lack of resource."
    ::= { hh3cDot11APReassocStatis2Entry 1 }

-- *****************************************************************************
-- *  End of hh3cDot11APReassocStatis2Table Definition
-- *****************************************************************************

-- *****************************************************************************
-- *  hh3cDot11TrafficTable Definition
-- *****************************************************************************
hh3cDot11TrafficTable OBJECT-TYPE
    SYNTAX      SEQUENCE OF Hh3cDot11TrafficEntry
    MAX-ACCESS  not-accessible
    STATUS      current
    DESCRIPTION
        "The table describes user's traffic based on ssid"
    ::= { hh3cDot11APStatisGroup 27 }

hh3cDot11TrafficEntry OBJECT-TYPE
    SYNTAX      Hh3cDot11TrafficEntry
    MAX-ACCESS  not-accessible
    STATUS      current
    DESCRIPTION
        "Each entry contains the traffc information of a ssid."
    INDEX
        {
            hh3cDot11SSIDIndex
        }
    ::= { hh3cDot11TrafficTable 1 }

Hh3cDot11TrafficEntry ::= SEQUENCE
    {
        hh3cDot11SSIDIndex             OCTET STRING,
        hh3cDot11UpPacketNumber        Counter64,
        hh3cDot11UpByteNumber          Counter64,
        hh3cDot11DownPacketNumber      Counter64,
        hh3cDot11DownByteNumber        Counter64
    }

hh3cDot11SSIDIndex OBJECT-TYPE
    SYNTAX      OCTET STRING
    MAX-ACCESS  not-accessible
    STATUS      current
    DESCRIPTION
        "Represents the SSID."
    ::= { hh3cDot11TrafficEntry 1 }

hh3cDot11UpPacketNumber OBJECT-TYPE
    SYNTAX      Counter64
    MAX-ACCESS  read-only
    STATUS      current
    DESCRIPTION
        "Represents the packet count of up link."
    ::= { hh3cDot11TrafficEntry 2 }

hh3cDot11UpByteNumber OBJECT-TYPE
    SYNTAX      Counter64
    MAX-ACCESS  read-only
    STATUS      current
    DESCRIPTION
        "Represents the byte count of up link."
    ::= { hh3cDot11TrafficEntry 3 }

hh3cDot11DownPacketNumber OBJECT-TYPE
    SYNTAX      Counter64
    MAX-ACCESS  read-only
    STATUS      current
    DESCRIPTION
        "Represents the packet count of down link."
    ::= { hh3cDot11TrafficEntry 4 }

hh3cDot11DownByteNumber OBJECT-TYPE
    SYNTAX      Counter64
    MAX-ACCESS  read-only
    STATUS      current
    DESCRIPTION
        "Represents the byte count of down link."
    ::= { hh3cDot11TrafficEntry 5 }

-- *****************************************************************************
-- *  End of hh3cDot11TrafficTable Definition
-- *****************************************************************************

-- *****************************************************************************
-- *  hh3cDot11APEchoStatisTable Definition
-- *****************************************************************************
hh3cDot11APEchoStatisTable OBJECT-TYPE
    SYNTAX      SEQUENCE OF Hh3cDot11APEchoInfoStatisEntry
    MAX-ACCESS  not-accessible
    STATUS      current
    DESCRIPTION
        "The table will provide the Echo statistic of this AP."
    ::= { hh3cDot11APStatisGroup 28 }

hh3cDot11APEchoInfoStatisEntry OBJECT-TYPE
    SYNTAX      Hh3cDot11APEchoInfoStatisEntry
    MAX-ACCESS  not-accessible
    STATUS      current
    DESCRIPTION
        "Each entry of the table will provide the Echo statistic
        of this AP."
    INDEX
        {
            hh3cDot11CurAPID
        }
    ::= { hh3cDot11APEchoStatisTable 1 }

Hh3cDot11APEchoInfoStatisEntry ::= SEQUENCE
    {
        hh3cDot11APEchoAvgDelay                 Integer32,
        hh3cDot11APEchoRequestCnt               Counter64,
        hh3cDot11APEchoRespLossCnt              Counter64
    }

hh3cDot11APEchoAvgDelay OBJECT-TYPE
    SYNTAX      Integer32
    UNITS       "millisecond"
    MAX-ACCESS  read-only
    STATUS      current
    DESCRIPTION
        "This object represents the average time delay of heart beat in this AP."
    ::= { hh3cDot11APEchoInfoStatisEntry 1 }

hh3cDot11APEchoRequestCnt OBJECT-TYPE
    SYNTAX      Counter64
    MAX-ACCESS  read-only
    STATUS      current
    DESCRIPTION
        "This object represents the count of echo request in this AP."
    ::= { hh3cDot11APEchoInfoStatisEntry 2 }

hh3cDot11APEchoRespLossCnt OBJECT-TYPE
    SYNTAX      Counter64
    MAX-ACCESS  read-only
    STATUS      current
    DESCRIPTION
        "This object represents the loss count of echo response in this AP."
    ::= { hh3cDot11APEchoInfoStatisEntry 3 }

-- *****************************************************************************
-- *  End of hh3cDot11APEchoStatisTable Definition
-- *****************************************************************************

-- *****************************************************************************
-- *  hh3cDot11APUserSecAuthTypeStatisTable Definition
-- *****************************************************************************
hh3cDot11APUserSecAuthTypeStatisTable OBJECT-TYPE
    SYNTAX      SEQUENCE OF Hh3cDot11APUserSecAuthTypeStatisEntry
    MAX-ACCESS  not-accessible
    STATUS      current
    DESCRIPTION
        "The table will provide the user authentication type statistic for this AP."
    ::= { hh3cDot11APStatisGroup 29 }

hh3cDot11APUserSecAuthTypeStatisEntry OBJECT-TYPE
    SYNTAX      Hh3cDot11APUserSecAuthTypeStatisEntry
    MAX-ACCESS  not-accessible
    STATUS      current
    DESCRIPTION
        "Each entry of the table will provide the user authentication type statistic
        for this AP."
    INDEX
        {
            hh3cDot11CurAPID
        }
    ::= { hh3cDot11APUserSecAuthTypeStatisTable 1 }

Hh3cDot11APUserSecAuthTypeStatisEntry ::= SEQUENCE
    {
        hh3cDot11APPortalOnlineUserNum          Integer32,
        hh3cDot11APAuthFreeOnlineUserNum        Integer32,
        hh3cDot11APAssocAuthOnlineUserNum       Integer32,
        hh3cDot11APMacAuthOnlineUserNum         Integer32,
        hh3cDot11APAllPortalUserOnlineTime      TimeTicks,
        hh3cDot11APAllAuthFreeUserOnlineTime    TimeTicks,
        hh3cDot11APAllAssocAuthUserOnlineTime   TimeTicks,
        hh3cDot11APAllMacAuthUserOnlineTime     TimeTicks,
        hh3cDot11APPortalUserLostCnntCnt        Counter32,
        hh3cDot11APAuthFreeUserLostCnntCnt      Counter32,
        hh3cDot11APAssocAuthUserLostCnntCnt     Counter32,
        hh3cDot11APMacAuthUserLostCnntCnt       Counter32,
        hh3cDot11APPortalAuthReqCnt             Counter32,
        hh3cDot11APAssocAuthReqCnt              Counter32,
        hh3cDot11APMacAuthReqCnt                Counter32,
        hh3cDot11APPortalAuthSucCnt             Counter32,
        hh3cDot11APAssocAuthSucCnt              Counter32,
        hh3cDot11APMacAuthSucCnt                Counter32,
        hh3cDot11APPortalAuthReqFailCnt         Counter32,
        hh3cDot11APAssocAuthReqFailCnt          Counter32,
        hh3cDot11APMacAuthReqFailCnt            Counter32,
        hh3cDot11APAutoAuthOnlineUserNumCM      Integer32,
        hh3cDot11APAllAutoAuthUserOnlineTimeCM  TimeTicks,
        hh3cDot11APAutoAuthUserLostCnntCntCM    Counter32,
        hh3cDot11APAutoAuthReqCntCM             Counter32,
        hh3cDot11APAutoAuthSucCntCM             Counter32,
        hh3cDot11APAutoAuthReqFailCntCM         Counter32
    }

hh3cDot11APPortalOnlineUserNum OBJECT-TYPE
    SYNTAX      Integer32
    MAX-ACCESS  read-only
    STATUS      current
    DESCRIPTION
        "Represents the number of online portal users of this AP, including
        MAC-trigger and IMSIAuth users."
    ::= { hh3cDot11APUserSecAuthTypeStatisEntry 1 }

hh3cDot11APAuthFreeOnlineUserNum OBJECT-TYPE
    SYNTAX      Integer32
    MAX-ACCESS  read-only
    STATUS      current
    DESCRIPTION
        "Represents the online number of user free authenticated with this AP."
    ::= { hh3cDot11APUserSecAuthTypeStatisEntry 2 }

hh3cDot11APAssocAuthOnlineUserNum OBJECT-TYPE
    SYNTAX      Integer32
    MAX-ACCESS  read-only
    STATUS      current
    DESCRIPTION
        "Represents the number of online users authenticated by associated
        authentication with this AP, excluding AutoAuth users."
    ::= { hh3cDot11APUserSecAuthTypeStatisEntry 3 }

hh3cDot11APMacAuthOnlineUserNum OBJECT-TYPE
    SYNTAX      Integer32
    MAX-ACCESS  read-only
    STATUS      current
    DESCRIPTION
        "Represents the online number of user MAC address authenticated with this AP."
    ::= { hh3cDot11APUserSecAuthTypeStatisEntry 4 }

hh3cDot11APAllPortalUserOnlineTime OBJECT-TYPE
    SYNTAX      TimeTicks
    MAX-ACCESS  read-only
    STATUS      current
    DESCRIPTION
        "Represents the online time of all user portal authenticated with this AP."
    ::= { hh3cDot11APUserSecAuthTypeStatisEntry 5 }

hh3cDot11APAllAuthFreeUserOnlineTime OBJECT-TYPE
    SYNTAX      TimeTicks
    MAX-ACCESS  read-only
    STATUS      current
    DESCRIPTION
        "Represents the online time of all user free authenticated with this AP."
    ::= { hh3cDot11APUserSecAuthTypeStatisEntry 6 }

hh3cDot11APAllAssocAuthUserOnlineTime OBJECT-TYPE
    SYNTAX      TimeTicks
    MAX-ACCESS  read-only
    STATUS      current
    DESCRIPTION
        "Represents the online time of all user associated authenticated with this AP."
    ::= { hh3cDot11APUserSecAuthTypeStatisEntry 7 }

hh3cDot11APAllMacAuthUserOnlineTime OBJECT-TYPE
    SYNTAX      TimeTicks
    MAX-ACCESS  read-only
    STATUS      current
    DESCRIPTION
        "Represents the online time of all user MAC address authenticated with this AP."
    ::= { hh3cDot11APUserSecAuthTypeStatisEntry 8 }

hh3cDot11APPortalUserLostCnntCnt OBJECT-TYPE
    SYNTAX      Counter32
    MAX-ACCESS  read-only
    STATUS      current
    DESCRIPTION
        "Represents the lost connective count of user portal authenticated with this AP."
    ::= { hh3cDot11APUserSecAuthTypeStatisEntry 9 }

hh3cDot11APAuthFreeUserLostCnntCnt OBJECT-TYPE
    SYNTAX      Counter32
    MAX-ACCESS  read-only
    STATUS      current
    DESCRIPTION
        "Represents the lost connective count of user free authenticated with this AP."
    ::= { hh3cDot11APUserSecAuthTypeStatisEntry 10 }

hh3cDot11APAssocAuthUserLostCnntCnt OBJECT-TYPE
    SYNTAX      Counter32
    MAX-ACCESS  read-only
    STATUS      current
    DESCRIPTION
        "Represents the lost connective count of user associate authenticated with this AP."
    ::= { hh3cDot11APUserSecAuthTypeStatisEntry 11 }

hh3cDot11APMacAuthUserLostCnntCnt OBJECT-TYPE
    SYNTAX      Counter32
    MAX-ACCESS  read-only
    STATUS      current
    DESCRIPTION
        "Represents the lost connective count of user MAC address authenticated with this AP."
    ::= { hh3cDot11APUserSecAuthTypeStatisEntry 12 }

hh3cDot11APPortalAuthReqCnt OBJECT-TYPE
    SYNTAX      Counter32
    MAX-ACCESS  read-only
    STATUS      current
    DESCRIPTION
        "Represents the request count of user portal authenticated with this AP."
    ::= { hh3cDot11APUserSecAuthTypeStatisEntry 13 }

hh3cDot11APAssocAuthReqCnt OBJECT-TYPE
    SYNTAX      Counter32
    MAX-ACCESS  read-only
    STATUS      current
    DESCRIPTION
        "Represents the request count of user associate authenticated with this AP."
    ::= { hh3cDot11APUserSecAuthTypeStatisEntry 14 }

hh3cDot11APMacAuthReqCnt OBJECT-TYPE
    SYNTAX      Counter32
    MAX-ACCESS  read-only
    STATUS      current
    DESCRIPTION
        "Represents the request count of user MAC address authenticated with this AP."
    ::= { hh3cDot11APUserSecAuthTypeStatisEntry 15 }

hh3cDot11APPortalAuthSucCnt OBJECT-TYPE
    SYNTAX      Counter32
    MAX-ACCESS  read-only
    STATUS      current
    DESCRIPTION
        "Represents the count of user portal authenticated successed with this AP."
    ::= { hh3cDot11APUserSecAuthTypeStatisEntry 16 }

hh3cDot11APAssocAuthSucCnt OBJECT-TYPE
    SYNTAX      Counter32
    MAX-ACCESS  read-only
    STATUS      current
    DESCRIPTION
        "Represents the count of user associate authenticated successed with this AP."
    ::= { hh3cDot11APUserSecAuthTypeStatisEntry 17 }

hh3cDot11APMacAuthSucCnt OBJECT-TYPE
    SYNTAX      Counter32
    MAX-ACCESS  read-only
    STATUS      current
    DESCRIPTION
        "Represents the count of user MAC address authenticated successed with this AP."
    ::= { hh3cDot11APUserSecAuthTypeStatisEntry 18 }

hh3cDot11APPortalAuthReqFailCnt OBJECT-TYPE
    SYNTAX      Counter32
    MAX-ACCESS  read-only
    STATUS      current
    DESCRIPTION
        "Represents the count of user portal authenticated failed with this AP."
    ::= { hh3cDot11APUserSecAuthTypeStatisEntry 19 }

hh3cDot11APAssocAuthReqFailCnt OBJECT-TYPE
    SYNTAX      Counter32
    MAX-ACCESS  read-only
    STATUS      current
    DESCRIPTION
        "Represents the count of user associate authenticated failed with this AP."
    ::= { hh3cDot11APUserSecAuthTypeStatisEntry 20 }

hh3cDot11APMacAuthReqFailCnt OBJECT-TYPE
    SYNTAX      Counter32
    MAX-ACCESS  read-only
    STATUS      current
    DESCRIPTION
        "Represents the count of user MAC address authenticated failed with this AP."
    ::= { hh3cDot11APUserSecAuthTypeStatisEntry 21 }

hh3cDot11APAutoAuthOnlineUserNumCM OBJECT-TYPE
    SYNTAX      Integer32
    MAX-ACCESS  read-only
    STATUS      current
    DESCRIPTION
        "Represents the number of online users authenticated by auto authentication
        with this AP."
    ::= { hh3cDot11APUserSecAuthTypeStatisEntry 22 }

hh3cDot11APAllAutoAuthUserOnlineTimeCM OBJECT-TYPE
    SYNTAX      TimeTicks
    MAX-ACCESS  read-only
    STATUS      current
    DESCRIPTION
        "Represents the online time of users authenticated by auto authentication
        with this AP."
    ::= { hh3cDot11APUserSecAuthTypeStatisEntry 23 }

hh3cDot11APAutoAuthUserLostCnntCntCM OBJECT-TYPE
    SYNTAX      Counter32
    MAX-ACCESS  read-only
    STATUS      current
    DESCRIPTION
        "Represents the disconnection count of AutoAuth users."
    ::= { hh3cDot11APUserSecAuthTypeStatisEntry 24 }

hh3cDot11APAutoAuthReqCntCM OBJECT-TYPE
    SYNTAX      Counter32
    MAX-ACCESS  read-only
    STATUS      current
    DESCRIPTION
        "Represents the count of AutoAuth requests with this AP."
    ::= { hh3cDot11APUserSecAuthTypeStatisEntry 25 }

hh3cDot11APAutoAuthSucCntCM OBJECT-TYPE
    SYNTAX      Counter32
    MAX-ACCESS  read-only
    STATUS      current
    DESCRIPTION
        "Represents the count of successful AutoAuth authentications with this AP."
    ::= { hh3cDot11APUserSecAuthTypeStatisEntry 26 }

hh3cDot11APAutoAuthReqFailCntCM OBJECT-TYPE
    SYNTAX      Counter32
    MAX-ACCESS  read-only
    STATUS      current
    DESCRIPTION
        "Represents the count of failed AutoAuth requests with this AP."
    ::= { hh3cDot11APUserSecAuthTypeStatisEntry 27 }

-- *****************************************************************************
-- *  End of hh3cDot11APUserSecAuthTypeStatisTable Definition
-- *****************************************************************************

-- *****************************************************************************
-- *  hh3cDot11RadioRxStatis64Table Definition
-- *****************************************************************************
hh3cDot11RadioRxStatis64Table OBJECT-TYPE
    SYNTAX      SEQUENCE OF Hh3cDot11RadioRxStatis64Entry
    MAX-ACCESS  not-accessible
    STATUS      current
    DESCRIPTION
        "The table will provide the reception statistic for a specific
        radio of AP."
    ::= { hh3cDot11APStatisGroup 30 }

hh3cDot11RadioRxStatis64Entry OBJECT-TYPE
    SYNTAX      Hh3cDot11RadioRxStatis64Entry
    MAX-ACCESS  not-accessible
    STATUS      current
    DESCRIPTION
        "Each entry of the table will provide the reception statistic
        data for each radio of a specific AP."
    INDEX
        {
            hh3cDot11CurAPID,
            hh3cDot11RadioID
        }
    ::= { hh3cDot11RadioRxStatis64Table 1 }

Hh3cDot11RadioRxStatis64Entry ::= SEQUENCE
    {
        hh3cDot11Rx64FrameDupCnt          Counter64,
        hh3cDot11Rx64FrameCnt             Counter64,
        hh3cDot11Rx64UcastFrameCnt        Counter64,
        hh3cDot11Rx64BcastFrameCnt        Counter64,
        hh3cDot11Rx64McastFrameCnt        Counter64,
        hh3cDot11Rx64DiscardFrameCnt      Counter64,
        hh3cDot11Rx64FragCnt              Counter64,
        hh3cDot11Rx64FcsErrCnt            Counter64,
        hh3cDot11Rx64FrameBytes           Counter64,
        hh3cDot11Rx64UcastFrameBytes      Counter64,
        hh3cDot11Rx64BcastFrameBytes      Counter64,
        hh3cDot11Rx64McastFrameBytes      Counter64,
        hh3cDot11Rx64DiscardFrameBytes    Counter64,
        hh3cDot11Rx64MgmtFrameCnt         Counter64,
        hh3cDot11Rx64CtrlFrameCnt         Counter64,
        hh3cDot11Rx64DataFrameCnt         Counter64,
        hh3cDot11Rx64DecryptErrorCnt      Counter64,
        hh3cDot11Rx64AuthenFrameCnt       Counter64,
        hh3cDot11Rx64AssociateFrameCnt    Counter64,
        hh3cDot11Rx64PhyErrorCnt          Counter64,
        hh3cDot11Rx64MICErrorCnt          Counter64,
        hh3cDot11Rx64DataFrameBytes       Counter64,
        hh3cDot11Rx64PayloadBytes         Counter64,
        hh3cDot11Rx64DataFrameBytesCM     Counter64
    }

hh3cDot11Rx64FrameDupCnt OBJECT-TYPE
    SYNTAX      Counter64
    MAX-ACCESS  read-only
    STATUS      current
    DESCRIPTION
        "Represents the number of duplicate frames reception."
    ::= { hh3cDot11RadioRxStatis64Entry 1 }

hh3cDot11Rx64FrameCnt OBJECT-TYPE
    SYNTAX      Counter64
    MAX-ACCESS  read-only
    STATUS      current
    DESCRIPTION
        "Represents the number of frames reception."
    ::= { hh3cDot11RadioRxStatis64Entry 2 }

hh3cDot11Rx64UcastFrameCnt OBJECT-TYPE
    SYNTAX      Counter64
    MAX-ACCESS  read-only
    STATUS      current
    DESCRIPTION
        "Represents the number of unicast frames reception."
    ::= { hh3cDot11RadioRxStatis64Entry 3 }

hh3cDot11Rx64BcastFrameCnt OBJECT-TYPE
    SYNTAX      Counter64
    MAX-ACCESS  read-only
    STATUS      current
    DESCRIPTION
        "Represents the number of broadcast frames reception."
    ::= { hh3cDot11RadioRxStatis64Entry 4 }

hh3cDot11Rx64McastFrameCnt OBJECT-TYPE
    SYNTAX      Counter64
    MAX-ACCESS  read-only
    STATUS      current
    DESCRIPTION
        "Represents the number of multicast frames reception."
    ::= { hh3cDot11RadioRxStatis64Entry 5 }

hh3cDot11Rx64DiscardFrameCnt OBJECT-TYPE
    SYNTAX      Counter64
    MAX-ACCESS  read-only
    STATUS      current
    DESCRIPTION
        "Represents the number of discarded frames reception."
    ::= { hh3cDot11RadioRxStatis64Entry 6 }

hh3cDot11Rx64FragCnt OBJECT-TYPE
    SYNTAX      Counter64
    MAX-ACCESS  read-only
    STATUS      current
    DESCRIPTION
        "Represents the number of frame fragments reception."
    ::= { hh3cDot11RadioRxStatis64Entry 7 }

hh3cDot11Rx64FcsErrCnt OBJECT-TYPE
    SYNTAX      Counter64
    MAX-ACCESS  read-only
    STATUS      current
    DESCRIPTION
        "Represents the number of FCS error frames reception."
    ::= { hh3cDot11RadioRxStatis64Entry 8 }

hh3cDot11Rx64FrameBytes OBJECT-TYPE
    SYNTAX      Counter64
    MAX-ACCESS  read-only
    STATUS      current
    DESCRIPTION
        "Represents the bytes of frames reception."
    ::= { hh3cDot11RadioRxStatis64Entry 9 }

hh3cDot11Rx64UcastFrameBytes OBJECT-TYPE
    SYNTAX      Counter64
    MAX-ACCESS  read-only
    STATUS      current
    DESCRIPTION
        "Represents the bytes of unicast frames reception."
    ::= { hh3cDot11RadioRxStatis64Entry 10 }

hh3cDot11Rx64BcastFrameBytes OBJECT-TYPE
    SYNTAX      Counter64
    MAX-ACCESS  read-only
    STATUS      current
    DESCRIPTION
        "Represents the bytes of broadcast frames reception."
    ::= { hh3cDot11RadioRxStatis64Entry 11 }

hh3cDot11Rx64McastFrameBytes OBJECT-TYPE
    SYNTAX      Counter64
    MAX-ACCESS  read-only
    STATUS      current
    DESCRIPTION
        "Represents the bytes of multicast frames reception."
    ::= { hh3cDot11RadioRxStatis64Entry 12 }

hh3cDot11Rx64DiscardFrameBytes OBJECT-TYPE
    SYNTAX      Counter64
    MAX-ACCESS  read-only
    STATUS      current
    DESCRIPTION
        "Represents the bytes of discarded frames reception."
    ::= { hh3cDot11RadioRxStatis64Entry 13 }

hh3cDot11Rx64MgmtFrameCnt OBJECT-TYPE
    SYNTAX      Counter64
    MAX-ACCESS  read-only
    STATUS      current
    DESCRIPTION
        "Represents the number of management frames reception."
    ::= { hh3cDot11RadioRxStatis64Entry 14 }

hh3cDot11Rx64CtrlFrameCnt OBJECT-TYPE
    SYNTAX      Counter64
    MAX-ACCESS  read-only
    STATUS      current
    DESCRIPTION
        "Represents the number of control frames reception."
    ::= { hh3cDot11RadioRxStatis64Entry 15 }

hh3cDot11Rx64DataFrameCnt OBJECT-TYPE
    SYNTAX      Counter64
    MAX-ACCESS  read-only
    STATUS      current
    DESCRIPTION
        "Represents the number of data frames reception."
    ::= { hh3cDot11RadioRxStatis64Entry 16 }

hh3cDot11Rx64DecryptErrorCnt OBJECT-TYPE
    SYNTAX      Counter64
    MAX-ACCESS  read-only
    STATUS      current
    DESCRIPTION
        "Represents the number of decryption error reception."
    ::= { hh3cDot11RadioRxStatis64Entry 17 }

hh3cDot11Rx64AuthenFrameCnt OBJECT-TYPE
    SYNTAX      Counter64
    MAX-ACCESS  read-only
    STATUS      current
    DESCRIPTION
        "Represents the number of authentication frame reception."
    ::= { hh3cDot11RadioRxStatis64Entry 18 }

hh3cDot11Rx64AssociateFrameCnt OBJECT-TYPE
    SYNTAX      Counter64
    MAX-ACCESS  read-only
    STATUS      current
    DESCRIPTION
        "Represents the number of associate frame reception."
    ::= { hh3cDot11RadioRxStatis64Entry 19 }

hh3cDot11Rx64PhyErrorCnt OBJECT-TYPE
    SYNTAX      Counter64
    MAX-ACCESS  read-only
    STATUS      current
    DESCRIPTION
        "Represents the number of physical error reception."
    ::= { hh3cDot11RadioRxStatis64Entry 20 }

hh3cDot11Rx64MICErrorCnt OBJECT-TYPE
    SYNTAX      Counter64
    MAX-ACCESS  read-only
    STATUS      current
    DESCRIPTION
        "Represents the number of MIC verification error reception."
    ::= { hh3cDot11RadioRxStatis64Entry 21 }

hh3cDot11Rx64DataFrameBytes OBJECT-TYPE
    SYNTAX      Counter64
    MAX-ACCESS  read-only
    STATUS      current
    DESCRIPTION
        "Represents the bytes of data frames reception."
    ::= { hh3cDot11RadioRxStatis64Entry 22 }

hh3cDot11Rx64PayloadBytes OBJECT-TYPE
    SYNTAX      Counter64
    MAX-ACCESS  read-only
    STATUS      current
    DESCRIPTION
        "Represents the payload bytes of data frames reception."
    ::= { hh3cDot11RadioRxStatis64Entry 23 }

hh3cDot11Rx64DataFrameBytesCM OBJECT-TYPE
    SYNTAX      Counter64
    MAX-ACCESS  read-only
    STATUS      current
    DESCRIPTION
        "Represents the number of received data frames, excluding retransmitted
        frames."
    ::= { hh3cDot11RadioRxStatis64Entry 24 }

-- *****************************************************************************
-- *  End of hh3cDot11RadioRxStatis64Table Definition
-- *****************************************************************************

-- *****************************************************************************
-- *  hh3cDot11RadioTxStatis64Table Definition
-- *****************************************************************************
hh3cDot11RadioTxStatis64Table OBJECT-TYPE
    SYNTAX      SEQUENCE OF Hh3cDot11RadioTxStatis64Entry
    MAX-ACCESS  not-accessible
    STATUS      current
    DESCRIPTION
        "The table will provide the transmission statistic for a
        specific radio of AP."
    ::= { hh3cDot11APStatisGroup 31 }

hh3cDot11RadioTxStatis64Entry OBJECT-TYPE
    SYNTAX      Hh3cDot11RadioTxStatis64Entry
    MAX-ACCESS  not-accessible
    STATUS      current
    DESCRIPTION
        "Each entry of the table will provide the transmission
        statistic data for each radio of a specific AP."
    INDEX
        {
            hh3cDot11CurAPID,
            hh3cDot11RadioID
        }
    ::= { hh3cDot11RadioTxStatis64Table 1 }

Hh3cDot11RadioTxStatis64Entry ::= SEQUENCE
    {
        hh3cDot11Tx64FragCnt              Counter64,
        hh3cDot11Tx64FailedCnt            Counter64,
        hh3cDot11Tx64RetryCnt             Counter64,
        hh3cDot11Tx64MultiRetryCnt        Counter64,
        hh3cDot11Tx64RtsSuccessCnt        Counter64,
        hh3cDot11Tx64RtsFailCnt           Counter64,
        hh3cDot11Tx64AckFailCnt           Counter64,
        hh3cDot11Tx64FrameCnt             Counter64,
        hh3cDot11Tx64UcastFrameCnt        Counter64,
        hh3cDot11Tx64BcastFrameCnt        Counter64,
        hh3cDot11Tx64McastFrameCnt        Counter64,
        hh3cDot11Tx64DiscardFrameCnt      Counter64,
        hh3cDot11Tx64FrameBytes           Counter64,
        hh3cDot11Tx64UcastFrameBytes      Counter64,
        hh3cDot11Tx64BcastFrameBytes      Counter64,
        hh3cDot11Tx64McastFrameBytes      Counter64,
        hh3cDot11Tx64DiscardFrameBytes    Counter64,
        hh3cDot11Tx64AuthenFrameCnt       Counter64,
        hh3cDot11Tx64AssociateFrameCnt    Counter64,
        hh3cDot11Tx64DataFrameCnt         Counter64,
        hh3cDot11Tx64DataFrameBytes       Counter64,
        hh3cDot11Tx64MSDUCnt              Counter64,
        hh3cDot11Tx64DiscardMSDUCnt       Counter64,
        hh3cDot11Tx64RetryMSDUCnt         Counter64,
        hh3cDot11Tx64PayloadBytes         Counter64,
        hh3cDot11Tx64MgtFrameCnt          Counter64,
        hh3cDot11Tx64CtrlFrameCnt         Counter64,
        hh3cDot11Tx64MACErrCnt            Counter64,
        hh3cDot11Tx64ErrFrameCnt          Counter64
    }

hh3cDot11Tx64FragCnt OBJECT-TYPE
    SYNTAX      Counter64
    MAX-ACCESS  read-only
    STATUS      current
    DESCRIPTION
        "Represents the number of fragmented frames transmission."
    ::= { hh3cDot11RadioTxStatis64Entry 1 }

hh3cDot11Tx64FailedCnt OBJECT-TYPE
    SYNTAX      Counter64
    MAX-ACCESS  read-only
    STATUS      current
    DESCRIPTION
        "Represents the number of failures transmission."
    ::= { hh3cDot11RadioTxStatis64Entry 2 }

hh3cDot11Tx64RetryCnt OBJECT-TYPE
    SYNTAX      Counter64
    MAX-ACCESS  read-only
    STATUS      current
    DESCRIPTION
        "Represents the number of retries transmission."
    ::= { hh3cDot11RadioTxStatis64Entry 3 }

hh3cDot11Tx64MultiRetryCnt OBJECT-TYPE
    SYNTAX      Counter64
    MAX-ACCESS  read-only
    STATUS      current
    DESCRIPTION
        "Represents the number of transmits that required more than
        one retry transmission."
    ::= { hh3cDot11RadioTxStatis64Entry 4 }

hh3cDot11Tx64RtsSuccessCnt OBJECT-TYPE
    SYNTAX      Counter64
    MAX-ACCESS  read-only
    STATUS      current
    DESCRIPTION
        "Represents the number of successful RTS (Request to send)
        transmission."
    ::= { hh3cDot11RadioTxStatis64Entry 5 }

hh3cDot11Tx64RtsFailCnt OBJECT-TYPE
    SYNTAX      Counter64
    MAX-ACCESS  read-only
    STATUS      current
    DESCRIPTION
        "Represents the number of RTS failures transmission."
    ::= { hh3cDot11RadioTxStatis64Entry 6 }

hh3cDot11Tx64AckFailCnt OBJECT-TYPE
    SYNTAX      Counter64
    MAX-ACCESS  read-only
    STATUS      current
    DESCRIPTION
        "Represents the number of acknowledgement failures transmission."
    ::= { hh3cDot11RadioTxStatis64Entry 7 }

hh3cDot11Tx64FrameCnt OBJECT-TYPE
    SYNTAX      Counter64
    MAX-ACCESS  read-only
    STATUS      current
    DESCRIPTION
        "Represents the total number of frames transmission."
    ::= { hh3cDot11RadioTxStatis64Entry 8 }

hh3cDot11Tx64UcastFrameCnt OBJECT-TYPE
    SYNTAX      Counter64
    MAX-ACCESS  read-only
    STATUS      current
    DESCRIPTION
        "Represents the number of unicast frames transmission."
    ::= { hh3cDot11RadioTxStatis64Entry 9 }

hh3cDot11Tx64BcastFrameCnt OBJECT-TYPE
    SYNTAX      Counter64
    MAX-ACCESS  read-only
    STATUS      current
    DESCRIPTION
        "Represents the number of broadcast frames transmission."
    ::= { hh3cDot11RadioTxStatis64Entry 10 }

hh3cDot11Tx64McastFrameCnt OBJECT-TYPE
    SYNTAX      Counter64
    MAX-ACCESS  read-only
    STATUS      current
    DESCRIPTION
        "Represents the number of multicast frames transmission."
    ::= { hh3cDot11RadioTxStatis64Entry 11 }

hh3cDot11Tx64DiscardFrameCnt OBJECT-TYPE
    SYNTAX      Counter64
    MAX-ACCESS  read-only
    STATUS      current
    DESCRIPTION
        "Represents the number of discarded frames transmission."
    ::= { hh3cDot11RadioTxStatis64Entry 12 }

hh3cDot11Tx64FrameBytes OBJECT-TYPE
    SYNTAX      Counter64
    MAX-ACCESS  read-only
    STATUS      current
    DESCRIPTION
        "Represents the total bytes of frames transmission."
    ::= { hh3cDot11RadioTxStatis64Entry 13 }

hh3cDot11Tx64UcastFrameBytes OBJECT-TYPE
    SYNTAX      Counter64
    MAX-ACCESS  read-only
    STATUS      current
    DESCRIPTION
        "Represents the bytes of unicast frames transmission."
    ::= { hh3cDot11RadioTxStatis64Entry 14 }

hh3cDot11Tx64BcastFrameBytes OBJECT-TYPE
    SYNTAX      Counter64
    MAX-ACCESS  read-only
    STATUS      current
    DESCRIPTION
        "Represents the bytes of broadcast frames transmission."
    ::= { hh3cDot11RadioTxStatis64Entry 15 }

hh3cDot11Tx64McastFrameBytes OBJECT-TYPE
    SYNTAX      Counter64
    MAX-ACCESS  read-only
    STATUS      current
    DESCRIPTION
        "Represents the bytes of multicast frames transmission."
    ::= { hh3cDot11RadioTxStatis64Entry 16 }

hh3cDot11Tx64DiscardFrameBytes OBJECT-TYPE
    SYNTAX      Counter64
    MAX-ACCESS  read-only
    STATUS      current
    DESCRIPTION
        "Represents the bytes of discarded frames transmission."
    ::= { hh3cDot11RadioTxStatis64Entry 17 }

hh3cDot11Tx64AuthenFrameCnt OBJECT-TYPE
    SYNTAX      Counter64
    MAX-ACCESS  read-only
    STATUS      current
    DESCRIPTION
        "Represents the number of authentication frame transmission."
    ::= { hh3cDot11RadioTxStatis64Entry 18 }

hh3cDot11Tx64AssociateFrameCnt OBJECT-TYPE
    SYNTAX      Counter64
    MAX-ACCESS  read-only
    STATUS      current
    DESCRIPTION
        "Represents the number of associate frame transmission."
    ::= { hh3cDot11RadioTxStatis64Entry 19 }

hh3cDot11Tx64DataFrameCnt OBJECT-TYPE
    SYNTAX      Counter64
    MAX-ACCESS  read-only
    STATUS      current
    DESCRIPTION
        "Represents the number of data frame transmission."
    ::= { hh3cDot11RadioTxStatis64Entry 20 }

hh3cDot11Tx64DataFrameBytes OBJECT-TYPE
    SYNTAX      Counter64
    MAX-ACCESS  read-only
    STATUS      current
    DESCRIPTION
        "Represents the bytes of data frame transmission."
    ::= { hh3cDot11RadioTxStatis64Entry 21 }

hh3cDot11Tx64MSDUCnt OBJECT-TYPE
    SYNTAX      Counter64
    MAX-ACCESS  read-only
    STATUS      current
    DESCRIPTION
        "Represents the total number of MSDU transmission."
    ::= { hh3cDot11RadioTxStatis64Entry 22 }

hh3cDot11Tx64DiscardMSDUCnt OBJECT-TYPE
    SYNTAX      Counter64
    MAX-ACCESS  read-only
    STATUS      current
    DESCRIPTION
        "Represents the number of discarded MSDU transmission."
    ::= { hh3cDot11RadioTxStatis64Entry 23 }

hh3cDot11Tx64RetryMSDUCnt OBJECT-TYPE
    SYNTAX      Counter64
    MAX-ACCESS  read-only
    STATUS      current
    DESCRIPTION
        "Represents the number of retransfer MSDU transmission."
    ::= { hh3cDot11RadioTxStatis64Entry 24 }

hh3cDot11Tx64PayloadBytes OBJECT-TYPE
    SYNTAX      Counter64
    MAX-ACCESS  read-only
    STATUS      current
    DESCRIPTION
        "Represents the payload bytes of data frames transmission."
    ::= { hh3cDot11RadioTxStatis64Entry 25 }

hh3cDot11Tx64MgtFrameCnt OBJECT-TYPE
    SYNTAX      Counter64
    MAX-ACCESS  read-only
    STATUS      current
    DESCRIPTION
        "Represents the number of management frames transmission."
    ::= { hh3cDot11RadioTxStatis64Entry 26 }

hh3cDot11Tx64CtrlFrameCnt OBJECT-TYPE
    SYNTAX      Counter64
    MAX-ACCESS  read-only
    STATUS      current
    DESCRIPTION
        "Represents the number of control frames transmission."
    ::= { hh3cDot11RadioTxStatis64Entry 27 }
hh3cDot11Tx64MACErrCnt OBJECT-TYPE
    SYNTAX      Counter64
    MAX-ACCESS  read-only
    STATUS      current
    DESCRIPTION
        "Represents the number of MAC error frame transmission."
    ::= { hh3cDot11RadioTxStatis64Entry 28 }

hh3cDot11Tx64ErrFrameCnt OBJECT-TYPE
    SYNTAX      Counter64
    MAX-ACCESS  read-only
    STATUS      current
    DESCRIPTION
        "Represents the number of error frame transmission."
    ::= { hh3cDot11RadioTxStatis64Entry 29 }

-- *****************************************************************************
-- *  End of hh3cDot11RadioTxStatis64Table Definition
-- *****************************************************************************

-- *****************************************************************************
-- *  hh3cDot11BSSRxStatis64Table Definition
-- *****************************************************************************
hh3cDot11BSSRxStatis64Table OBJECT-TYPE
    SYNTAX      SEQUENCE OF Hh3cDot11BSSRxStatis64Entry
    MAX-ACCESS  not-accessible
    STATUS      current
    DESCRIPTION
        "The table will provide the reception statistic for a
        specific BSS on a radio."
    ::= { hh3cDot11APStatisGroup 32 }

hh3cDot11BSSRxStatis64Entry OBJECT-TYPE
    SYNTAX      Hh3cDot11BSSRxStatis64Entry
    MAX-ACCESS  not-accessible
    STATUS      current
    DESCRIPTION
        "Each entry of the table will provide the reception statistic data for
        each BSS on a specific radio."
    INDEX
        {
            hh3cDot11CurAPID,
            hh3cDot11RadioID,
            hh3cDot11WlanID
        }
    ::= { hh3cDot11BSSRxStatis64Table 1 }

Hh3cDot11BSSRxStatis64Entry ::= SEQUENCE
    {
        hh3cDot11BSSRx64FrameCnt             Counter64,
        hh3cDot11BSSRx64FrameBytes           Counter64,
        hh3cDot11BSSRx64DataFrameCnt         Counter64,
        hh3cDot11BSSRx64DataFrameBytes       Counter64,
        hh3cDot11BSSRx64AssocFrameCnt        Counter64,
        hh3cDot11BSSRx64PayloadBytes         Counter64,
        hh3cDot11BSSRx64UniFrameCnt          Counter64,
        hh3cDot11BSSRx64NonUniFrameCnt       Counter64,
        hh3cDot11BSSRx64AuthenFrameCnt       Counter64
    }

hh3cDot11BSSRx64FrameCnt OBJECT-TYPE
    SYNTAX      Counter64
    MAX-ACCESS  read-only
    STATUS      current
    DESCRIPTION
        "Represents the number of frames reception with this BSS."
    ::= { hh3cDot11BSSRxStatis64Entry 1 }

hh3cDot11BSSRx64FrameBytes OBJECT-TYPE
    SYNTAX      Counter64
    MAX-ACCESS  read-only
    STATUS      current
    DESCRIPTION
        "Represents the bytes of frames reception with this BSS."
    ::= { hh3cDot11BSSRxStatis64Entry 2 }

hh3cDot11BSSRx64DataFrameCnt OBJECT-TYPE
    SYNTAX      Counter64
    MAX-ACCESS  read-only
    STATUS      current
    DESCRIPTION
        "Represents the number of data frames reception with this BSS."
    ::= { hh3cDot11BSSRxStatis64Entry 3 }

hh3cDot11BSSRx64DataFrameBytes OBJECT-TYPE
    SYNTAX      Counter64
    MAX-ACCESS  read-only
    STATUS      current
    DESCRIPTION
        "Represents the bytes of data frames reception with this BSS."
    ::= { hh3cDot11BSSRxStatis64Entry 4 }

hh3cDot11BSSRx64AssocFrameCnt OBJECT-TYPE
    SYNTAX      Counter64
    MAX-ACCESS  read-only
    STATUS      current
    DESCRIPTION
        "Represents the number of associate frames reception with this BSS."
    ::= { hh3cDot11BSSRxStatis64Entry 5 }

hh3cDot11BSSRx64PayloadBytes OBJECT-TYPE
    SYNTAX      Counter64
    MAX-ACCESS  read-only
    STATUS      current
    DESCRIPTION
        "Represents the payload bytes of data frames reception with this BSS."
    ::= { hh3cDot11BSSRxStatis64Entry 6 }

hh3cDot11BSSRx64UniFrameCnt OBJECT-TYPE
    SYNTAX      Counter64
    MAX-ACCESS  read-only
    STATUS      current
    DESCRIPTION
        "Represents the number of unicast frames reception with this BSS."
    ::= { hh3cDot11BSSRxStatis64Entry 7 }

hh3cDot11BSSRx64NonUniFrameCnt  OBJECT-TYPE
    SYNTAX      Counter64
    MAX-ACCESS  read-only
    STATUS      current
    DESCRIPTION
        "Represents the number of non-unicast frames reception with this BSS."
    ::= { hh3cDot11BSSRxStatis64Entry 8 }

hh3cDot11BSSRx64AuthenFrameCnt OBJECT-TYPE
    SYNTAX      Counter64
    MAX-ACCESS  read-only
    STATUS      current
    DESCRIPTION
        "Represents the number of authentication frames reception with this BSS."
    ::= { hh3cDot11BSSRxStatis64Entry 9 }

-- *****************************************************************************
-- *  End of hh3cDot11BSSRxStatis64Table Definition
-- *****************************************************************************

-- *****************************************************************************
-- *  hh3cDot11BSSTxStatis64Table Definition
-- *****************************************************************************
hh3cDot11BSSTxStatis64Table OBJECT-TYPE
    SYNTAX      SEQUENCE OF Hh3cDot11BSSTxStatis64Entry
    MAX-ACCESS  not-accessible
    STATUS      current
    DESCRIPTION
        "The table will provide the transmission statistic for a
        specific BSS on a radio."
    ::= { hh3cDot11APStatisGroup 33 }

hh3cDot11BSSTxStatis64Entry OBJECT-TYPE
    SYNTAX      Hh3cDot11BSSTxStatis64Entry
    MAX-ACCESS  not-accessible
    STATUS      current
    DESCRIPTION
        "Each entry of the table will provide the transmission statistic data for
        each BSS on a specific radio."
    INDEX
        {
            hh3cDot11CurAPID,
            hh3cDot11RadioID,
            hh3cDot11WlanID
        }
    ::= { hh3cDot11BSSTxStatis64Table 1 }

Hh3cDot11BSSTxStatis64Entry ::= SEQUENCE
    {
        hh3cDot11BSSTx64FrameCnt             Counter64,
        hh3cDot11BSSTx64FrameBytes           Counter64,
        hh3cDot11BSSTx64DataFrameCnt         Counter64,
        hh3cDot11BSSTx64DataFrameBytes       Counter64,
        hh3cDot11BSSTx64AssocFrameCnt        Counter64,
        hh3cDot11BSSTx64PayloadBytes         Counter64,
        hh3cDot11BSSTx64RetryCnt             Counter64,
        hh3cDot11BSSTx64UniFrameCnt          Counter64,
        hh3cDot11BSSTx64NonUniFrameCnt       Counter64,
        hh3cDot11BSSTx64AuthenFrameCnt       Counter64
    }

hh3cDot11BSSTx64FrameCnt OBJECT-TYPE
    SYNTAX      Counter64
    MAX-ACCESS  read-only
    STATUS      current
    DESCRIPTION
        "Represents the total number of frames transmission with this BSS."
    ::= { hh3cDot11BSSTxStatis64Entry 1 }

hh3cDot11BSSTx64FrameBytes OBJECT-TYPE
    SYNTAX      Counter64
    MAX-ACCESS  read-only
    STATUS      current
    DESCRIPTION
        "Represents the total number of bytes transmission with this BSS."
    ::= { hh3cDot11BSSTxStatis64Entry 2 }

hh3cDot11BSSTx64DataFrameCnt OBJECT-TYPE
    SYNTAX      Counter64
    MAX-ACCESS  read-only
    STATUS      current
    DESCRIPTION
        "Represents the number of data frame transmission with this BSS."
    ::= { hh3cDot11BSSTxStatis64Entry 3 }

hh3cDot11BSSTx64DataFrameBytes OBJECT-TYPE
    SYNTAX      Counter64
    MAX-ACCESS  read-only
    STATUS      current
    DESCRIPTION
        "Represents the bytes of data frame transmission with this BSS."
    ::= { hh3cDot11BSSTxStatis64Entry 4 }

hh3cDot11BSSTx64AssocFrameCnt OBJECT-TYPE
    SYNTAX      Counter64
    MAX-ACCESS  read-only
    STATUS      current
    DESCRIPTION
        "Represents the number of associate frame transmission with this BSS."
    ::= { hh3cDot11BSSTxStatis64Entry 5 }

hh3cDot11BSSTx64PayloadBytes OBJECT-TYPE
    SYNTAX      Counter64
    MAX-ACCESS  read-only
    STATUS      current
    DESCRIPTION
        "Represents the payload bytes of data frame transmission with this BSS."
    ::= { hh3cDot11BSSTxStatis64Entry 6 }

hh3cDot11BSSTx64RetryCnt   OBJECT-TYPE
    SYNTAX      Counter64
    MAX-ACCESS  read-only
    STATUS      current
    DESCRIPTION
        "Represents the number of bytes retransmitted with this BSS."
    ::= { hh3cDot11BSSTxStatis64Entry 7 }

hh3cDot11BSSTx64UniFrameCnt OBJECT-TYPE
    SYNTAX      Counter64
    MAX-ACCESS  read-only
    STATUS      current
    DESCRIPTION
        "Represents the number of unicast frames transmission with this BSS."
    ::= { hh3cDot11BSSTxStatis64Entry 8 }

hh3cDot11BSSTx64NonUniFrameCnt OBJECT-TYPE
    SYNTAX      Counter64
    MAX-ACCESS  read-only
    STATUS      current
    DESCRIPTION
        "Represents the number of non-unicast frames transmission with this BSS."
    ::= { hh3cDot11BSSTxStatis64Entry 9 }

hh3cDot11BSSTx64AuthenFrameCnt OBJECT-TYPE
    SYNTAX      Counter64
    MAX-ACCESS  read-only
    STATUS      current
    DESCRIPTION
        "Represents the number of authentication frames transmission with this BSS."
    ::= { hh3cDot11BSSTxStatis64Entry 10 }

-- *****************************************************************************
-- *  End of hh3cDot11BSSTxStatis64Table Definition
-- *****************************************************************************

-- *****************************************************************************
-- *  hh3cDot11APPacketMCSRateStatis2Table Definition
-- *****************************************************************************
hh3cDot11APPacketMCSRateStatis2Table  OBJECT-TYPE
    SYNTAX        SEQUENCE OF Hh3cDot11APPacketMCSRateStatis2Entry
    MAX-ACCESS    not-accessible
    STATUS        current
    DESCRIPTION
        "This table provides packet statistics based on MCS rate."
    ::= { hh3cDot11APStatisGroup 34 }

hh3cDot11APPacketMCSRateStatis2Entry  OBJECT-TYPE
    SYNTAX        Hh3cDot11APPacketMCSRateStatis2Entry
    MAX-ACCESS    not-accessible
    STATUS        current
    DESCRIPTION
        "Each entry provides packet statistics based on MCS rate for each radio
        of a specific AP."
    INDEX
        {
            hh3cDot11CurAPID,
            hh3cDot11RadioID,
            hh3cDot11APPacketMCS2Rate
        }
    ::= { hh3cDot11APPacketMCSRateStatis2Table 1 }

Hh3cDot11APPacketMCSRateStatis2Entry  ::=SEQUENCE
    {
        hh3cDot11APPacketMCS2Rate          Integer32,
        hh3cDot11APRXPacketMCSRate2Count   Counter64,
        hh3cDot11APTXPacketMCSRate2Count   Counter64
    }

hh3cDot11APPacketMCS2Rate    OBJECT-TYPE
    SYNTAX        Integer32 (1..2000000000)
    MAX-ACCESS    not-accessible
    STATUS        current
    DESCRIPTION
        "Represents data transmission rate(Tenfold as actual rate)."
    ::= { hh3cDot11APPacketMCSRateStatis2Entry 1 }

hh3cDot11APRXPacketMCSRate2Count    OBJECT-TYPE
    SYNTAX        Counter64
    MAX-ACCESS    read-only
    STATUS        current
    DESCRIPTION
        "Represents the count of packets received based on data transmission rate."
    ::= { hh3cDot11APPacketMCSRateStatis2Entry 2 }

hh3cDot11APTXPacketMCSRate2Count    OBJECT-TYPE
    SYNTAX        Counter64
    MAX-ACCESS    read-only
    STATUS        current
    DESCRIPTION
        "Represents the count of packets transmitted base on data transmission rate."
    ::= { hh3cDot11APPacketMCSRateStatis2Entry 3 }

-- *****************************************************************************
-- *  End of hh3cDot11APPacketMcsRateStatis2Table Definition
-- *****************************************************************************

-- *****************************************************************************
-- *  hh3cDot11APUserSecAuthStatisCMTable Definition
-- *****************************************************************************
hh3cDot11APUserSecAuthStatisCMTable OBJECT-TYPE
    SYNTAX      SEQUENCE OF Hh3cDot11APUserSecAuthStatisCMEntry
    MAX-ACCESS  not-accessible
    STATUS      current
    DESCRIPTION
        "The table provides the user authentication statistics."
    ::= { hh3cDot11APStatisGroup 35 }

hh3cDot11APUserSecAuthStatisCMEntry OBJECT-TYPE
    SYNTAX      Hh3cDot11APUserSecAuthStatisCMEntry
    MAX-ACCESS  not-accessible
    STATUS      current
    DESCRIPTION
        "Each entry of the table provides the user authentication statistics
        of AP."
    INDEX
        {
            hh3cDot11CurAPID,
            hh3cDot11RadioID,
            hh3cDot11WlanID
       }
    ::= { hh3cDot11APUserSecAuthStatisCMTable 1 }

Hh3cDot11APUserSecAuthStatisCMEntry ::= SEQUENCE
    {
        hh3cDot11APUserConnFailCntCM              Counter32,
        hh3cDot11APUserAuthReqCntCM               Counter32,
        hh3cDot11APUserAuthSuccCntCM              Counter32,
        hh3cDot11APUserAuthFailCntCM              Counter32,
        hh3cDot11AllUserOnlineTimeCM              TimeTicks
    }

hh3cDot11APUserConnFailCntCM OBJECT-TYPE
    SYNTAX      Counter32
    MAX-ACCESS  read-only
    STATUS      current
    DESCRIPTION
        "Represents the failed connection count of users with this AP."
    ::= { hh3cDot11APUserSecAuthStatisCMEntry 1 }

hh3cDot11APUserAuthReqCntCM OBJECT-TYPE
    SYNTAX      Counter32
    MAX-ACCESS  read-only
    STATUS      current
    DESCRIPTION
        "Represents the total number of user authentication requests with this AP."
    ::= { hh3cDot11APUserSecAuthStatisCMEntry 2 }

hh3cDot11APUserAuthSuccCntCM OBJECT-TYPE
    SYNTAX      Counter32
    MAX-ACCESS  read-only
    STATUS      current
    DESCRIPTION
        "Represents the total number of successful user authentications with this AP."
    ::= { hh3cDot11APUserSecAuthStatisCMEntry 3 }

hh3cDot11APUserAuthFailCntCM OBJECT-TYPE
    SYNTAX      Counter32
    MAX-ACCESS  read-only
    STATUS      current
    DESCRIPTION
        "Represents the total number of failed user authentications with this AP."
    ::= { hh3cDot11APUserSecAuthStatisCMEntry 4 }

hh3cDot11AllUserOnlineTimeCM OBJECT-TYPE
    SYNTAX      TimeTicks
    MAX-ACCESS  read-only
    STATUS      current
    DESCRIPTION
        "Represents the online time of all users with this AP."
    ::= { hh3cDot11APUserSecAuthStatisCMEntry 5 }

-- *****************************************************************************
-- *  End of hh3cDot11APUserSecAuthStatisCMTable Definition
-- *****************************************************************************

-- *****************************************************************************
-- *  hh3cDot11APUserInfoStatis2CMTable Definition
-- *****************************************************************************
hh3cDot11APUserInfoStatis2CMTable OBJECT-TYPE
    SYNTAX      SEQUENCE OF Hh3cDot11APUserInfoStatis2CMEntry
    MAX-ACCESS  not-accessible
    STATUS      current
    DESCRIPTION
        "The table will provide the authentication user information statistic
        of this AP."
    ::= { hh3cDot11APStatisGroup 36 }

hh3cDot11APUserInfoStatis2CMEntry OBJECT-TYPE
    SYNTAX      Hh3cDot11APUserInfoStatis2CMEntry
    MAX-ACCESS  not-accessible
    STATUS      current
    DESCRIPTION
        "Each entry of the table will provide the authentication user information
        statistic of this AP."
    INDEX
        {
            hh3cDot11CurAPID,
            hh3cDot11APUserMacAddr2CM
        }
    ::= { hh3cDot11APUserInfoStatis2CMTable 1 }

Hh3cDot11APUserInfoStatis2CMEntry ::= SEQUENCE
    {
        hh3cDot11APUserMacAddr2CM                  MacAddress,
        hh3cDot11APUserIpAddr2CM                   IpAddress,
        hh3cDot11APUserLoginName2CM                OCTET STRING,
        hh3cDot11APUserLoginTime2CM                OCTET STRING,
        hh3cDot11APUserOnlineTime2CM               TimeTicks,
        hh3cDot11APUserAuthType2CM                 INTEGER,
        hh3cDot11APUserTxPacketCnt2CM              Counter32,
        hh3cDot11APUserTxBytes2CM                  Counter64,
        hh3cDot11APUserRxPacketCnt2CM              Counter32,
        hh3cDot11APUserRxBytes2CM                  Counter64,
        hh3cDot11APUserIPv6Addr2CM                 OCTET STRING,
        hh3cDot11APUserMac2CM                      MacAddress,
        hh3cDot11APUserInCirValueCM                Counter32,
        hh3cDot11APUserOutCirValueCM               Counter32
    }

hh3cDot11APUserMacAddr2CM OBJECT-TYPE
    SYNTAX      MacAddress
    MAX-ACCESS  not-accessible
    STATUS      current
    DESCRIPTION
        "Represents the mac address of authentication user logging to this AP."
    ::= { hh3cDot11APUserInfoStatis2CMEntry 1 }

hh3cDot11APUserIpAddr2CM OBJECT-TYPE
    SYNTAX      IpAddress
    MAX-ACCESS  read-only
    STATUS      current
    DESCRIPTION
        "Represents the ip address of authentication user logging to this AP."
    ::= { hh3cDot11APUserInfoStatis2CMEntry 2 }

hh3cDot11APUserLoginName2CM OBJECT-TYPE
    SYNTAX      OCTET STRING
    MAX-ACCESS  read-only
    STATUS      current
    DESCRIPTION
        "Represents the login name of authentication user logging to this AP."
    ::= { hh3cDot11APUserInfoStatis2CMEntry 3 }

hh3cDot11APUserLoginTime2CM OBJECT-TYPE
    SYNTAX      OCTET STRING
    MAX-ACCESS  read-only
    STATUS      current
    DESCRIPTION
        "Represents the login time of authentication user with this AP."
    ::= { hh3cDot11APUserInfoStatis2CMEntry 4 }

hh3cDot11APUserOnlineTime2CM OBJECT-TYPE
    SYNTAX      TimeTicks
    MAX-ACCESS  read-only
    STATUS      current
    DESCRIPTION
        "Represents how long authentication user has been online."
    ::= { hh3cDot11APUserInfoStatis2CMEntry 5 }

hh3cDot11APUserAuthType2CM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { hh3cDot11APUserInfoStatis2CMEntry 6 }

hh3cDot11APUserTxPacketCnt2CM OBJECT-TYPE
    SYNTAX      Counter32
    MAX-ACCESS  read-only
    STATUS      current
    DESCRIPTION
        "Represents the total count of packets sent to online users."
    ::= { hh3cDot11APUserInfoStatis2CMEntry 7 }

hh3cDot11APUserTxBytes2CM OBJECT-TYPE
    SYNTAX      Counter64
    MAX-ACCESS  read-only
    STATUS      current
    DESCRIPTION
        "Represents the total bytes sent to online users."
    ::= { hh3cDot11APUserInfoStatis2CMEntry 8 }

hh3cDot11APUserRxPacketCnt2CM OBJECT-TYPE
    SYNTAX      Counter32
    MAX-ACCESS  read-only
    STATUS      current
    DESCRIPTION
        "Represents the total count of packets received from online users."
    ::= { hh3cDot11APUserInfoStatis2CMEntry 9 }

hh3cDot11APUserRxBytes2CM OBJECT-TYPE
    SYNTAX      Counter64
    MAX-ACCESS  read-only
    STATUS      current
    DESCRIPTION
        "Represents the total bytes received from online users."
    ::= { hh3cDot11APUserInfoStatis2CMEntry 10 }

hh3cDot11APUserIPv6Addr2CM OBJECT-TYPE
    SYNTAX      OCTET STRING
    MAX-ACCESS  read-only
    STATUS      current
    DESCRIPTION
        "Represents the IPv6 address of online users."
    ::= { hh3cDot11APUserInfoStatis2CMEntry 11 }

hh3cDot11APUserMac2CM OBJECT-TYPE
    SYNTAX      MacAddress
    MAX-ACCESS  read-only
    STATUS      current
    DESCRIPTION
        "Represents the mac address of authentication user logging to this AP."
    ::= { hh3cDot11APUserInfoStatis2CMEntry 12 }

hh3cDot11APUserInCirValueCM OBJECT-TYPE
    SYNTAX      Counter32
    MAX-ACCESS  read-only
    STATUS      current
    DESCRIPTION
        "Represents the CIR of inbound direction of this user."
    ::= { hh3cDot11APUserInfoStatis2CMEntry 13 }

hh3cDot11APUserOutCirValueCM OBJECT-TYPE
    SYNTAX      Counter32
    MAX-ACCESS  read-only
    STATUS      current
    DESCRIPTION
        "Represents the CIR of outbound direction of this user."
    ::= { hh3cDot11APUserInfoStatis2CMEntry 14 }

-- *****************************************************************************
-- *  End of hh3cDot11APUserInfoStatis2CMTable Definition
-- *****************************************************************************

-- *****************************************************************************
-- *  AP Management Notifications Definition
-- *****************************************************************************
-- AP Management Notification

        hh3cDot11APMtTraps OBJECT IDENTIFIER
    ::= { hh3cDot11APMtNotifyGroup 0 }

hh3cDot11APMtWorkModeChgTrap NOTIFICATION-TYPE
    OBJECTS
        {
            hh3cDot11APID,
            hh3cDot11APChgWorkMode,
            hh3cDot11APMtTrapAPMacAddress
        }
    STATUS      current
    DESCRIPTION
        "The notification will be sent when AP changes the work mode, and
         hh3cDot11APWorkMode suggests which work mode will be used by AP."
    ::= { hh3cDot11APMtTraps 1 }

hh3cDot11APMtCfgErrorTrap NOTIFICATION-TYPE
    OBJECTS
        {
            hh3cDot11APID,
            hh3cDot11RadioID,
            hh3cDot11APMtTrapCfgErrReason
        }
    STATUS      current
    DESCRIPTION
        "The notification will represent errors caused by the
        configuration operation of AP."
    ::= { hh3cDot11APMtTraps 2 }

hh3cDot11APMtRadioFailTrap NOTIFICATION-TYPE
    OBJECTS
        {
            hh3cDot11APID,
            hh3cDot11RadioID,
            hh3cDot11APMtTrapRadioFailReason
        }
    STATUS      current
    DESCRIPTION
        "The notification will notify which the operational status
        of radio becomes down."
    ::= { hh3cDot11APMtTraps 3 }

hh3cDot11APMtRadioFailRecoverTrap NOTIFICATION-TYPE
    OBJECTS
        {
            hh3cDot11APID,
            hh3cDot11RadioID,
            hh3cDot11APMtTrapRadioFailReason
        }
    STATUS      current
    DESCRIPTION
        "The notification will notify the operational status of which radio
        becomes up again."
    ::= { hh3cDot11APMtTraps 4 }

hh3cDot11APMtRdoChanlChgTrap NOTIFICATION-TYPE
    OBJECTS
        {
            hh3cDot11APID,
            hh3cDot11RadioID,
            hh3cDot11APChannelChgMode,
            hh3cDot11APMtTrapOldChannel,
            hh3cDot11APMtTrapNewChannel,
            hh3cDot11APMtChanlChgCount,
            hh3cDot11APMtTrapAPMacAddress
        }
    STATUS      current
    DESCRIPTION
        "The notification will represent which radio changes the channel."
    ::= { hh3cDot11APMtTraps 5 }

hh3cDot11APMtTimeSynFail NOTIFICATION-TYPE
    OBJECTS
        {
            hh3cDot11APID
        }
    STATUS      current
    DESCRIPTION
        "The notification will be sent when AC and AP failed to
        synchronize their time."
    ::= { hh3cDot11APMtTraps 6 }

hh3cDot11APMtChlIntfDetected NOTIFICATION-TYPE
    OBJECTS
        {
            hh3cDot11Channel
        }
    STATUS      current
    DESCRIPTION
        "The notification will be sent when some ambient device interferes with
        current channel."
    ::= { hh3cDot11APMtTraps 7 }

hh3cDot11APMtIntfAPDetected NOTIFICATION-TYPE
    OBJECTS
        {
            hh3cDot11Channel,
            hh3cDot11APIntfDevMACAddress
        }
    STATUS current
    DESCRIPTION
        "The notification will be sent when some ambient AP interferes with
        current channel."
    ::= { hh3cDot11APMtTraps 8 }

hh3cDot11APMtIntfStaDetected NOTIFICATION-TYPE
    OBJECTS
        {
            hh3cDot11Channel,
            hh3cDot11APIntfDevMACAddress
        }
    STATUS current
    DESCRIPTION
        "The notification will be sent when some ambient station interferes with
        current channel."
    ::= { hh3cDot11APMtTraps 9 }

hh3cDot11APMtIPChange NOTIFICATION-TYPE
    OBJECTS
        {
            hh3cDot11APIPAddress,
            hh3cDot11APMtTrapOldIPAddr
        }
    STATUS current
    DESCRIPTION
        "The notification will be sent when IP address of the AP changes."
    ::= { hh3cDot11APMtTraps 10 }

hh3cDot11APFlashWriteFailure NOTIFICATION-TYPE
    OBJECTS
        {
            hh3cDot11APID,
            hh3cDot11APMtFormerApVersion,
            hh3cDot11APMtTrapAPMacAddress
        }
    STATUS      current
    DESCRIPTION
        "The notification will be sent when AP failed to write data
        into flash."
    ::= { hh3cDot11APMtTraps 11 }

hh3cDot11APSysReboot NOTIFICATION-TYPE
    OBJECTS
        {
            hh3cDot11APID
        }
    STATUS current
    DESCRIPTION
        "The notification will be sent when AP reboots."
    ::= { hh3cDot11APMtTraps 12 }

hh3cDot11APMtAvailChlTooLow NOTIFICATION-TYPE
    OBJECTS
        {
            hh3cDot11RadioID,
            hh3cDot11APMtAPID,
            hh3cDot11APMtTrapAPMacAddress
        }
    STATUS current
    DESCRIPTION
        "The notification will be sent when number of available channels is
         too low.
        "
    ::= { hh3cDot11APMtTraps 13 }

hh3cDot11APImgDwldSuccess NOTIFICATION-TYPE
    OBJECTS
        {
            hh3cDot11CurrAPName,
            hh3cDot11CurrAPIPAddress,
            hh3cDot11CurrAPSoftwareVersion
        }
    STATUS current
    DESCRIPTION
        "The notification will be sent when AP succeeds to download image from
        AC.
        "
    ::= { hh3cDot11APMtTraps 14 }

hh3cDot11APInterfDetectedTrap NOTIFICATION-TYPE
    OBJECTS
        {
            hh3cDot11Channel,
            hh3cDot11CurrInterfDetectedNum,
            hh3cDot11InterfMacList
        }
    STATUS current
    DESCRIPTION
        "This notification will be sent when some ambient AP interferes with
         current channel."
    ::= { hh3cDot11APMtTraps 15 }

hh3cDot11APInterfClearTrap NOTIFICATION-TYPE
    OBJECTS
        {
            hh3cDot11Channel,
            hh3cDot11APMtAPID,
            hh3cDot11APMtRadioID,
            hh3cDot11APMtInterfMacAdd,
            hh3cDot11APMtFirstTrapTime,
            hh3cDot11APMtTrapAPMacAddress
        }
    STATUS current
    DESCRIPTION
        "This notification will be sent when interference caused by ambient
         APs on the current channel disappears."
    ::= { hh3cDot11APMtTraps 16 }

hh3cDot11StaInterfDetectedTrap NOTIFICATION-TYPE
    OBJECTS
        {
            hh3cDot11Channel,
            hh3cDot11CurrInterfDetectedNum,
            hh3cDot11InterfMacList,
            hh3cDot11APMtFirstTrapTime
        }
    STATUS current
    DESCRIPTION
        "This notification will be sent when interference caused by ambient
         STAs on the current channel disappears."
    ::= { hh3cDot11APMtTraps 17 }

hh3cDot11StaInterfClearTrap NOTIFICATION-TYPE
    OBJECTS
        {
            hh3cDot11Channel,
            hh3cDot11APMtAPID,
            hh3cDot11APMtRadioID,
            hh3cDot11APMtInterfMacAdd,
            hh3cDot11APMtFirstTrapTime,
            hh3cDot11APMtTrapAPMacAddress
        }
    STATUS current
    DESCRIPTION
        "This notification will be sent when interference caused by ambient
         devices on the current channel happens."
    ::= { hh3cDot11APMtTraps 18 }

hh3cDot11OtherDevIntDetectedTrap NOTIFICATION-TYPE
    OBJECTS
        {
            hh3cDot11Channel,
            hh3cDot11APMtFirstTrapTime
        }
    STATUS      current
    DESCRIPTION
        "This notification will be sent when interference caused by ambient
         devices on the current channel disappears."
    ::= { hh3cDot11APMtTraps 19 }

hh3cDot11OtherDevIntClearTrap NOTIFICATION-TYPE
    OBJECTS
        {
            hh3cDot11Channel,
            hh3cDot11APMtAPID,
            hh3cDot11APMtRadioID,
            hh3cDot11APMtFirstTrapTime,
            hh3cDot11APMtTrapAPMacAddress
        }
    STATUS      current
    DESCRIPTION
        "This notification will be sent when previous ambient device disappeared with
         the same channel."
    ::= { hh3cDot11APMtTraps 20 }

hh3cDot11APModuleTroubleTrap NOTIFICATION-TYPE
    OBJECTS
        {
            hh3cDot11RadioID,
            hh3cDot11APMtAPID,
            hh3cDot11APMtTrapAPMacAddress
        }
    STATUS current
    DESCRIPTION
        "This notification will be sent when WLAN module failed."
    ::= { hh3cDot11APMtTraps 21 }

hh3cDot11APModuleTroubleClearTrap NOTIFICATION-TYPE
    OBJECTS
        {
            hh3cDot11RadioID,
            hh3cDot11APMtAPID,
            hh3cDot11APMtTrapAPMacAddress
        }
    STATUS current
    DESCRIPTION
        "The notification will be sent when WLAN module recovered."
    ::= { hh3cDot11APMtTraps 22 }

hh3cDot11APRadioDownTrap NOTIFICATION-TYPE
    OBJECTS
        {
            hh3cDot11RadioID,
            hh3cDot11APRadioDownReason,
            hh3cDot11APMtAPID,
            hh3cDot11APMtFirstTrapTime,
            hh3cDot11APMtTrapAPMacAddress
        }
    STATUS current
    DESCRIPTION
        "This notification will be sent when WLAN links interrupted."
    ::= { hh3cDot11APMtTraps 23 }

hh3cDot11APRadioDownRecovTrap NOTIFICATION-TYPE
    OBJECTS
        {
            hh3cDot11RadioID,
            hh3cDot11APMtAPID,
            hh3cDot11APMtFirstTrapTime,
            hh3cDot11APMtTrapAPMacAddress
        }
    STATUS current
    DESCRIPTION
        "This notification will be sent when WLAN links recover."
    ::= { hh3cDot11APMtTraps 24 }

hh3cDot11APStaFullTrap NOTIFICATION-TYPE
    OBJECTS
        {
            hh3cDot11APID,
            hh3cDot11StaLimitNumber,
            hh3cDot11StaFullReason,
            hh3cDot11APMtFirstTrapTime,
            hh3cDot11APMtTrapAPMacAddress
        }
    STATUS current
    DESCRIPTION
        "This notification will be sent when STA number reach limit number."
    ::= { hh3cDot11APMtTraps 25 }

hh3cDot11APStaFullRecoverTrap NOTIFICATION-TYPE
    OBJECTS
        {
            hh3cDot11APID,
            hh3cDot11StaLimitNumber,
            hh3cDot11StaFullReason,
            hh3cDot11APMtFirstTrapTime,
            hh3cDot11APMtTrapAPMacAddress
        }
    STATUS current
    DESCRIPTION
        "This notification will be sent when STA number recover enough level."
    ::= { hh3cDot11APMtTraps 26 }

hh3cDot11DFSFreeCntBelowThrRecov NOTIFICATION-TYPE
    OBJECTS
        {
            hh3cDot11RadioID,
            hh3cDot11APMtAPID,
            hh3cDot11APMtTrapAPMacAddress
        }
    STATUS current
    DESCRIPTION
        "This notification will be sent when available channels number
        recover enough level."
    ::= { hh3cDot11APMtTraps 27 }

hh3cDot11APCpuUsageHigh NOTIFICATION-TYPE
    OBJECTS
        {
            hh3cDot11APID,
            hh3cDot11APCPURTUsage,
            hh3cDot11APMtFirstTrapTime,
            hh3cDot11APMtTrapAPMacAddress
        }
    STATUS current
    DESCRIPTION
        "The notification will be sent when the AP CPU usage exceeds the
         threshold.
        "
    ::= { hh3cDot11APMtTraps 28 }

hh3cDot11APCpuUsageHighRecover NOTIFICATION-TYPE
    OBJECTS
        {
            hh3cDot11APID,
            hh3cDot11APCPURTUsage,
            hh3cDot11APMtFirstTrapTime,
            hh3cDot11APMtTrapAPMacAddress
        }
    STATUS current
    DESCRIPTION
        "The notification will be sent when the AP CPU usage descends the
         threshold.
        "
    ::= { hh3cDot11APMtTraps 29 }

hh3cDot11APMemUsageHigh NOTIFICATION-TYPE
    OBJECTS
        {
            hh3cDot11APID,
            hh3cDot11APMemRTUsage,
            hh3cDot11APMtFirstTrapTime,
            hh3cDot11APMtTrapAPMacAddress
        }
    STATUS current
    DESCRIPTION
        "The notification will be sent when the AP memory usage exceeds the
         threshold.
        "
    ::= { hh3cDot11APMtTraps 30 }

hh3cDot11APMemUsageHighRecover NOTIFICATION-TYPE
    OBJECTS
        {
            hh3cDot11APID,
            hh3cDot11APMemRTUsage,
            hh3cDot11APMtFirstTrapTime,
            hh3cDot11APMtTrapAPMacAddress
        }
    STATUS current
    DESCRIPTION
        "The notification will be sent when the AP memory usage descends the
         threshold.
         "
    ::= { hh3cDot11APMtTraps 31 }

hh3cDot11APTrapUserCntExceedThre NOTIFICATION-TYPE
    OBJECTS
        {
            hh3cDot11APID,
            hh3cDot11APTrapUserCnt,
            hh3cDot11APTrapUserThreshold
        }
    STATUS      current
    DESCRIPTION
        "The notification will be sent when the online user counter exceeds
        the threshold."
    ::= { hh3cDot11APMtTraps 32 }

hh3cDot11APMtDetectedIntfAP NOTIFICATION-TYPE
    OBJECTS
        {
            hh3cDot11APMtAPID,
            hh3cDot11APMtRadioID,
            hh3cDot11APMtChannel,
            hh3cDot11APMtInterfMacAdd,
            hh3cDot11APMtFirstTrapTime,
            hh3cDot11APMtTrapAPMacAddress
        }
    STATUS current
    DESCRIPTION
        "This notification will be sent when some ambient AP interferes with
         current channel."
    ::= { hh3cDot11APMtTraps 33 }

hh3cDot11APMtDetectedIntfSTA NOTIFICATION-TYPE
    OBJECTS
        {
            hh3cDot11APMtAPID,
            hh3cDot11APMtRadioID,
            hh3cDot11APMtChannel,
            hh3cDot11APMtInterfMacAdd,
            hh3cDot11APMtFirstTrapTime,
            hh3cDot11APMtTrapAPMacAddress
        }
    STATUS current
    DESCRIPTION
        "This notification will be sent when some ambient STA interferes with
         current channel."
    ::= { hh3cDot11APMtTraps 34 }

hh3cDot11APMtDetectedIntfOtherDev NOTIFICATION-TYPE
    OBJECTS
        {
            hh3cDot11APMtAPID,
            hh3cDot11APMtRadioID,
            hh3cDot11APMtChannel,
            hh3cDot11APMtTrapAPMacAddress
        }
    STATUS      current
    DESCRIPTION
        "This notification will be sent when other device interferes with
         current channel."
    ::= { hh3cDot11APMtTraps 35 }

hh3cDot11DetcAdjChlIntfAP NOTIFICATION-TYPE
    OBJECTS
        {
            hh3cDot11APMtAPID,
            hh3cDot11APMtRadioID,
            hh3cDot11APMtChannel,
            hh3cDot11APMtAdjChannel,
            hh3cDot11APMtInterfMacAdd,
            hh3cDot11APMtFirstTrapTime
        }
    STATUS current
    DESCRIPTION
        "This notification will be sent when some ambient AP interferes with
         adjacent channel."
    ::= { hh3cDot11APMtTraps 36 }

hh3cDot11DetcAdjChlIntfAPClear NOTIFICATION-TYPE
    OBJECTS
        {
            hh3cDot11APMtAPID,
            hh3cDot11APMtRadioID,
            hh3cDot11APMtChannel,
            hh3cDot11APMtAdjChannel,
            hh3cDot11APMtInterfMacAdd,
            hh3cDot11APMtFirstTrapTime
        }
    STATUS current
    DESCRIPTION
        "This notification will be sent when interference caused by ambient
         APs on the adjacent channel disappears."
    ::= { hh3cDot11APMtTraps 37 }

hh3cDot11APPowerOffTrap NOTIFICATION-TYPE
    OBJECTS
        {
            hh3cDot11APMtAPID
        }
    STATUS current
    DESCRIPTION
        "This notification will be sent when AP is power-off."
    ::= { hh3cDot11APMtTraps 38 }

hh3cDot11APPowerOnTrap NOTIFICATION-TYPE
    OBJECTS
        {
            hh3cDot11APMtAPID
        }
    STATUS current
    DESCRIPTION
        "This notification will be sent when AP is power-on."
    ::= { hh3cDot11APMtTraps 39 }

hh3cDot11UpLinkSwitchTrap NOTIFICATION-TYPE
    OBJECTS
        {
            hh3cDot11APMtAPID,
            hh3cDot11APMtUpLinkSwitchInfo,
            hh3cDot11APMtTrapAPMacAddress,
            hh3cDot11APMtUpLinkSwitchTime,
            hh3cDot11APMtOldCellId,
            hh3cDot11APMtCurCellId,
            hh3cDot11APMtOldBand,
            hh3cDot11APMtActiveBand
        }
    STATUS current
    DESCRIPTION
        "This notification will be sent when uplink switches to 3G or 4G."
    ::= { hh3cDot11APMtTraps 40 }

-- AP Management Notification variable object

hh3cDot11APMtTrapVarObjects OBJECT IDENTIFIER
    ::= { hh3cDot11APMtNotifyGroup 1 }

hh3cDot11APMtTrapCfgErrReason OBJECT-TYPE
    SYNTAX      Hh3cDot11NotifyReasonType
    MAX-ACCESS  accessible-for-notify
    STATUS      current
    DESCRIPTION
        "Represents errors caused by configuration operation."
    ::= { hh3cDot11APMtTrapVarObjects 1 }

hh3cDot11APMtTrapRadioFailReason OBJECT-TYPE
    SYNTAX      INTEGER
        {
            config(1),
            hh3cerror(2),
            swerror(3),
            radar(4),
            unknown(8)
        }
    MAX-ACCESS  accessible-for-notify
    STATUS      current
    DESCRIPTION
        "Represents errors caused by configuration operation.
        The following values are supported:
        config     - Configuration error
        hh3cerror  - Hardware error
        swerror    - Software error
        radar      - Radar Detection
        unknown    - Unknown reason"
    ::= { hh3cDot11APMtTrapVarObjects 2 }

hh3cDot11APMtTrapOldChannel OBJECT-TYPE
    SYNTAX      Hh3cDot11ChannelScopeType
    MAX-ACCESS  accessible-for-notify
    STATUS      current
    DESCRIPTION
        "Represents which channel the radio used to use."
    ::= { hh3cDot11APMtTrapVarObjects 3 }

hh3cDot11APMtTrapNewChannel OBJECT-TYPE
    SYNTAX      Hh3cDot11ChannelScopeType
    MAX-ACCESS  accessible-for-notify
    STATUS      current
    DESCRIPTION
        "Represents which channel the radio will use."
    ::= { hh3cDot11APMtTrapVarObjects 4 }

hh3cDot11APChannelChgMode OBJECT-TYPE
    SYNTAX      Hh3cDot11RFModeType
    MAX-ACCESS  accessible-for-notify
    STATUS      current
    DESCRIPTION
        "Represents the channel change mode for a radio."
    ::= { hh3cDot11APMtTrapVarObjects 5 }

hh3cDot11APChgWorkMode OBJECT-TYPE
    SYNTAX      INTEGER
        {
            normal(1),
            monitor(2),
            hybrid(3)
        }
    MAX-ACCESS  accessible-for-notify
    STATUS      current
    DESCRIPTION
        "Represents what work mode for AP.
        The following values are supported:
        normal  - AP will supply WLAN service.
        monitor - AP will be a monitor to detect attack.
        hybrid  - AP will supply WLAN service and detect attack."
    ::= { hh3cDot11APMtTrapVarObjects 6 }

hh3cDot11APIntfDevMACAddress OBJECT-TYPE
    SYNTAX      MacAddress
    MAX-ACCESS  accessible-for-notify
    STATUS      current
    DESCRIPTION
        "Represents MAC address of the device which triggers the notification."
    ::= { hh3cDot11APMtTrapVarObjects 7 }

hh3cDot11APMtTrapOldIPAddr OBJECT-TYPE
    SYNTAX      IpAddress
    MAX-ACCESS  accessible-for-notify
    STATUS      current
    DESCRIPTION
        "Represents the IP address of AP."
    ::= { hh3cDot11APMtTrapVarObjects 8 }

hh3cDot11CurrInterfDetectedNum OBJECT-TYPE
    SYNTAX      Integer32
    MAX-ACCESS  accessible-for-notify
    STATUS      current
    DESCRIPTION
        "Represents the number of interfere detected."
    ::= { hh3cDot11APMtTrapVarObjects 9 }

hh3cDot11StaFullReason OBJECT-TYPE
    SYNTAX      INTEGER
        {
            ap(1),
            bss(2),
            radio(3),
            radioConcur(4),
            radiopolicy(5),
            ac(6),
            acConcur(7),
            aid(8)
        }
    MAX-ACCESS  accessible-for-notify
    STATUS      current
    DESCRIPTION
        "Reports which kind maximum number of STA
         is reached.  New STA is not able to associate."
    ::= { hh3cDot11APMtTrapVarObjects 10 }

hh3cDot11StaLimitNumber OBJECT-TYPE
    SYNTAX      Integer32
    MAX-ACCESS  accessible-for-notify
    STATUS      current
    DESCRIPTION
        "Represents the limit number of STA."
    ::= { hh3cDot11APMtTrapVarObjects 11 }

hh3cDot11APRadioDownReason OBJECT-TYPE
    SYNTAX  INTEGER
        {
            phyicalUnusable(1),
            configDisable(2),
            operatinUnusable(3),
            apTunnelDown(4)
        }
    MAX-ACCESS  accessible-for-notify
    STATUS      current
    DESCRIPTION
        "Reports the reason why WLAN links is interrupted."
    ::= { hh3cDot11APMtTrapVarObjects 12 }

hh3cDot11InterfMacList OBJECT-TYPE
    SYNTAX      OCTET STRING
    MAX-ACCESS  accessible-for-notify
    STATUS      current
    DESCRIPTION
        "Represents MAC address list of interfere detected."
    ::= { hh3cDot11APMtTrapVarObjects 13 }

hh3cDot11APTrapUserCnt OBJECT-TYPE
    SYNTAX      Integer32
    MAX-ACCESS  accessible-for-notify
    STATUS      current
    DESCRIPTION
        "Represents the online user counter of AP."
    ::= { hh3cDot11APMtTrapVarObjects 14 }

hh3cDot11APTrapUserThreshold OBJECT-TYPE
    SYNTAX      Integer32
    MAX-ACCESS  accessible-for-notify
    STATUS      current
    DESCRIPTION
        "Represents threshold of AP's online user counter."
    ::= { hh3cDot11APMtTrapVarObjects 15 }

hh3cDot11APMtChanlChgCount OBJECT-TYPE
    SYNTAX      Integer32
    MAX-ACCESS  accessible-for-notify
    STATUS      current
    DESCRIPTION
        "Represents how many times that channel changed."
    ::= { hh3cDot11APMtTrapVarObjects 16 }

hh3cDot11APMtFormerApVersion OBJECT-TYPE
    SYNTAX      OCTET STRING
    MAX-ACCESS  accessible-for-notify
    STATUS      current
    DESCRIPTION
        "Represents former software version of AP."
    ::= { hh3cDot11APMtTrapVarObjects 17 }

hh3cDot11APMtAPID OBJECT-TYPE
    SYNTAX      Hh3cDot11ObjectIDType
    MAX-ACCESS  accessible-for-notify
    STATUS      current
    DESCRIPTION
        "To uniquely identify each AP."
    ::= { hh3cDot11APMtTrapVarObjects 18 }

hh3cDot11APMtRadioID OBJECT-TYPE
    SYNTAX      Hh3cDot11RadioScopeType
    MAX-ACCESS  accessible-for-notify
    STATUS      current
    DESCRIPTION
        "Represents each radio."
    ::= { hh3cDot11APMtTrapVarObjects 19 }

hh3cDot11APMtChannel OBJECT-TYPE
    SYNTAX      Hh3cDot11ChannelScopeType
    MAX-ACCESS  accessible-for-notify
    STATUS      current
    DESCRIPTION
        "Represents the current channel allocation for radio."
    ::= { hh3cDot11APMtTrapVarObjects 20 }

hh3cDot11APMtInterfMacAdd OBJECT-TYPE
    SYNTAX      MacAddress
    MAX-ACCESS  accessible-for-notify
    STATUS      current
    DESCRIPTION
        "Represents the MAC address of an AP."
    ::= { hh3cDot11APMtTrapVarObjects 21 }

hh3cDot11APMtAdjChannel OBJECT-TYPE
    SYNTAX      Hh3cDot11ChannelScopeType
    MAX-ACCESS  accessible-for-notify
    STATUS      current
    DESCRIPTION
        "Represents the adjacent channel of radio."
    ::= { hh3cDot11APMtTrapVarObjects 22 }

hh3cDot11APMtFirstTrapTime OBJECT-TYPE
    SYNTAX      TimeTicks
    MAX-ACCESS  accessible-for-notify
    STATUS      current
    DESCRIPTION
        "Represents the first trap time."
    ::= { hh3cDot11APMtTrapVarObjects 23 }

hh3cDot11APMtTrapAPMacAddress OBJECT-TYPE
    SYNTAX      MacAddress
    MAX-ACCESS  accessible-for-notify
    STATUS      current
    DESCRIPTION
        "Represents the MAC address of an AP."
    ::= {hh3cDot11APMtTrapVarObjects 24}

hh3cDot11APMtUpLinkSwitchInfo OBJECT-TYPE
    SYNTAX      INTEGER
        {
            unknown(1),
            tdscdma(2),
            tdlte(3)
        }
    MAX-ACCESS  accessible-for-notify
    STATUS      current
    DESCRIPTION
        "Represents the type which uplink switches to.
        The following values are supported:
        TDSCDMA - The uplink switches to TDSCDMA.
        TDLTE - The uplink switches to TDLTE.
        unknown - Unknown uplink type."
    ::= {hh3cDot11APMtTrapVarObjects 25}

hh3cDot11APMtUpLinkSwitchTime OBJECT-TYPE
    SYNTAX      TimeStamp
    MAX-ACCESS  accessible-for-notify
    STATUS      current
    DESCRIPTION
        "Represents the time when uplink switches."
    ::= { hh3cDot11APMtTrapVarObjects 26 }

hh3cDot11APMtOldCellId OBJECT-TYPE
    SYNTAX      Integer32
    MAX-ACCESS  accessible-for-notify
    STATUS      current
    DESCRIPTION
        "Represents the cell id before uplink switch."
    ::= { hh3cDot11APMtTrapVarObjects 27 }

hh3cDot11APMtCurCellId OBJECT-TYPE
    SYNTAX      Integer32
    MAX-ACCESS  accessible-for-notify
    STATUS      current
    DESCRIPTION
        "Represents the cell id after uplink switch."
    ::= { hh3cDot11APMtTrapVarObjects 28 }

hh3cDot11APMtOldBand OBJECT-TYPE
    SYNTAX      OCTET STRING
    MAX-ACCESS  accessible-for-notify
    STATUS      current
    DESCRIPTION
        "Represents the band before uplink switch."
    ::= { hh3cDot11APMtTrapVarObjects 29 }

hh3cDot11APMtActiveBand OBJECT-TYPE
    SYNTAX      OCTET STRING
    MAX-ACCESS  accessible-for-notify
    STATUS      current
    DESCRIPTION
        "Represents the band after uplink switch."
    ::= { hh3cDot11APMtTrapVarObjects 30 }

-- *****************************************************************************
-- *  End of AP Management Notification  Definition
-- *****************************************************************************
END
