-- =================================================================
-- Copyright (c) 2004-2023 New H3C Tech. Co., Ltd. All rights reserved.
--
-- Description: Cluster MIB
-- Reference:
-- Version: V1.0
-- History:
--  V1.0 Created by meishenhe
--      Initial version 2023-07-04
-- =================================================================
HH3C-CLUSTER-MIB DEFINITIONS ::= BEGIN

IMPORTS
    MODULE-IDENTITY, OBJECT-TYPE, NOTIFICATION-TYPE,
    Integer32
        FROM SNMPv2-SMI
    hh3cCommon
        FROM HH3C-OID-MIB;

hh3cCluster MODULE-IDENTITY
    LAST-UPDATED "202307040000Z"
    ORGANIZATION
        "New H3C Technologies Co., Ltd."
    CONTACT-INFO
        "No.466 Changhe Road, Binjiang District, Hangzhou, Zhejiang
         http://www.h3c.com
         Zip: 310052"
    DESCRIPTION
        "The MIB module is used for cluster status notification."
    REVISION    "202307040000Z"
    DESCRIPTION    "The initial version."
    ::= { hh3cCommon 264 }

-- ==================================================================
--
-- CLUSTER trap object
--
-- ==================================================================
hh3cClusterObjects OBJECT IDENTIFIER ::= { hh3cCluster 1 }

hh3cClusterConnObjects OBJECT IDENTIFIER ::= { hh3cClusterObjects 1 }

hh3cClusterMemberID OBJECT-TYPE
    SYNTAX      Integer32
    MAX-ACCESS  accessible-for-notify
    STATUS      current
    DESCRIPTION
        "Member ID of a device in a cluster."
    ::= { hh3cClusterConnObjects 1 }

hh3cClusterTrap OBJECT IDENTIFIER ::= { hh3cCluster 2 }

hh3cClusterConnTrapPrefix OBJECT IDENTIFIER ::= { hh3cClusterTrap 0 }

hh3cClusterRecombine NOTIFICATION-TYPE
    OBJECTS {
            hh3cClusterMemberID
        }
    STATUS  current
    DESCRIPTION
        "The hh3cClusterRecombine notification indicates a cluster merge event."
::= { hh3cClusterConnTrapPrefix 1 }

hh3cClusterSplitOut NOTIFICATION-TYPE
    OBJECTS {
            hh3cClusterMemberID
        }
    STATUS  current
    DESCRIPTION
        "The hh3cClusterSplitOut notification indicates a cluster split event."
::= { hh3cClusterConnTrapPrefix 2 }

END
