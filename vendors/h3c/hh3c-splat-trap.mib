-- ==================================================================
-- Copyright (c) 2004-2025 New H3C Tech. Co., Ltd. All rights reserved.
--
-- Description: Trap MIB
-- Reference:
-- Version: V2.8
-- History:
-- V1.0 Created by Zhangshilin, 2001.06.29
-- V1.1 Modified by lifengguang 2008.11.10, add trap node hh3cBootImageUpdated
-- V1.2 2011-11-26 updated by duyanbing
--      Added hh3cDevMFirstTrapTime to powerfailure and hh3cPowerNormal.
-- V1.3 2012-04-26 updated by wangcong
--      Added hh3cNetworkHealthMonitorFailure, hh3cNetworkHealthMonitorNormal for reserving.
-- V1.4 2013-03-08 updated by fangliwen
--      Added hh3cCpuRemoved, hh3cCpuFailure, hh3cCpuNormal.
--      2014-08-02 updated by fangliwen
--      Added hh3cPowerIncompatible.
-- V1.5 2016-12-21 updated by yanfang
--      Added hh3cCpuUsageSevereNotification
--            hh3cCpuUsageSevereRecoverNotification
--            hh3cCpuUsageMinorNotification
--            hh3cCpuUsageMinorRecoverNotification.
--            hh3cMemoryUsageEarlyWarningNotification
--            hh3cMemoryUsageEarlyWarningRecoverNotification
--            hh3cMemoryUsageMinorNotification
--            hh3cMemoryUsageMinorRecoverNotification
--            hh3cMemoryUsageSevereNotification
--            hh3cMemoryUsageSevereRecoverNotification
--            hh3cMemoryUsageCriticalNotification
--            hh3cMemoryUsageCriticalRecoverNotification.
--      2017-06-23 updated by wangweihui
--      Added hh3cCoreUsageNotification
--      2017-07-17 updated by fangliwen
--      Added hh3cBoardPowerNotEnough, hh3cAvailablePower and hh3cRequiredPower.
--      2017-12-5 updated by yuhaiyan
--      Added hh3cAlarmInPortIn
--            hh3cAlarmInPortRecover
-- V1.6 2018-04-13 updated by wangweihui
--      Added hh3cLswAlarmInPortInNum
-- V1.7 2019-01-11 updated by wangweihui
--      Added hh3cCoreUsageSevereRecoveryNotification
--            hh3cCoreUsageMinorNotification
--            hh3cCoreUsageMinorRecoveryNotification
-- V1.8 2019-11-22 updated by xuyuanqiang
--      Added hh3cDMAMemoryUsageCriticalNotification
--            hh3cDMAMemoryUsageRecoverNotification
-- V1.9 2020-10-15 updated by caohao
--      Added hh3cRemainingPowerNotEnough
--            hh3cFrameRemainingPower
-- V2.0 2022-02-15 updated by fangliwen
--      Added hh3cMMUParityError
--      2022-03-02 updated by liwenxiao
--      Added hh3cOutputPowerStatusNotification
-- V2.1 2022-06-15 updated by caohao
--      Added hh3cHeartbeatTimeoutSeconds
--            hh3cBoardHeartbeatTimeout
--            hh3cBoardHeartbeatResume.
-- V2.2 2022-07-12 updated by zhangjindong
--      Added hh3cDevTrapChassis
--            hh3cDevTrapSrcSlot
--            hh3cDevTrapSrcCpu
--            hh3cDevTrapDestChassis
--            hh3cDevTrapDestSlot
--            hh3cDevTrapDestCpu
--            hh3cDevTrapRebootReason
--            hh3cDevTrapSlaveSwitchFailReason
--            hh3cCommunicateError
--            hh3cCommunicateResume
--            hh3cBoardRebooted
--            hh3cDevTrapSlaveSwitchFail
--            hh3cAllBoardHeartbeatTimeout
--            hh3cAllBoardHeartbeatResume
--            hh3cDevTrapFanFailureErrcode
-- V2.3 2022-09-26 updated by fangliwen
--      Added hh3cBladeNotInsertedNotCleared
--            hh3cBladeInsertedCleared
-- V2.4 2022-12-06 updated by shenhongxia
--      Added hh3cDevTrapSliceStarting
--            hh3cDevTrapSliceOnline
--            hh3cDevTrapSliceOffline
--            hh3cDevTrapSliceIndex
--      2023-02-23 updated by tianruichuan
--      Added hh3cBoardReceiveWrongPackets
-- V2.5 2023-9-14 updated by liziyi
--      Added hh3cDevTrapPressKeyName
--            hh3cDevTrapPressKeyOper
--            hh3cDevPressKeyOperNotification
-- V2.6 2023-10-15 Add hh3cDevProcessAbnormal by fangliwen
--      2023-10-18 updated by xuyuanqiang
--      Added hh3cDevBatchBackupStart
--            hh3cDevBatchBackupFinish
--            hh3cDevStandbyNotReady
--            hh3cDevStandbyToMaster
--      2023-10-18 updated by zhaoyunfei
--      Added hh3cDevBoardFaultTooLong, hh3cDevClockChange, hh3cDevAutoSwitchFault, hh3cDevAutoSwitchFaultReboot,
--            hh3cDevBoardRunningFault, hh3cDevBoardRunningFaultReboot, hh3cDevFdUPLimited, hh3cDevFdUPReachLimit,
--            hh3cDevSlotFaultTime, hh3cDevClockOldTime, hh3cDevClockNewTime, hh3cDevProcessID, hh3cDevProcessName
-- V2.7 2024-09-10 updated by shenhongxia
--      Added hh3cSystemSecurityRiskOccur, hh3cSystemSecurityRiskClear
-- V2.8 2025-02-12 Add hh3cCpuGroupUsageSevereNotification,hh3cCpuGroupUsageSevereRecoverNotification
--      hh3cCpuGroupUsageMinorNotification,hh3cCpuGroupUsageMinorRecoverNotification by shenhongxia
-- ==================================================================

-- ==================================================================
--
-- Variables and types be imported
--
-- ==================================================================
HH3C-LswTRAP-MIB DEFINITIONS ::= BEGIN
IMPORTS
    MODULE-IDENTITY, NOTIFICATION-TYPE, OBJECT-TYPE, Unsigned32, Integer32
        FROM SNMPv2-SMI
    hh3clswCommon
        FROM HH3C-OID-MIB
    CounterBasedGauge64
        FROM HCNUM-TC
    SnmpAdminString
        FROM SNMP-FRAMEWORK-MIB
    hh3cDevMPowerNum, hh3cDevMFanNum, hh3cDevMFirstTrapTime
        FROM HH3C-LswDEVM-MIB
    hh3cLswFrameIndex, hh3cLswSlotIndex, hh3cLswSubslotIndex, hh3cLswCpuIndex, hh3cLswCoreIndex, hh3cLswCoreThreshold,
    hh3cLswCoreMinorThreshold, hh3cLswCoreRecoveryThreshold,hh3cLswCpuRatio,hh3cLswCpuUsageMinorThreshold,hh3cLswCpuUsageSevereThreshold,
    hh3cLswCpuUsageRecoverThreshold,hh3cLswCpuMemory,hh3cLswCpuMemoryFree,hh3cLswCpuMemoryFreeRatio,hh3cLswCpuMemoryHighTotal,hh3cLswCpuMemoryHighFree,
    hh3cLswCpuMemoryLowTotal,hh3cLswCpuMemoryLowFree,hh3cLswCpuMemorySecureThreshold,hh3cLswCpuMemoryEarlyWarningThreshold,hh3cLswCpuMemoryNormalThreshold,
    hh3cLswCpuMemoryMinorThreshold,hh3cLswCpuMemorySevereThreshold,hh3cLswCpuMemoryCriticalThreshold,hh3cLswCpuMemoryCurrentState,hh3cLswOutputPowerPortID,
    hh3cLswOutputPowerStatus,hh3cCpuGroupUsageGroupName,hh3cCpuGroupUsageSevereThreshold,hh3cCpuGroupUsageMinorThreshold,
    hh3cCpuGroupUsageRecovThreshold,hh3cCpuGroupUsageInterval,hh3cCpuGroupUsageAverageCpuUsage,hh3cCpuGroupUsageLast5sCpuUsage,
    hh3cCpuGroupUsageLast1mCpuUsage,hh3cCpuGroupUsageLast5mCpuUsage,hh3cCpuGroupUsageCurrentState
        FROM HH3C-LSW-DEV-ADM-MIB
    DisplayString
        FROM SNMPv2-TC;
-- ==================================================================
--
-- ======================= definition begin =========================
--
-- ==================================================================

    hh3cLswTrapMib MODULE-IDENTITY
            LAST-UPDATED "202502120000Z"
            ORGANIZATION
                "New H3C Tech. Co., Ltd."
            CONTACT-INFO
                "Platform Team New H3C Tech. Co., Ltd.
                Hai-Dian District Beijing P.R. China
                http://www.h3c.com
                Zip:100085
                "
            DESCRIPTION
            "Notifications related to the status changes of boards and resources on the device."
            REVISION "202502120000Z"
            DESCRIPTION
            "Added hh3cCpuGroupUsageSevereNotification,hh3cCpuGroupUsageSevereRecoverNotification,
             hh3cCpuGroupUsageMinorNotification,hh3cCpuGroupUsageMinorRecoverNotification."
            REVISION "202409120000Z"
            DESCRIPTION
            "Added hh3cSystemSecurityRiskOccur, hh3cSystemSecurityRiskClear"
            REVISION "202310180000Z"
            DESCRIPTION
            "Added hh3cDevBatchBackupStart,hh3cDevBatchBackupFinish,hh3cDevStandbyNotReady,
             hh3cDevStandbyToMaster,hh3cDevProcessAbnormal,hh3cDevBoardFaultTooLong, hh3cDevClockChange,
             hh3cDevAutoSwitchFault, hh3cDevAutoSwitchFaultReboot,hh3cDevBoardRunningFault,
             hh3cDevBoardRunningFaultReboot, hh3cDevFdUPLimited, hh3cDevFdUPReachLimit."
            REVISION "202309140000Z"
            DESCRIPTION
            "Added hh3cDevTrapPressKeyName
             hh3cDevTrapPressKeyOper
             hh3cDevPressKeyOperNotification."
            REVISION "202302230000Z"
            DESCRIPTION
            "Added hh3cBoardReceiveWrongPackets."
            REVISION "202209260000Z"
            DESCRIPTION
            "Added hh3cBladeNotInsertedNotCleared
             hh3cBladeInsertedCleared."
            REVISION "202207120000Z"
            DESCRIPTION
            "Added hh3cLswSrcChassis
             hh3cDevTrapSrcSlot
             hh3cDevTrapSrcCpu
             hh3cDevTrapDestChassis
             hh3cDevTrapDestSlot
             hh3cDevTrapDestCpu
             hh3cDevTrapRebootReason
             hh3cDevTrapSlaveSwitchFailReason
             hh3cCommunicateError
             hh3cCommunicateResume
             hh3cBoardRebooted
             hh3cDevTrapSlaveSwitchFail
             hh3cAllBoardHeartbeatTimeout
             hh3cAllBoardHeartbearReaume
             hh3cDevTrapFanFailureErrcode."
            REVISION "202206150000Z"
            DESCRIPTION
            "Added hh3cHeartbeatTimeoutSeconds
             hh3cBoardHeartbeatTimeout
             hh3cBoardHeartbeatResume."
            REVISION "202203020000Z"
            DESCRIPTION
            "Added hh3cOutputPowerStatusNotification."
            REVISION "202202150000Z"
            DESCRIPTION
            "Added hh3cMMUParityError."
            REVISION "202010150000Z"
            DESCRIPTION
            "Added hh3cRemainingPowerNotEnough
             hh3cFrameRemainingPower."
            REVISION "201911220000Z"
            DESCRIPTION
            "Added hh3cDMAMemoryUsageCriticalNotification
             hh3cDMAMemoryUsageRecoverNotification."
            REVISION "201901110000Z"
            DESCRIPTION
            "Added hh3cCoreUsageSevereRecoveryNotification
            hh3cCoreUsageMinorNotification
            hh3cCoreUsageMinorRecoveryNotificationm."
            REVISION "201804130000Z"
            DESCRIPTION
            "Added hh3cLswAlarmInPortInNum."
            REVISION "201712050000Z"
            DESCRIPTION
            "Added hh3cAlarmInPortIn,  hh3cAlarmInPortRecover."
            REVISION "201707170000Z"
            DESCRIPTION
            "Added hh3cBoardPowerNotEnough, hh3cAvailablePower and hh3cRequiredPower."
            REVISION "201706240000Z"
            DESCRIPTION
            "hh3cCoreUsageNotification.
             Added hh3csLswTRAPMibObjectV2Prefix for bindings of notification."
            REVISION "201701120000Z"
            DESCRIPTION
            "Added hh3cCpuUsageSevereNotification
             hh3cCpuUsageSevereRecoverNotification
             hh3cCpuUsageMinorNotification
             hh3cCpuUsageMinorRecoverNotification.
             hh3cMemoryUsageEarlyWarningNotification
             hh3cMemoryUsageEarlyWarningRecoverNotification
             hh3cMemoryUsageMinorNotification
             hh3cMemoryUsageMinorRecoverNotification
             hh3cMemoryUsageSevereNotification
             hh3cMemoryUsageSevereRecoverNotification
             hh3cMemoryUsageCriticalNotification
             hh3cMemoryUsageCriticalRecoverNotification.
             Added hh3csLswTRAPMibInfor for bindings of notification."
            REVISION "201111260000Z"
            DESCRIPTION
            "Initial revision"
            ::= { hh3clswCommon 12 }

-- ==================================================================
--
-- lsw trap object
--
-- ==================================================================
    hh3csLswTRAPMibObject OBJECT IDENTIFIER ::= { hh3cLswTrapMib 1 }

    hh3cpowerfailure NOTIFICATION-TYPE
      OBJECTS { hh3cDevMPowerNum, hh3cDevMFirstTrapTime }
      STATUS  current
      DESCRIPTION
              "Power supply failure"
      ::= { hh3csLswTRAPMibObject 1 }

    hh3cPowerNormal NOTIFICATION-TYPE
      OBJECTS { hh3cDevMPowerNum, hh3cDevMFirstTrapTime }
      STATUS  current
      DESCRIPTION
              "Power supply normal"
      ::= { hh3csLswTRAPMibObject 2 }

    hh3cMasterPowerNormal NOTIFICATION-TYPE
      OBJECTS { hh3cDevMPowerNum }
      STATUS  current
      DESCRIPTION
              "Master power supply normal"
      ::= { hh3csLswTRAPMibObject 3 }

    hh3cSlavePowerNormal NOTIFICATION-TYPE
      OBJECTS { hh3cDevMPowerNum }
      STATUS  current
      DESCRIPTION
              "Slave power supply normal"
      ::= { hh3csLswTRAPMibObject 4 }

    hh3cPowerRemoved NOTIFICATION-TYPE
      OBJECTS { hh3cDevMPowerNum }
      STATUS  current
      DESCRIPTION
              "Power removed"
      ::= { hh3csLswTRAPMibObject 5 }

    hh3cfanfailure NOTIFICATION-TYPE
      OBJECTS { hh3cDevMFanNum, hh3cDevTrapFanFailureErrcode }
      STATUS  current
      DESCRIPTION
              "Fan failure"
      ::= { hh3csLswTRAPMibObject 6 }

    hh3cFanNormal NOTIFICATION-TYPE
      OBJECTS { hh3cDevMFanNum }
      STATUS  current
      DESCRIPTION
              "Fan normal"
      ::= { hh3csLswTRAPMibObject 7 }

    hh3cBoardRemoved NOTIFICATION-TYPE
      OBJECTS { hh3cLswFrameIndex, hh3cLswSlotIndex }
      STATUS  current
      DESCRIPTION
              "Board removed"
      ::= { hh3csLswTRAPMibObject 8 }

    hh3cBoardInserted NOTIFICATION-TYPE
      OBJECTS { hh3cLswFrameIndex,hh3cLswSlotIndex }
      STATUS  current
      DESCRIPTION
              "Board inserted"
      ::= { hh3csLswTRAPMibObject 9 }

    hh3cBoardFailure NOTIFICATION-TYPE
      OBJECTS { hh3cLswFrameIndex, hh3cLswSlotIndex }
      STATUS  current
      DESCRIPTION
              "Board failed"
      ::= { hh3csLswTRAPMibObject 10 }

    hh3cBoardNormal NOTIFICATION-TYPE
      OBJECTS { hh3cLswFrameIndex, hh3cLswSlotIndex }
      STATUS  current
      DESCRIPTION
              "Board normal"
      ::= { hh3csLswTRAPMibObject 11 }

    hh3cSubcardRemove NOTIFICATION-TYPE
      OBJECTS { hh3cLswFrameIndex, hh3cLswSlotIndex, hh3cLswSubslotIndex }
      STATUS  current
      DESCRIPTION
              "Sub card removed"
      ::= { hh3csLswTRAPMibObject 12 }

    hh3cSubcardInsert NOTIFICATION-TYPE
      OBJECTS { hh3cLswFrameIndex, hh3cLswSlotIndex, hh3cLswSubslotIndex }
      STATUS  current
      DESCRIPTION
              "Sub card inserted"
      ::= { hh3csLswTRAPMibObject 13 }

    hh3cBoardTemperatureLower NOTIFICATION-TYPE
      OBJECTS { hh3cLswFrameIndex, hh3cLswSlotIndex }
      STATUS  current
      DESCRIPTION
              "Board temperature low"
      ::= { hh3csLswTRAPMibObject 14 }

    hh3cBoardTemperatureFromLowerToNormal NOTIFICATION-TYPE
      OBJECTS { hh3cLswFrameIndex, hh3cLswSlotIndex }
      STATUS  current
      DESCRIPTION
              "Board temperature form lower to normal"
      ::= { hh3csLswTRAPMibObject 15 }

    hh3cBoardTemperatureHigher NOTIFICATION-TYPE
      OBJECTS { hh3cLswFrameIndex, hh3cLswSlotIndex }
      STATUS  current
      DESCRIPTION
              "Board temperature high"
      ::= { hh3csLswTRAPMibObject 16 }

    hh3cBoardTemperatureFormHigherToNormal NOTIFICATION-TYPE
      OBJECTS { hh3cLswFrameIndex, hh3cLswSlotIndex }
      STATUS  current
      DESCRIPTION
              "Board temperature from higher to normal"
      ::= { hh3csLswTRAPMibObject 17 }

    hh3cRequestLoading NOTIFICATION-TYPE
      OBJECTS { hh3cLswFrameIndex, hh3cLswSlotIndex }
      STATUS  current
      DESCRIPTION
              "Board request load"
      ::= { hh3csLswTRAPMibObject 18 }

    hh3cLoadFailure NOTIFICATION-TYPE
      OBJECTS { hh3cLswFrameIndex, hh3cLswSlotIndex }
      STATUS  current
      DESCRIPTION
              "Board load failure"
      ::= { hh3csLswTRAPMibObject 19 }

    hh3cLoadFinished NOTIFICATION-TYPE
      OBJECTS { hh3cLswFrameIndex, hh3cLswSlotIndex }
      STATUS  current
      DESCRIPTION
              "Board load finished"
      ::= { hh3csLswTRAPMibObject 20 }

    hh3cBackBoardModeSetFuilure NOTIFICATION-TYPE
      OBJECTS { hh3cLswFrameIndex }
      STATUS  current
      DESCRIPTION
              "Back board mode set failure"
      ::= { hh3csLswTRAPMibObject 21 }

    hh3cBackBoardModeSetOK NOTIFICATION-TYPE
      OBJECTS { hh3cLswFrameIndex }
      STATUS  current
      DESCRIPTION
              "Back board mode set OK"
      ::= { hh3csLswTRAPMibObject 22 }

    hh3cPowerInserted NOTIFICATION-TYPE
      OBJECTS { hh3cDevMPowerNum }
      STATUS  current
      DESCRIPTION
              "Power inserted"
      ::= { hh3csLswTRAPMibObject 23 }

    hh3cBootImageUpdated NOTIFICATION-TYPE
      OBJECTS { hh3cLswFrameIndex, hh3cLswSlotIndex }
      STATUS  current
      DESCRIPTION
              "This trap node indicates that the boot image of specified board
              is updated."
      ::= { hh3csLswTRAPMibObject 24 }

    hh3cCpuRemoved NOTIFICATION-TYPE
      OBJECTS { hh3cLswFrameIndex, hh3cLswSlotIndex, hh3cLswCpuIndex }
      STATUS  current
      DESCRIPTION
              "Node removed"
      ::= { hh3csLswTRAPMibObject 25 }

    hh3cCpuFailure NOTIFICATION-TYPE
      OBJECTS { hh3cLswFrameIndex, hh3cLswSlotIndex, hh3cLswCpuIndex }
      STATUS  current
      DESCRIPTION
              "Node failed"
      ::= { hh3csLswTRAPMibObject 26 }

    hh3cCpuNormal NOTIFICATION-TYPE
      OBJECTS { hh3cLswFrameIndex, hh3cLswSlotIndex, hh3cLswCpuIndex }
      STATUS  current
      DESCRIPTION
              "Node normal"
      ::= { hh3csLswTRAPMibObject 27 }

      hh3cPowerIncompatible NOTIFICATION-TYPE
      OBJECTS { hh3cDevMPowerNum}
      STATUS  current
      DESCRIPTION
              "Power module is incompatible with the device"
      ::= { hh3csLswTRAPMibObject 28 }

      hh3cCpuUsageSevereNotification NOTIFICATION-TYPE
      OBJECTS {
            hh3cLswFrameIndex,
            hh3cLswSlotIndex,
            hh3cLswCpuIndex,
            hh3cLswCpuRatio,
            hh3cLswCpuUsageMinorThreshold,
            hh3cLswCpuUsageSevereThreshold,
            hh3cLswCpuUsageRecoverThreshold,
            hh3csLswTrapCpuCoreInfo,
            hh3csLswTrapProcessCpuInfo
            }
      STATUS current
      DESCRIPTION
            "The trap indicates that the CPU usage increased to or above
             the hh3cLswCpuUsageSevereThreshold."
      ::= { hh3csLswTRAPMibObject 29 }

      hh3cCpuUsageSevereRecoverNotification NOTIFICATION-TYPE
      OBJECTS {
            hh3cLswFrameIndex,
            hh3cLswSlotIndex,
            hh3cLswCpuIndex,
            hh3cLswCpuRatio,
            hh3cLswCpuUsageMinorThreshold,
            hh3cLswCpuUsageSevereThreshold,
            hh3cLswCpuUsageRecoverThreshold,
            hh3csLswTrapCpuCoreInfo,
            hh3csLswTrapProcessCpuInfo
            }
      STATUS current
      DESCRIPTION
            "
            When the product does not support hh3cLswCpuUsageRecoverThreshold,
            the trap indicates that the CPU usage decreased to or below
            the hh3cLswCpuUsageSevereThreshold.
            When the product supports hh3cLswCpuUsageRecoverThreshold,
            the trap indicates that the CPU usage decreased to or below
            the hh3cLswCpuUsageMinorThreshold.
            "
      ::= { hh3csLswTRAPMibObject 30 }

      hh3cCpuUsageMinorNotification NOTIFICATION-TYPE
      OBJECTS {
            hh3cLswFrameIndex,
            hh3cLswSlotIndex,
            hh3cLswCpuIndex,
            hh3cLswCpuRatio,
            hh3cLswCpuUsageMinorThreshold,
            hh3cLswCpuUsageSevereThreshold,
            hh3cLswCpuUsageRecoverThreshold,
            hh3csLswTrapCpuCoreInfo,
            hh3csLswTrapProcessCpuInfo
            }
      STATUS current
      DESCRIPTION
            "The trap indicates that the CPU usage increased to or above
             the hh3cLswCpuUsageMinorThreshold."
      ::= { hh3csLswTRAPMibObject 31 }

      hh3cCpuUsageMinorRecoverNotification NOTIFICATION-TYPE
      OBJECTS {
            hh3cLswFrameIndex,
            hh3cLswSlotIndex,
            hh3cLswCpuIndex,
            hh3cLswCpuRatio,
            hh3cLswCpuUsageMinorThreshold,
            hh3cLswCpuUsageSevereThreshold,
            hh3cLswCpuUsageRecoverThreshold,
            hh3csLswTrapCpuCoreInfo,
            hh3csLswTrapProcessCpuInfo
            }
      STATUS current
      DESCRIPTION
            "
            When the product dose not support hh3cLswCpuUsageRecoverThreshold,
            the trap indicates that the CPU usage decreased to or below
            the hh3cLswCpuUsageMinorThreshold.
            When the product supports hh3cLswCpuUsageRecoverThreshold,
            the trap indicates that the CPU usage decreased to or below
            the hh3cLswCpuUsageRecoverThreshold.
            "
      ::= { hh3csLswTRAPMibObject 32 }

      hh3cMemoryUsageEarlyWarningNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory decreased to or below
            the hh3cMemoryUsageEarlyWarningThreshold."
      ::= { hh3csLswTRAPMibObject 33 }

      hh3cMemoryUsageEarlyWarningRecoverNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory usage increased to or above
             the hh3cMemoryUsageSecureThreshold."
      ::= { hh3csLswTRAPMibObject 34 }

      hh3cMemoryUsageMinorNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory decreased to or below
            the hh3cLswCpuMemoryMinorThreshold."
      ::= { hh3csLswTRAPMibObject 35 }

      hh3cMemoryUsageMinorRecoverNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory usage increased to or above
             the hh3cLswCpuMemoryNormalThreshold."
      ::= { hh3csLswTRAPMibObject 36 }

      hh3cMemoryUsageSevereNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory decreased to or below
             the hh3cMemoryUsageSevereThreshold."
      ::= { hh3csLswTRAPMibObject 37 }

      hh3cMemoryUsageSevereRecoverNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory usage increased to or above
            the hh3cMemoryUsageMinorThreshold."
      ::= { hh3csLswTRAPMibObject 38 }

      hh3cMemoryUsageCriticalNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory decreased to or below
             the hh3cMemoryUsageCriticalThreshold."
      ::= { hh3csLswTRAPMibObject 39 }

      hh3cMemoryUsageCriticalRecoverNotification NOTIFICATION-TYPE
      OBJECTS {
            hh3cLswFrameIndex,
            hh3cLswSlotIndex,
            hh3cLswCpuIndex,
            hh3cLswCpuMemory,
            hh3cLswCpuMemoryFree,
            hh3cLswCpuMemoryFreeRatio,
            hh3cLswCpuMemoryHighTotal,
            hh3cLswCpuMemoryHighFree,
            hh3cLswCpuMemoryLowTotal,
            hh3cLswCpuMemoryLowFree,
            hh3cLswCpuMemorySecureThreshold,
            hh3cLswCpuMemoryEarlyWarningThreshold,
            hh3cLswCpuMemoryNormalThreshold,
            hh3cLswCpuMemoryMinorThreshold,
            hh3cLswCpuMemorySevereThreshold,
            hh3cLswCpuMemoryCriticalThreshold,
            hh3cLswCpuMemoryCurrentState,
            hh3csLswTrapProcessMemoryInfo,
            hh3csLswTrapSlubInfo
            }
      STATUS current
      DESCRIPTION
            "The trap indicates that the amount of free memory usage increased to or above
             the hh3cMemoryUsageSevereThreshold."
      ::= { hh3csLswTRAPMibObject 40 }

    hh3cNetworkHealthMonitorFailure OBJECT IDENTIFIER ::= { hh3csLswTRAPMibObject 98 }
    hh3cNetworkHealthMonitorNormal OBJECT IDENTIFIER ::= { hh3csLswTRAPMibObject 99 }

-- For compatibility reasons, DO NOT add notification nodes under hh3csLswTRAPMibObject.
-- Please use hh3csLswTRAPMibObjectV2Prefix instead.

-- ==================================================================
--
-- lsw trap info
--
-- ==================================================================
   hh3csLswTRAPMibInfor OBJECT IDENTIFIER ::= { hh3cLswTrapMib 2 }

   hh3csLswTrapCpuCoreInfo OBJECT-TYPE
        SYNTAX      SnmpAdminString (SIZE (0..255))
        MAX-ACCESS  accessible-for-notify
        STATUS      current
        DESCRIPTION
            "hh3cLswCpuCoreIndex,hh3cLswCpuCoreUsage,hh3cLswCpuCoreUsr,
             hh3cLswCpuCoreSys,hh3cLswCpuCoreIrq,hh3cLswCpuCoreIdle.

            Each line contains the following comma-separated values:

            hh3cLswCpuCoreIndex(Integer32):CPU core index.
            hh3cLswCpuCoreUsage(Unsigned32): Percentage of CPU core usage ,0~100
            hh3cLswCpuCoreUsr(Unsigned32): Percentage of CPU core user usage ,0~100
            hh3cLswCpuCoreSys(Unsigned32): Percentage of CPU core system usage ,0~100
            hh3cLswCpuCoreIrq(Unsigned32): Percentage of CPU core interrupt usage ,0~100
            hh3cLswCpuCoreIdle(Unsigned32): Percentage of CPU core idle usage ,0~100
            "
        ::= { hh3csLswTRAPMibInfor 1}

   hh3csLswTrapProcessCpuInfo OBJECT-TYPE
        SYNTAX      SnmpAdminString (SIZE (0..255))
        MAX-ACCESS  accessible-for-notify
        STATUS      current
        DESCRIPTION
            "hh3cLswProcessJobId,hh3cLswProcessPid,hh3cLswProcessName,
            hh3cLswProcessState,hh3cLswProcessPriority,hh3cLswProcessFDs,
            hh3cLswProcessRunTime,hh3cLswProcessCpuRatio5Secs,hh3cLswProcessCpuRatio1Min,
            hh3cLswProcessCpuRatio5Mins.

            Each line contains the following comma-separated values:

            hh3cLswProcessName: Process name
            hh3cLswProcessJobId:Job ID
            hh3cLswProcessPid: Process ID
            hh3cLswProcessPriority: Process priority
            hh3cLswProcessState: Process state
                {
                R(1):running,
                S(2):sleeping,
                T(3):tracedorStopped,
                D(4):uninterruptibleSleep,
                Z(5):zombie
                }
            hh3cLswProcessFDs: Process FDs
            hh3cLswProcessRunTime: Process run time
            hh3cLswProcessCpuRatio: CPU ratio for the process.
            "
        ::= { hh3csLswTRAPMibInfor 2 }

   hh3csLswTrapProcessMemoryInfo OBJECT-TYPE
        SYNTAX      SnmpAdminString (SIZE (0..255))
        MAX-ACCESS  accessible-for-notify
        STATUS      current
        DESCRIPTION
            "hh3cLswProcessJobId,hh3cLswProcessName,hh3cLswProcessMemoryUsed.

            Each line contains the following comma-separated values:

            hh3cLswProcessJobId: Job ID
            hh3cLswProcessName: Process name
            hh3cLswProcessMemoryUsed:
            Memory be used by the process(text + data + stack + dynamic)in KB.
            "
        ::= { hh3csLswTRAPMibInfor 3 }

   hh3csLswTrapSlubInfo OBJECT-TYPE
        SYNTAX      SnmpAdminString (SIZE (0..255))
        MAX-ACCESS  accessible-for-notify
        STATUS      current
        DESCRIPTION
            "hh3cLswSlubInfoUsed + hh3cLswSlubInfoName.

            Each line contains the following comma-separated values:

            hh3cLswSlubInfoName: Name of slubinfo
            hh3cLswSlubInfoUsed: Memory be used by the slub(num*size)
            "
        ::= { hh3csLswTRAPMibInfor 4 }

    hh3cLswTrapCpuUsage OBJECT-TYPE
        SYNTAX      SnmpAdminString (SIZE (0..255))
        MAX-ACCESS  accessible-for-notify
        STATUS      current
        DESCRIPTION
            "Cpu usage in 5sec 1min 5min."
        ::= { hh3csLswTRAPMibInfor 5 }

    hh3cLswTrapCoreProcessInfo OBJECT-TYPE
        SYNTAX      SnmpAdminString (SIZE (0..255))
        MAX-ACCESS  accessible-for-notify
        STATUS      current
        DESCRIPTION
            "
            Each line contains the following values:
            JID PID PPID CPU State Memory 5Sec 1Min 5Min Name.
            "
        ::= { hh3csLswTRAPMibInfor 6 }

    hh3cLswCoreTrapUsage   OBJECT-TYPE
        SYNTAX     Unsigned32
        MAX-ACCESS     accessible-for-notify
        STATUS     current
        DESCRIPTION
            "Core usage in last 30 minutes."
        ::= {hh3csLswTRAPMibInfor 7}

    hh3cBoardAvailablePower OBJECT-TYPE
        SYNTAX      Integer32
        MAX-ACCESS  accessible-for-notify
        STATUS      current
        DESCRIPTION
            "Available power of power supply."
        ::= { hh3csLswTRAPMibInfor 8 }

    hh3cBoardRequiredPower OBJECT-TYPE
        SYNTAX      Integer32
        MAX-ACCESS  accessible-for-notify
        STATUS      current
        DESCRIPTION
            "Power required for a single board."
        ::= { hh3csLswTRAPMibInfor 9 }

    hh3cLswAlarmInPortInNum OBJECT-TYPE
        SYNTAX      Unsigned32
        MAX-ACCESS  accessible-for-notify
        STATUS      current
        DESCRIPTION
            "Alarm-in port-in num."
        ::= { hh3csLswTRAPMibInfor 10 }

    hh3cDMAMemoryTotal   OBJECT-TYPE
        SYNTAX     CounterBasedGauge64
        UNITS "byte"
        MAX-ACCESS     accessible-for-notify
        STATUS     current
        DESCRIPTION
            "The total DMA-memory space on the node."
        ::= { hh3csLswTRAPMibInfor 11 }

    hh3cDMAMemoryUsed   OBJECT-TYPE
        SYNTAX     CounterBasedGauge64
        UNITS "byte"
        MAX-ACCESS     accessible-for-notify
        STATUS     current
        DESCRIPTION
            "The used DMA-memory space on the node."
        ::= { hh3csLswTRAPMibInfor 12 }

    hh3cDMAMemoryFree   OBJECT-TYPE
        SYNTAX     CounterBasedGauge64
        UNITS "byte"
        MAX-ACCESS     accessible-for-notify
        STATUS     current
        DESCRIPTION
            "The free memory space on the node."
        ::= { hh3csLswTRAPMibInfor 13 }

    hh3cDMAMemoryFreeRatio   OBJECT-TYPE
        SYNTAX     Unsigned32 (0..100)
        MAX-ACCESS     accessible-for-notify
        STATUS     current
        DESCRIPTION
            "The percentage of free DMA-memory space on the node."
        ::= { hh3csLswTRAPMibInfor 14 }

    hh3cDMAMemoryCriticalThreshold   OBJECT-TYPE
        SYNTAX     Unsigned32
        MAX-ACCESS     accessible-for-notify
        STATUS     current
        DESCRIPTION
            "The critical alarm threshold for free DMA-memory,
             MB or percentage."
        ::= { hh3csLswTRAPMibInfor 15 }

    hh3cDMAMemoryRecoverThreshold   OBJECT-TYPE
        SYNTAX     Unsigned32
        MAX-ACCESS     accessible-for-notify
        STATUS     current
        DESCRIPTION
            "The normal state threshold for free DMA-memory,
             MB or percentage.

             When the free DMA-memory space exceeds this threshold, a recovery notification will be sent.
             The normal state threshold cannot be smaller than the critical alarm threshold."
        ::= { hh3csLswTRAPMibInfor 16 }

    hh3cDMAMemoryCurrentState   OBJECT-TYPE
        SYNTAX          INTEGER
        {
            normal (1),
            critical (2)
        }
        MAX-ACCESS     accessible-for-notify
        STATUS     current
        DESCRIPTION
            "Current status of free DMA-memory.

             Normal
             Critical"
        ::= { hh3csLswTRAPMibInfor 17 }

    hh3cFrameRemainingPower   OBJECT-TYPE
        SYNTAX     Unsigned32
        UNITS "W"
        MAX-ACCESS     accessible-for-notify
        STATUS     current
        DESCRIPTION
            "Remaining power of the frame."
        ::= {hh3csLswTRAPMibInfor 18}

    hh3cHeartbeatTimeoutSeconds   OBJECT-TYPE
        SYNTAX     Unsigned32
        MAX-ACCESS     accessible-for-notify
        STATUS     current
        DESCRIPTION
            "Heartbeat timeout value, in seconds."
        ::= {hh3csLswTRAPMibInfor 19}

    hh3cDevTrapSrcChassis   OBJECT-TYPE
        SYNTAX      Integer32
        MAX-ACCESS  accessible-for-notify
        STATUS      current
        DESCRIPTION
            "Source chassis number."
        ::= {hh3csLswTRAPMibInfor 20}

    hh3cDevTrapSrcSlot   OBJECT-TYPE
        SYNTAX      Integer32
        MAX-ACCESS  accessible-for-notify
        STATUS      current
        DESCRIPTION
            "Source slot number."
        ::= {hh3csLswTRAPMibInfor 21}

    hh3cDevTrapSrcCpu   OBJECT-TYPE
        SYNTAX      Integer32
        MAX-ACCESS  accessible-for-notify
        STATUS      current
        DESCRIPTION
            "Source CPU number."
        ::= {hh3csLswTRAPMibInfor 22}

    hh3cDevTrapDestChassis   OBJECT-TYPE
        SYNTAX      Integer32
        MAX-ACCESS  accessible-for-notify
        STATUS      current
        DESCRIPTION
            "Destination chassis number."
        ::= {hh3csLswTRAPMibInfor 23}

    hh3cDevTrapDestSlot   OBJECT-TYPE
        SYNTAX      Integer32
        MAX-ACCESS  accessible-for-notify
        STATUS      current
        DESCRIPTION
            "Destination slot number."
        ::= {hh3csLswTRAPMibInfor 24}

    hh3cDevTrapDestCpu   OBJECT-TYPE
        SYNTAX      Integer32
        MAX-ACCESS  accessible-for-notify
        STATUS      current
        DESCRIPTION
            "Destination CPU number."
        ::= {hh3csLswTRAPMibInfor 25}

    hh3cDevTrapRebootReason   OBJECT-TYPE
        SYNTAX      SnmpAdminString (SIZE (0..255))
        MAX-ACCESS  accessible-for-notify
        STATUS      current
        DESCRIPTION
            "Reboot failure reason."
        ::= {hh3csLswTRAPMibInfor 26}

    hh3cDevTrapSlaveSwitchFailReason   OBJECT-TYPE
        SYNTAX      INTEGER {
                        other(0),
                        systemRestarting(1),
                        standbyAbsent(2),
                        standbyNoReady(3)
                    }
        MAX-ACCESS  accessible-for-notify
        STATUS      current
        DESCRIPTION
            "Reason for active/standby or master/subordinate switchover failure."
        ::= {hh3csLswTRAPMibInfor 27}

    hh3cDevTrapFanFailureErrcode   OBJECT-TYPE
        SYNTAX      INTEGER {
                        remove(0),
                        failed(1)
                    }
        MAX-ACCESS  accessible-for-notify
        STATUS      current
        DESCRIPTION
            "Cause of fan failure."
        ::= {hh3csLswTRAPMibInfor 28}

    hh3cDevTrapSliceIndex   OBJECT-TYPE
        SYNTAX      Unsigned32
        MAX-ACCESS  accessible-for-notify
        STATUS      current
        DESCRIPTION
            "Slice index."
        ::= {hh3csLswTRAPMibInfor 29}

    hh3cDevTrapPressKeyName   OBJECT-TYPE
        SYNTAX      SnmpAdminString (SIZE (0..255))
        MAX-ACCESS  accessible-for-notify
        STATUS      current
        DESCRIPTION
            "Device button name."
        ::= {hh3csLswTRAPMibInfor 30}

    hh3cDevTrapPressKeyOper   OBJECT-TYPE
        SYNTAX      SnmpAdminString (SIZE (0..255))
        MAX-ACCESS  accessible-for-notify
        STATUS      current
        DESCRIPTION
            "Operations triggered by device keys."
        ::= {hh3csLswTRAPMibInfor 31}

    hh3cDevSlotFaultTime   OBJECT-TYPE
        SYNTAX      Integer32
        MAX-ACCESS  accessible-for-notify
        STATUS      current
        DESCRIPTION
            "The duration of the fault state."
        ::= {hh3csLswTRAPMibInfor 32}

    hh3cDevClockOldTime   OBJECT-TYPE
        SYNTAX      SnmpAdminString (SIZE (0..255))
        MAX-ACCESS  accessible-for-notify
        STATUS      current
        DESCRIPTION
            "the old time."
        ::= {hh3csLswTRAPMibInfor 33}

    hh3cDevClockNewTime   OBJECT-TYPE
        SYNTAX      SnmpAdminString (SIZE (0..255))
        MAX-ACCESS  accessible-for-notify
        STATUS      current
        DESCRIPTION
            "the new time."
        ::= {hh3csLswTRAPMibInfor 34}

    hh3cDevProcessID   OBJECT-TYPE
        SYNTAX          Unsigned32
        MAX-ACCESS      accessible-for-notify
        STATUS          current
        DESCRIPTION
            "This object indicates the identifier of process, namely task ID
            in system."
        ::= { hh3csLswTRAPMibInfor 35 }

    hh3cDevProcessName   OBJECT-TYPE
        SYNTAX          DisplayString(SIZE(1..32))
        MAX-ACCESS      accessible-for-notify
        STATUS          current
        DESCRIPTION
            "This object indicates the process name."
        ::= { hh3csLswTRAPMibInfor 36 }

    hh3csLswTRAPMibObjectV2 OBJECT IDENTIFIER ::= { hh3cLswTrapMib 3 }
    hh3csLswTRAPMibObjectV2Prefix OBJECT IDENTIFIER ::= { hh3csLswTRAPMibObjectV2 0 }

    hh3cCoreUsageNotification NOTIFICATION-TYPE
      OBJECTS {
            hh3cLswFrameIndex,
            hh3cLswSlotIndex,
            hh3cLswCpuIndex,
            hh3cLswCoreIndex,
            hh3cLswCoreTrapUsage,
            hh3cLswCoreThreshold,
            hh3cLswTrapCpuUsage,
            hh3cLswTrapCoreProcessInfo,
            hh3cLswCoreMinorThreshold,
            hh3cLswCoreRecoveryThreshold
            }
      STATUS current
      DESCRIPTION
            "The trap indicates that the amount of core usage increased to or above
             the hh3cLswCoreThreshold."
      ::= { hh3csLswTRAPMibObjectV2Prefix 1 }

    hh3cBoardPowerNotEnough NOTIFICATION-TYPE
      OBJECTS { hh3cLswFrameIndex, hh3cLswSlotIndex, hh3cBoardAvailablePower, hh3cBoardRequiredPower}
      STATUS  current
      DESCRIPTION
              "Not enough power for the board."
      ::= { hh3csLswTRAPMibObjectV2Prefix 2 }

    hh3cAlarmInPortIn NOTIFICATION-TYPE
        OBJECTS { hh3cLswFrameIndex, hh3cLswSlotIndex, hh3cLswAlarmInPortInNum }
        STATUS current
        DESCRIPTION
            "Alarm reported on the alarm-in port."
        ::= { hh3csLswTRAPMibObjectV2Prefix 3 }

    hh3cAlarmInPortRecover NOTIFICATION-TYPE
        OBJECTS { hh3cLswFrameIndex, hh3cLswSlotIndex, hh3cLswAlarmInPortInNum }
        STATUS current
        DESCRIPTION
            "Alarm removed on the alarm-in port."
        ::= { hh3csLswTRAPMibObjectV2Prefix 4 }

    hh3cCoreUsageSevereRecoveryNotification NOTIFICATION-TYPE
      OBJECTS {
            hh3cLswFrameIndex,
            hh3cLswSlotIndex,
            hh3cLswCpuIndex,
            hh3cLswCoreIndex,
            hh3cLswCoreTrapUsage,
            hh3cLswCoreThreshold,
            hh3cLswTrapCpuUsage,
            hh3cLswTrapCoreProcessInfo,
            hh3cLswCoreMinorThreshold,
            hh3cLswCoreRecoveryThreshold
            }
      STATUS current
      DESCRIPTION
            "
            When the product does not support hh3cLswCoreRecoveryThreshold,
            the trap indicates that the core usage decreased to or below
            the hh3cLswCoreThreshold.
            When the product supports hh3cLswCoreRecoveryThreshold,
            the trap indicates that the core usage decreased to or below
            the hh3cLswCoreMinorThreshold.
            "
      ::= { hh3csLswTRAPMibObjectV2Prefix 10 }

    hh3cCoreUsageMinorNotification NOTIFICATION-TYPE
      OBJECTS {
            hh3cLswFrameIndex,
            hh3cLswSlotIndex,
            hh3cLswCpuIndex,
            hh3cLswCoreIndex,
            hh3cLswCoreTrapUsage,
            hh3cLswCoreThreshold,
            hh3cLswTrapCpuUsage,
            hh3cLswTrapCoreProcessInfo,
            hh3cLswCoreMinorThreshold,
            hh3cLswCoreRecoveryThreshold
            }
      STATUS current
      DESCRIPTION
            "The trap indicates that the core usage increased to or above
             the hh3cLswCoreMinorThreshold."
      ::= { hh3csLswTRAPMibObjectV2Prefix 11 }

    hh3cCoreUsageMinorRecoveryNotification NOTIFICATION-TYPE
      OBJECTS {
            hh3cLswFrameIndex,
            hh3cLswSlotIndex,
            hh3cLswCpuIndex,
            hh3cLswCoreIndex,
            hh3cLswCoreTrapUsage,
            hh3cLswCoreThreshold,
            hh3cLswTrapCpuUsage,
            hh3cLswTrapCoreProcessInfo,
            hh3cLswCoreMinorThreshold,
            hh3cLswCoreRecoveryThreshold
            }
      STATUS current
      DESCRIPTION
            "
            When the product does not support hh3cLswCoreRecoveryThreshold,
            the trap indicates that the core usage decreased to or below
            the hh3cLswCoreMinorThreshold.
            When the product supports hh3cLswCoreRecoveryThreshold,
            the trap indicates that the core usage decreased to or below
            the hh3cLswCoreRecoveryThreshold.
            "
      ::= { hh3csLswTRAPMibObjectV2Prefix 12 }

      hh3cDMAMemoryUsageCriticalNotification NOTIFICATION-TYPE
      OBJECTS {
            hh3cLswFrameIndex,
            hh3cLswSlotIndex,
            hh3cLswCpuIndex,
            hh3cDMAMemoryTotal,
            hh3cDMAMemoryUsed,
            hh3cDMAMemoryFree,
            hh3cDMAMemoryCurrentState,
            hh3cDMAMemoryFreeRatio,
            hh3cDMAMemoryCriticalThreshold
            }
      STATUS current
      DESCRIPTION
            "The trap indicates that the free DMA-memory space decreased to or below
             the critical alarm threshold."
      ::= { hh3csLswTRAPMibObjectV2Prefix 41 }

      hh3cDMAMemoryUsageRecoverNotification NOTIFICATION-TYPE
      OBJECTS {
            hh3cLswFrameIndex,
            hh3cLswSlotIndex,
            hh3cLswCpuIndex,
            hh3cDMAMemoryTotal,
            hh3cDMAMemoryUsed,
            hh3cDMAMemoryFree,
            hh3cDMAMemoryCurrentState,
            hh3cDMAMemoryFreeRatio,
            hh3cDMAMemoryRecoverThreshold
            }
      STATUS current
      DESCRIPTION
            "The trap indicates that the of free DMA-memory space increased to or above
             the normal state threshold."
      ::= { hh3csLswTRAPMibObjectV2Prefix 42 }

      hh3cRemainingPowerNotEnough NOTIFICATION-TYPE
      OBJECTS {
            hh3cLswFrameIndex,
            hh3cFrameRemainingPower
            }
      STATUS current
      DESCRIPTION
            "The trap indicates that the remaining power of the chassis is not enouth."
      ::= { hh3csLswTRAPMibObjectV2Prefix 43 }

    hh3cMMUParityError NOTIFICATION-TYPE
      OBJECTS {
            hh3cLswFrameIndex,
            hh3cLswSlotIndex,
            hh3cLswCpuIndex
            }
      STATUS current
      DESCRIPTION
            "MMU(Memory Management Unit) checking error on the slot is detected,
             rebooting the slot is recommended."
      ::= { hh3csLswTRAPMibObjectV2Prefix 44 }

      hh3cOutputPowerStatusNotification NOTIFICATION-TYPE
      OBJECTS { hh3cLswFrameIndex, hh3cLswSlotIndex, hh3cLswOutputPowerPortID, hh3cLswOutputPowerStatus }
      STATUS current
      DESCRIPTION
            "The trap indicates that over voltage or over current."
      ::= { hh3csLswTRAPMibObjectV2Prefix 45 }

      hh3cBoardHeartbeatTimeout NOTIFICATION-TYPE
      OBJECTS { hh3cLswFrameIndex, hh3cLswSlotIndex, hh3cLswCpuIndex, hh3cHeartbeatTimeoutSeconds }
      STATUS current
      DESCRIPTION
            "This notification is generated when heartbeat between the MPU and a card times out."
      ::= { hh3csLswTRAPMibObjectV2Prefix 46 }

      hh3cBoardHeartbeatResume NOTIFICATION-TYPE
      OBJECTS { hh3cLswFrameIndex, hh3cLswSlotIndex, hh3cLswCpuIndex }
      STATUS current
      DESCRIPTION
            "This notification is generated when heartbeat between the MPU and a card recovers."
      ::= { hh3csLswTRAPMibObjectV2Prefix 47 }

      hh3cCommunicateError  NOTIFICATION-TYPE
      OBJECTS
          {
              hh3cDevTrapSrcChassis,
              hh3cDevTrapSrcSlot,
              hh3cDevTrapSrcCpu,
              hh3cDevTrapDestChassis,
              hh3cDevTrapDestSlot,
              hh3cDevTrapDestCpu
          }
      STATUS current
      DESCRIPTION
          "This notification is generated when communication between LIPC nodes times out."
      ::= { hh3csLswTRAPMibObjectV2Prefix 48 }

      hh3cCommunicateResume  NOTIFICATION-TYPE
      OBJECTS
          {
              hh3cDevTrapSrcChassis,
              hh3cDevTrapSrcSlot,
              hh3cDevTrapSrcCpu,
              hh3cDevTrapDestChassis,
              hh3cDevTrapDestSlot,
              hh3cDevTrapDestCpu
          }
      STATUS current
      DESCRIPTION
          "This notification is generated when LIPC nodes are reconnected after they are disconnected."
      ::= { hh3csLswTRAPMibObjectV2Prefix 49 }

      hh3cBoardRebooted  NOTIFICATION-TYPE
      OBJECTS
          {
              hh3cDevTrapRebootReason,
              hh3cDevTrapSrcChassis,
              hh3cDevTrapSrcSlot,
              hh3cDevTrapSrcCpu
          }
      STATUS current
      DESCRIPTION
          "This notification is generated when reboot fails for a single card or member device."
      ::= { hh3csLswTRAPMibObjectV2Prefix 50 }

      hh3cDevTrapSlaveSwitchFail  NOTIFICATION-TYPE
      OBJECTS
          {
              hh3cDevTrapSlaveSwitchFailReason
          }
      STATUS current
      DESCRIPTION
          "This notification is generated when an active/standby or master/subordinate switchover fails."
      ::= { hh3csLswTRAPMibObjectV2Prefix 51 }

      hh3cAllBoardHeartbeatTimeout  NOTIFICATION-TYPE
      OBJECTS
          {
              hh3cHeartbeatTimeoutSeconds
          }
      STATUS current
      DESCRIPTION
          "This notification is generated when the active MPU or master device is disconnected from all cards or member devices."
      ::= { hh3csLswTRAPMibObjectV2Prefix 52 }

      hh3cAllBoardHeartbeatResume  NOTIFICATION-TYPE
      STATUS current
      DESCRIPTION
          "This notification is generated when the active MPU or master device is reconnected to any card or member device after a disconnection."
      ::= { hh3csLswTRAPMibObjectV2Prefix 53 }

      hh3cBladeNotInsertedNotCleared NOTIFICATION-TYPE
      OBJECTS { hh3cLswFrameIndex, hh3cLswSlotIndex, hh3cLswCpuIndex }
      STATUS  current
      DESCRIPTION
          "This notification is generated when a blade controller is not reinserted or data about the blade controller
       is not cleared a long time after it is removed."
      ::= { hh3csLswTRAPMibObjectV2Prefix 54 }

      hh3cBladeInsertedCleared NOTIFICATION-TYPE
      OBJECTS { hh3cLswFrameIndex, hh3cLswSlotIndex, hh3cLswCpuIndex }
      STATUS  current
      DESCRIPTION
          "This notification is generated when the removed blade controller is reinserted or data about the removed blade controller is cleared."
      ::= { hh3csLswTRAPMibObjectV2Prefix 55 }

    hh3cDevTrapSliceStarting NOTIFICATION-TYPE
      OBJECTS { hh3cLswFrameIndex, hh3cLswSlotIndex, hh3cDevTrapSliceIndex }
      STATUS current
      DESCRIPTION
          "This notification is generated when the Slice module is starting."
      ::= { hh3csLswTRAPMibObjectV2Prefix 56 }

    hh3cDevTrapSliceOnline NOTIFICATION-TYPE
      OBJECTS { hh3cLswFrameIndex, hh3cLswSlotIndex, hh3cDevTrapSliceIndex }
      STATUS  current
      DESCRIPTION
          "This notification is generated when the slice module is onlined."
      ::= { hh3csLswTRAPMibObjectV2Prefix 57 }

    hh3cDevTrapSliceOffline NOTIFICATION-TYPE
      OBJECTS { hh3cLswFrameIndex, hh3cLswSlotIndex, hh3cDevTrapSliceIndex }
      STATUS  current
      DESCRIPTION
          "This notification is generated when the slice module is offlined."
      ::= { hh3csLswTRAPMibObjectV2Prefix 58 }

    hh3cBoardReceiveWrongPackets NOTIFICATION-TYPE
      OBJECTS { hh3cLswFrameIndex, hh3cLswSlotIndex, hh3cLswCpuIndex }
      STATUS  current
      DESCRIPTION
          "This notification is generated when a board has received some wrong packets."
      ::= { hh3csLswTRAPMibObjectV2Prefix 59 }

    hh3cDevPressKeyOperNotification NOTIFICATION-TYPE
      OBJECTS { hh3cDevTrapPressKeyName, hh3cDevTrapPressKeyOper }
      STATUS  current
      DESCRIPTION
          "This notification is generated When the reset key is pressed."
      ::= { hh3csLswTRAPMibObjectV2Prefix 60 }

    hh3cDevBatchBackupStart NOTIFICATION-TYPE
      OBJECTS { hh3cLswFrameIndex, hh3cLswSlotIndex, hh3cLswCpuIndex }
      STATUS current
      DESCRIPTION
            "The batch backup between main process unit starts."
      ::= { hh3csLswTRAPMibObjectV2Prefix 61 }

    hh3cDevBatchBackupFinish NOTIFICATION-TYPE
      OBJECTS { hh3cLswFrameIndex, hh3cLswSlotIndex, hh3cLswCpuIndex }
      STATUS current
      DESCRIPTION
            "The batch backup between main process unit completed."
      ::= { hh3csLswTRAPMibObjectV2Prefix 62 }

    hh3cDevStandbyNotReady NOTIFICATION-TYPE
      OBJECTS { hh3cLswFrameIndex, hh3cLswSlotIndex, hh3cLswCpuIndex }
      STATUS current
      DESCRIPTION
            "When the device performs active/standby switchover, the standby board is not ready."
      ::= { hh3csLswTRAPMibObjectV2Prefix 63 }

    hh3cDevStandbyToMaster NOTIFICATION-TYPE
      OBJECTS { hh3cLswFrameIndex, hh3cLswSlotIndex, hh3cLswCpuIndex }
      STATUS current
      DESCRIPTION
            "The role of the standby main control board becomes the active main control board."
      ::= { hh3csLswTRAPMibObjectV2Prefix 64 }

    hh3cDevProcessAbnormal NOTIFICATION-TYPE
      OBJECTS { hh3cLswFrameIndex, hh3cLswSlotIndex, hh3cLswCpuIndex, hh3cDevProcessID, hh3cDevProcessName }
      STATUS current
      DESCRIPTION
            "The trap indicates that The process exited abnormally."
      ::= { hh3csLswTRAPMibObjectV2Prefix 65 }

    hh3cDevAutoSwitchFault NOTIFICATION-TYPE
      OBJECTS { hh3cDevTrapSrcChassis }
      STATUS current
      DESCRIPTION
            "This notification is generated when the automatic switching of the device between primary and backup."
      ::= { hh3csLswTRAPMibObjectV2Prefix 66 }

    hh3cDevAutoSwitchFaultReboot NOTIFICATION-TYPE
      OBJECTS
          {
              hh3cDevTrapSrcChassis,
              hh3cDevTrapSrcSlot,
              hh3cDevTrapSrcCpu
          }
      STATUS current
      DESCRIPTION
            "This notification is generated when the automatic switching of the device between active and standby, the device will immediately restart the faulty board to recover the fault."
      ::= { hh3csLswTRAPMibObjectV2Prefix 67 }

    hh3cDevBoardFaultTooLong NOTIFICATION-TYPE
      OBJECTS
          {
              hh3cDevSlotFaultTime,
              hh3cDevTrapSrcChassis,
              hh3cDevTrapSrcSlot,
              hh3cDevTrapSrcCpu
          }
      STATUS current
      DESCRIPTION
            "This notification is generated when the board has been in a Fault state for a long time."
      ::= { hh3csLswTRAPMibObjectV2Prefix 68 }

    hh3cDevClockChange NOTIFICATION-TYPE
      OBJECTS
          {
              hh3cDevTrapSrcChassis,
              hh3cDevClockOldTime,
              hh3cDevClockNewTime
          }
      STATUS current
      DESCRIPTION
            "This notification is generated when system time has changed."
      ::= { hh3csLswTRAPMibObjectV2Prefix 69 }

    hh3cDevBoardRunningFault NOTIFICATION-TYPE
      OBJECTS
          {
              hh3cDevTrapSrcChassis,
              hh3cDevTrapSrcSlot
          }
      STATUS current
      DESCRIPTION
            "This notification is generated when heartbeat between the Board fault detected."
      ::= { hh3csLswTRAPMibObjectV2Prefix 70 }

    hh3cDevBoardRunningFaultReboot NOTIFICATION-TYPE
      OBJECTS
          {
              hh3cDevTrapSrcChassis,
              hh3cDevTrapSrcSlot
          }
      STATUS current
      DESCRIPTION
            "This notification is generated when heartbeat between the MPU and a card times out."
      ::= { hh3csLswTRAPMibObjectV2Prefix 71 }

    hh3cDevFdUPLimited NOTIFICATION-TYPE
      OBJECTS {
                 hh3cDevProcessName,
                 hh3cDevProcessID
              }
      STATUS current
      DESCRIPTION
            "File descriptor number upper limit already reached."
      ::= { hh3csLswTRAPMibObjectV2Prefix 72 }

    hh3cDevFdUPReachLimit NOTIFICATION-TYPE
      OBJECTS {
                 hh3cDevProcessName,
                 hh3cDevProcessID
              }
      STATUS current
      DESCRIPTION
            "Number of FDs is about to reach the upper limit."
      ::= { hh3csLswTRAPMibObjectV2Prefix 73 }

    hh3cSystemSecurityRiskOccur NOTIFICATION-TYPE
      STATUS current
      DESCRIPTION
            "The device has non security algorithms, protocols or configurations."
      ::= { hh3csLswTRAPMibObjectV2Prefix 74 }

    hh3cSystemSecurityRiskClear NOTIFICATION-TYPE
      STATUS current
      DESCRIPTION
            "All non security risk is cleared."
      ::= { hh3csLswTRAPMibObjectV2Prefix 75 }

    hh3cCpuGroupUsageSevereNotification NOTIFICATION-TYPE
      OBJECTS {
            hh3cLswFrameIndex,
            hh3cLswSlotIndex,
            hh3cLswCpuIndex,
            hh3cCpuGroupUsageGroupName,
            hh3cCpuGroupUsageSevereThreshold,
            hh3cCpuGroupUsageMinorThreshold,
            hh3cCpuGroupUsageRecovThreshold,
            hh3cCpuGroupUsageInterval,
            hh3cCpuGroupUsageAverageCpuUsage,
            hh3cCpuGroupUsageLast5sCpuUsage,
            hh3cCpuGroupUsageLast1mCpuUsage,
            hh3cCpuGroupUsageLast5mCpuUsage,
            hh3cCpuGroupUsageCurrentState
            }
      STATUS current
      DESCRIPTION
            "The trap indicates that the CPU group usage increased to or above
             the value for hh3cCpuGroupUsageSevereThreshold."
      ::= { hh3csLswTRAPMibObjectV2Prefix 76 }

      hh3cCpuGroupUsageSevereRecoverNotification NOTIFICATION-TYPE
      OBJECTS {
            hh3cLswFrameIndex,
            hh3cLswSlotIndex,
            hh3cLswCpuIndex,
            hh3cCpuGroupUsageGroupName,
            hh3cCpuGroupUsageSevereThreshold,
            hh3cCpuGroupUsageMinorThreshold,
            hh3cCpuGroupUsageRecovThreshold,
            hh3cCpuGroupUsageInterval,
            hh3cCpuGroupUsageAverageCpuUsage,
            hh3cCpuGroupUsageLast5sCpuUsage,
            hh3cCpuGroupUsageLast1mCpuUsage,
            hh3cCpuGroupUsageLast5mCpuUsage,
            hh3cCpuGroupUsageCurrentState
            }
      STATUS current
      DESCRIPTION
            "The trap indicates that the CPU group usage decreased to or below
            the value for hh3cCpuGroupUsageMinorThreshold.
            "
      ::= { hh3csLswTRAPMibObjectV2Prefix 77 }

      hh3cCpuGroupUsageMinorNotification NOTIFICATION-TYPE
      OBJECTS {
            hh3cLswFrameIndex,
            hh3cLswSlotIndex,
            hh3cLswCpuIndex,
            hh3cCpuGroupUsageGroupName,
            hh3cCpuGroupUsageSevereThreshold,
            hh3cCpuGroupUsageMinorThreshold,
            hh3cCpuGroupUsageRecovThreshold,
            hh3cCpuGroupUsageInterval,
            hh3cCpuGroupUsageAverageCpuUsage,
            hh3cCpuGroupUsageLast5sCpuUsage,
            hh3cCpuGroupUsageLast1mCpuUsage,
            hh3cCpuGroupUsageLast5mCpuUsage,
            hh3cCpuGroupUsageCurrentState
            }
      STATUS current
      DESCRIPTION
            "The trap indicates that the CPU group usage increased to or above
             the value for hh3cCpuGroupUsageMinorThreshold."
      ::= { hh3csLswTRAPMibObjectV2Prefix 78 }

      hh3cCpuGroupUsageMinorRecoverNotification NOTIFICATION-TYPE
      OBJECTS {
            hh3cLswFrameIndex,
            hh3cLswSlotIndex,
            hh3cLswCpuIndex,
            hh3cCpuGroupUsageGroupName,
            hh3cCpuGroupUsageSevereThreshold,
            hh3cCpuGroupUsageMinorThreshold,
            hh3cCpuGroupUsageRecovThreshold,
            hh3cCpuGroupUsageInterval,
            hh3cCpuGroupUsageAverageCpuUsage,
            hh3cCpuGroupUsageLast5sCpuUsage,
            hh3cCpuGroupUsageLast1mCpuUsage,
            hh3cCpuGroupUsageLast5mCpuUsage,
            hh3cCpuGroupUsageCurrentState
            }
      STATUS current
      DESCRIPTION
            "The trap indicates that the CPU group usage decreased to or below
            the value for hh3cCpuGroupUsageRecovThreshold.
            "
      ::= { hh3csLswTRAPMibObjectV2Prefix 79 }

END
