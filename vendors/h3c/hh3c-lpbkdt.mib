-- ==================================================================
-- Copyright (C) 2008-2023 New H3C Tech. Co., Ltd. All rights reserved.
--
-- Description: Loopback detection MIB
-- Reference:
-- Version: V1.5
-- History:
-- V1.0 2008-09-27 Created by LuoXuefang
-- V1.1 2009-03-30 Added hh3cLpbkdtTrapPerVlanLoopbacked,
--                 hh3cLpbkdtTrapPerVlanRecovered and
--                 hh3cLpbkdtObjects by TongWei.
-- V1.2 2014-07-26 Added hh3cLpbkdtVlanEnable, hh3cLpbkdtAction,
--                 hh3cLpbkdtIntervalTime, hh3cLpbkdtPortTable,
--                 hh3cLpbkdtPortEntry, hh3cLpbkdtPortIfIndex,
--                 hh3cLpbkdtPortVlanEnable, hh3cLpbkdtPortAction and
--                 hh3cLpbkdtPortLoopbacked by ZhangWei.
-- V1.3 2022-05-27 Added hh3cLpbkdtTrapVsiLoopbacked,
--                 hh3cLpbkdtTrapVsiRecovered by zhengjun.
-- V1.4 2022-07-18 Added hh3cLpbkdtTrapActionLOG, hh3cLpbkdtTrapActionLOGClear,
--                 hh3cLpbkdtTrapActionBlock, hh3cLpbkdtTrapActionBlockClear,
--                 hh3cLpbkdtTrapActionDown, hh3cLpbkdtTrapActionDownClear
--                 by zhengjun.
-- V1.5 2023-06-06 Added hh3cLpbkdtTrapVsiBlockFailed by zhengjun.
-- ==================================================================
HH3C-LPBKDT-MIB DEFINITIONS ::= BEGIN

IMPORTS
    hh3cCommon
        FROM HH3C-OID-MIB
    ifIndex, ifDescr
        FROM IF-MIB
    VlanId
        FROM Q-BRIDGE-MIB
    TEXTUAL-CONVENTION, TruthValue, DisplayString
        FROM SNMPv2-TC
    OBJECT-TYPE, MODULE-IDENTITY, NOTIFICATION-TYPE, Integer32
        FROM SNMPv2-SMI
    InterfaceIndex
        FROM IF-MIB;

hh3cLpbkdt MODULE-IDENTITY
    LAST-UPDATED "202306061111Z"        -- June 06, 2023 at 11:11 GMT
    ORGANIZATION "New H3C Technologies Co., Ltd."
    CONTACT-INFO
        "Comware Team New H3C Technologies Co., Ltd.
        Hai-Dian District Beijing P.R. China
        http://www.h3c.com
        Zip:100085"
    DESCRIPTION
        "Loops may cause broadcast storms.  The purpose of loopback detection
         is to detect loops on the device and to protect the network."
    REVISION "202306061111Z"
    DESCRIPTION
        "Added hh3cLpbkdtTrapVsiBlockFailed."
    REVISION "202207181101Z"
    DESCRIPTION
        "Added new trap hh3cLpbkdtTrapActionLOG, hh3cLpbkdtTrapActionLOGClear,
        hh3cLpbkdtTrapActionBlock, hh3cLpbkdtTrapActionBlockClear,
        hh3cLpbkdtTrapActionDown, hh3cLpbkdtTrapActionDownClear."
    REVISION "202205280926Z"
    DESCRIPTION
        "Added new trap hh3cLpbkdtTrapVsiLoopbacked, hh3cLpbkdtTrapVsiRecovered."
    REVISION "201407261518Z"
    DESCRIPTION
        "Added new nodes to configure the loop detection."
    REVISION "200903301741Z"
    DESCRIPTION
        "To fix bugs in the MIB file."
    REVISION "200809271504Z"
    DESCRIPTION
        "The initial revision of this MIB module."
    ::= { hh3cCommon 95 }

-- ==================================================================
--
-- ======================= definition begin =========================
--
-- ==================================================================

Hh3cLpbkdtActionType ::= TEXTUAL-CONVENTION
    STATUS current
    DESCRIPTION
        "Loopback detection action on the port on which a loop is detected.
        When a loop is detected on a port, the device generates a log.  The
        enumeration 'none(1)' means that the device performs no action on the
        port.  The enumeration 'block(2)' means that the device disables MAC
        address learning and blocks traffic on the port.  The enumeration
        'nolearning(3)' means that the device disables MAC address learning on
        the port.  The enumeration 'shutdown(4)' means that the device shuts
        down the port.  The device automatically sets the port to the forwarding
        state after the time interval configured."
    SYNTAX  INTEGER {
            none(1),
            block(2),
            nolearning(3),
            shutdown(4)
    }

hh3cLpbkdtNotifications OBJECT IDENTIFIER ::= { hh3cLpbkdt 1 }
hh3cLpbkdtObjects       OBJECT IDENTIFIER ::= { hh3cLpbkdt 2 }
hh3cLpbkdtTrapPrefix    OBJECT IDENTIFIER ::= { hh3cLpbkdtNotifications 0 }

hh3cLpbkdtTrapLoopbacked NOTIFICATION-TYPE
    OBJECTS { ifIndex, ifDescr }
    STATUS current
    DESCRIPTION
        "Trap message is generated when the interface is looped."
    ::= { hh3cLpbkdtTrapPrefix 1 }

hh3cLpbkdtTrapRecovered NOTIFICATION-TYPE
    OBJECTS { ifIndex, ifDescr }
    STATUS current
    DESCRIPTION
        "Trap message is generated when the loops on the interface
         are eliminated."
    ::= { hh3cLpbkdtTrapPrefix 2 }

hh3cLpbkdtTrapPerVlanLoopbacked NOTIFICATION-TYPE
    OBJECTS { ifIndex, ifDescr, hh3cLpbkdtVlanID }
    STATUS current
    DESCRIPTION
        "Trap message is generated when the interface is looped in the VLAN."
    ::= { hh3cLpbkdtTrapPrefix 3 }

hh3cLpbkdtTrapPerVlanRecovered NOTIFICATION-TYPE
    OBJECTS { ifIndex, ifDescr, hh3cLpbkdtVlanID }
    STATUS current
    DESCRIPTION
        "Trap message is generated when the loop on the interface
         is eliminated in the VLAN."
    ::= { hh3cLpbkdtTrapPrefix 4 }

hh3cLpbkdtTrapVsiLoopbacked NOTIFICATION-TYPE
    OBJECTS { ifIndex, hh3cLpbkdtACName, hh3cLpbkdtVsiName, hh3cLpbkdtSVlanID, hh3cLpbkdtCVlanID }
    STATUS current
    DESCRIPTION
        "This trap message is generated when an interface is looped in a VSI."
    ::= { hh3cLpbkdtTrapPrefix 5 }

hh3cLpbkdtTrapVsiRecovered NOTIFICATION-TYPE
    OBJECTS { ifIndex, hh3cLpbkdtACName, hh3cLpbkdtVsiName }
    STATUS current
    DESCRIPTION
        "This trap message is generated when the loops on a VSI
         are eliminated."
    ::= { hh3cLpbkdtTrapPrefix 6 }

hh3cLpbkdtTrapActionLOG NOTIFICATION-TYPE
    OBJECTS { ifIndex, ifDescr }
    STATUS current
    DESCRIPTION
        "This trap message is generated when the log action is triggered
         by a loop on an interface."
    ::= { hh3cLpbkdtTrapPrefix 7 }

hh3cLpbkdtTrapActionLOGClear NOTIFICATION-TYPE
    OBJECTS { ifIndex, ifDescr }
    STATUS current
    DESCRIPTION
        "This trap message is generated when a loop is removed from an
         interface when the log action is triggered."
    ::= { hh3cLpbkdtTrapPrefix 8 }

hh3cLpbkdtTrapActionBlock NOTIFICATION-TYPE
    OBJECTS { ifIndex, ifDescr }
    STATUS current
    DESCRIPTION
        "This trap message is generated when the block action is triggered
         by a loop on an interface."
    ::= { hh3cLpbkdtTrapPrefix 9 }

hh3cLpbkdtTrapActionBlockClear NOTIFICATION-TYPE
    OBJECTS { ifIndex, ifDescr }
    STATUS current
    DESCRIPTION
        "This trap message is generated when a loop is removed froam an
         interface where the block is triggered."
    ::= { hh3cLpbkdtTrapPrefix 10 }

hh3cLpbkdtTrapActionDown NOTIFICATION-TYPE
    OBJECTS { ifIndex, ifDescr }
    STATUS current
    DESCRIPTION
        "This trap message is generated when the shutdown action triggeded
         by a loop on an interface."
    ::= { hh3cLpbkdtTrapPrefix 11 }

hh3cLpbkdtTrapActionDownClear NOTIFICATION-TYPE
    OBJECTS { ifIndex, ifDescr }
    STATUS current
    DESCRIPTION
        "This trap message is generated when a loop is removed from an interface
         where the shutdown action is triggered."
    ::= { hh3cLpbkdtTrapPrefix 12 }

hh3cLpbkdtTrapVsiBlockFailed NOTIFICATION-TYPE
    OBJECTS { ifIndex, ifDescr, hh3cLpbkdtVsiName, hh3cLpbkdtSrvID }
    STATUS current
    DESCRIPTION
        "This trap is generated when a VSI blocking failure occurs on the interface."
    ::= { hh3cLpbkdtTrapPrefix 13 }

hh3cLpbkdtVlanID OBJECT-TYPE
    SYNTAX      VlanId
    MAX-ACCESS  accessible-for-notify
    STATUS      current
    DESCRIPTION
        "The ID of VLAN."
    ::= { hh3cLpbkdtObjects 1 }

hh3cLpbkdtVlanEnable OBJECT-TYPE
    SYNTAX      OCTET STRING(SIZE(512))
    MAX-ACCESS  read-write
    STATUS      current
    DESCRIPTION
       "Whether the loop detection is enabled globally for the VLANs.  Each
       octet within this value specifies a set of eight VLANs, with the first
       octet specifying VLANs 1 through 8, the second octet specifying VLANs 9
       through 16, etc.  Within each octet, the most significant bit represents
       the highest numbered VLAN, and the least significant bit represents the
       lowest numbered VLAN.  Thus, each VLAN is represented by a single bit
       within the value of this object.  A bit with a value of '1' indicates
       that the loop detection is enabled globally for the VLAN; the loop
       detection is disabled globally for the VLAN if its bit has a value of
       '0'.  The 4095th and 4096th bits must be have a value of '0'."
    ::= { hh3cLpbkdtObjects 2 }

hh3cLpbkdtAction OBJECT-TYPE
    SYNTAX      Hh3cLpbkdtActionType
    MAX-ACCESS  read-write
    STATUS      current
    DESCRIPTION
        "Global loopback detection action on the port on which a loop is
        detected.  The global action applies to all ports.  The per-port action
        takes precedence over the global action."
    DEFVAL      { none }
    ::= { hh3cLpbkdtObjects 3 }

hh3cLpbkdtIntervalTime OBJECT-TYPE
    SYNTAX      Integer32(1..300)
    MAX-ACCESS  read-write
    STATUS      current
    DESCRIPTION
        "The interval at which loop detection frames are transmitted."
    DEFVAL      { 30 }
    ::= { hh3cLpbkdtObjects 4 }

hh3cLpbkdtPortTable OBJECT-TYPE
    SYNTAX      SEQUENCE OF Hh3cLpbkdtPortEntry
    MAX-ACCESS  not-accessible
    STATUS      current
    DESCRIPTION
        "A table containing information about the loop detection configurations
        and status for individual ports."
    ::= { hh3cLpbkdtObjects  5 }

hh3cLpbkdtPortEntry OBJECT-TYPE
    SYNTAX      Hh3cLpbkdtPortEntry
    MAX-ACCESS  not-accessible
    STATUS      current
    DESCRIPTION
        "Detailed information of a specified port."
    INDEX   { hh3cLpbkdtPortIfIndex }
    ::= { hh3cLpbkdtPortTable 1 }

Hh3cLpbkdtPortEntry  ::= SEQUENCE
    {
        hh3cLpbkdtPortIfIndex       InterfaceIndex,
        hh3cLpbkdtPortVlanEnable    OCTET STRING,
        hh3cLpbkdtPortAction        Hh3cLpbkdtActionType,
        hh3cLpbkdtPortLoopbacked    TruthValue
    }

hh3cLpbkdtPortIfIndex OBJECT-TYPE
    SYNTAX      InterfaceIndex
    MAX-ACCESS  not-accessible
    STATUS      current
    DESCRIPTION
        "The ifIndex of the port."
    ::={ hh3cLpbkdtPortEntry 1 }

hh3cLpbkdtPortVlanEnable OBJECT-TYPE
    SYNTAX      OCTET STRING(SIZE(512))
    MAX-ACCESS  read-write
    STATUS      current
    DESCRIPTION
        "Whether the loop detection is enabled on the port for the VLANs.  Each
        octet within this value specifies a set of eight VLANs, with the first
        octet specifying VLANs 1 through 8, the second octet specifying VLANs 9
        through 16, etc.  Within each octet, the most significant bit represents
        the highest numbered VLAN, and the least significant bit represents the
        lowest numbered VLAN.  Thus, each VLAN is represented by a single bit
        within the value of this object.  A bit with a value of '1' indicates
        that the loop detection is enabled on the port for the VLAN; the loop
        detection is disabled on the port for the VLAN if its bit has a value of
        '0'.  The 4095th and 4096th bits must be have a value of '0'."
    ::={ hh3cLpbkdtPortEntry 2 }

hh3cLpbkdtPortAction OBJECT-TYPE
    SYNTAX      Hh3cLpbkdtActionType
    MAX-ACCESS  read-write
    STATUS      current
    DESCRIPTION
        "Loopback detection action on the port on which a loop is detected.  The
        per-port action takes precedence over the global action."
    ::={ hh3cLpbkdtPortEntry 3 }

hh3cLpbkdtPortLoopbacked OBJECT-TYPE
    SYNTAX      TruthValue
    MAX-ACCESS  read-only
    STATUS      current
    DESCRIPTION
        "Whether the port is looped."
    ::={ hh3cLpbkdtPortEntry 4 }

hh3cLpbkdtTrapOjbects OBJECT IDENTIFIER ::= { hh3cLpbkdtNotifications 1 }

hh3cLpbkdtVsiName OBJECT-TYPE
    SYNTAX DisplayString (SIZE (0..255))
    MAX-ACCESS   accessible-for-notify
    STATUS       current
    DESCRIPTION
        "VSI name."
    ::= { hh3cLpbkdtTrapOjbects 1 }

hh3cLpbkdtSVlanID OBJECT-TYPE
    SYNTAX VlanId
    MAX-ACCESS   accessible-for-notify
    STATUS       current
    DESCRIPTION
        "Outer VLAN ID."
    ::= { hh3cLpbkdtTrapOjbects 2 }

hh3cLpbkdtCVlanID OBJECT-TYPE
    SYNTAX VlanId
    MAX-ACCESS   accessible-for-notify
    STATUS       current
    DESCRIPTION
        "Inner VLAN ID."
    ::= { hh3cLpbkdtTrapOjbects 3 }

hh3cLpbkdtACName OBJECT-TYPE
    SYNTAX DisplayString (SIZE (0..255))
    MAX-ACCESS   accessible-for-notify
    STATUS       current
    DESCRIPTION
        "Ethernet service instance name."
    ::= { hh3cLpbkdtTrapOjbects 4 }

hh3cLpbkdtSrvID OBJECT-TYPE
    SYNTAX Integer32(1..4096)
    MAX-ACCESS   accessible-for-notify
    STATUS       current
    DESCRIPTION
        "Service instance ID."
    ::= { hh3cLpbkdtTrapOjbects 5 }

END
