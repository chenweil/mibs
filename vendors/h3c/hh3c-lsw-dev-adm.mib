-- ==================================================================
-- Copyright (c) 2004-2025 New H3C Tech. Co., Ltd.  All rights reserved.
--
-- Description: Device Physical Information MIB
-- Reference:
-- Version: V4.38
-- History:
--    v1.0 (1) Created by Hou Qiang, 2001.5.15
--         (2) Revised by Qi Zhenglin, 2002.01.08 ----r003 revision
--    v1.1 2004-7-12 add some card type define(hh3cLswSlotType 119-138)
--    v1.2 add enum value from 42 to 49 in hh3cLswPortType.
--    v1.3 2004-7-29 add some port type define(hh3cLswPortType 50-58)
--    v1.4 2004-8-11 add some slot type define
--                    (hh3cLswSlotType    type_LSA1FP8U(139))
--                    (hh3cLswSubslotType type_LSA1FP8U(139))
--    v1.5 2004-08-25 change enumeration name
--                     from type_LS81SFCA(120) to type_LS81SRPG0(120),
--                     from type_LS81SFCB(121) to type_LS81SRPG1(121),
--                     from type_LS81SFCC(122) to type_LS81SRPG2(122),
--                     from type_LS81SFCD(123) to type_LS81SRPG3(123).
--                    modify comments for these enumerations as well.
--    v1.6 2004-8-26 add some port types define(h2LswPortType 59-71)
--    v1.7 2004-09-08 add enum value from 140 to 148 in hh3cLswSlotType and hh3cLswSubSlotType by kangyinan
--    v1.8 2004-09-14 add enum value from 149 to 157 in hh3cLswSlotType and hh3cLswSubSlotType by wangyahui
--                    add enum value from 158 to 159 in hh3cLswSlotType and hh3cLswSubSlotType by kangyinan
--                    add enum value from 72 to 93 in hh3cLswPortType by wangyahui
--                    add enum value from 94 to 96 in hh3cLswPortType by kangyinan
--                    add type description for type_SP4, type_UP1, type_XP4 by kangyinan
--    v1.9 2004-10-12 updated by gaolong
--         Change all underscore('_') characters to hyphen characters('-') because underscore character is not allowed in MIB module.
--         The change refers to the value of hh3cLswSlotType, hh3cLswSlotAdminStatus, hh3cLswSubslotType, hh3cLswPortType, hh3cLswSubslotAdminStatus
--         Change MAX-ACCESS clause value of hh3cLswPortLoopbackOperate from write-only to read-write, and
--         update its DESCRIPTION.
--    v2.0 2004-10-19 add enum value from 160 to 162 in hh3cLswSlotType and hh3cLswSubSlotType by kangyinan
--                    add enum value 97 in hh3cLswPortType by kangyinan
--    v2.1  2004-11-23 add enum value from 163 to 166 in hh3cLswSlotType and hh3cLswSubSlotType by zhangchengmei
--    V2.2  2004-12-23 add enum value from 167 to 169 in hh3cLswSlotType and hh3cLswSubSlotType by zhangjianfeng
--    V2.3  2004-12-26 add enum value 170 in hh3cLswSlotType and hh3cLswSubSlotType by wangyahui
--    V2.4  2004-12-23 add enum value from 171 to 172 in hh3cLswSlotType and hh3cLswSubSlotType
--                     add enum value from 98 to 99 hh3cLswPortType by liyue
--    V2.5  2004-12-29 add enum value 173 in hh3cLswSlotType and hh3cLswSubSlotType by zhangjianfeng
--                     add enum value from 100 in hh3cLswPortType by zhangjianfeng
--    V2.6  2005-01-07 add enum value 174 and 175 in hh3cLswSlotType and hh3cLswSubSlotType by wangyahui
--    V2.7  2005-01-31 add enum value 176 in hh3cLswSlotType and hh3cLswSubSlotType by wangyahui
--    V2.8  2005-02-03 define Hh3cLswTypeOfSlot
--                     change the SYNTAX of hh3cLswSlotType and hh3cLswSubSlotType to Hh3cLswTypeOfSlot,add new enum value to Hh3cLswTypeOfSlot
--                     add enum value from 101 to 137 in hh3cLswPortType by zhangchengmei
--                     add enum value 178 in Hh3cLswTypeOfSlot by zhouqiang
--                     add enum value 138 in hh3cLswPortType by zhouqiang
--                     add enum value from 179 to 180 in hh3cLswSubSlotType by wangyahui
--    V2.9  2005-03-22 add enum value from 181 to 187 in Hh3cLswTypeOfSlot by zhangchengmei
--    V3.0  2005-05-10 add enum value from 188 to 216 in Hh3cLswTypeOfSlot by zhangchengmei
--    V3.1  2005-07-18 add enum value from 217 to 219 in Hh3cLswTypeOfSlot by yangliming
--          2005-06-25 add enum value from 139 to 142 in hh3cLswPortType by wangyahui
--    V3.11  2005-07-29 add enum value from 220 to 225 in Hh3cLswTypeOfSlot by wangyahui
--    V3.12  2005-07-21 change the name of subidentifier 183 in Hh3cLswTypeOfSlot by zhangchengmei
--                     add enum value 226 to 227 in Hh3cLswTypeOfSlot by zhangchengmei
--           2005-08-29 add enum value 143 in hh3cLswPortType by qianxiaoyu
--    V3.13  2005-09-13 add enum value 228 to 253 in Hh3cLswTypeOfSlot by zhangchengmei
--           2005-09-13 add enum value 257 to 268 in Hh3cLswTypeOfSlot by zhangchengmei
--    V3.14  2005-11-04 add enum value 144 to 149 in hh3cLswPortType by zhangchengmei
--                      add enum value 150 in hh3cLswPortType by huangyuetao
--                      add enum value 269 to 271 in hh3cLswSlotType by yangxiaopeng
--                      add enum value 272 in Hh3cLswTypeOfSlot by qianxiaoyu
--    V3.15  2005-11-24 add enum value 500 to 501 in hh3cLswSlotType by wangyahui
--    V3.16  2005-11-28 add enum value 300 to 316 in Hh3cLswTypeOfSlot by zhangchengmei
--    V3.17  2005-12-30 add enum value 151 to 170 in hh3cLswPortType by zhangchengmei
--    V3.18  2006-01-04 add enum value 701 in Hh3cLswTypeOfSlot by qianxiaoyu
--    V3.19  2006-02-12 add enum value 702 in Hh3cLswTypeOfSlot by chenxiaohui
--                      add enum value 317 in Hh3cLswTypeOfSlot by zhangchengmei
--    V3.20  2006-02-20 add enum value 703 in Hh3cLswTypeOfSlot by chijuntao
--    V3.21  2006-02-28 add enum value 171 to 174 in hh3cLswPortType by wangshunli
--                      add enum value 318 to 336 in Hh3cLswTypeOfSlot by zhaiyingying
--                      Modify description of hh3cLswSysIpAddr, hh3cLswSlotCpuRatio, hh3cLswSysCpuRatio
--                      and some wrong format of the description by wangyong
--    V3.22  2006-03-14 add enum value 175 in hh3cLswPortType by wangyahui
--                      add enum value 502 to 504 in Hh3cLswTypeOfSlot by wangyahui
--    V3.23  2006-04-03 add enum value 176 in hh3cLswPortType by wangyahui
--    V3.24  2006-04-21 add enum value 337 to 340 in Hh3cLswTypeOfSlot by zhaiyingying
--    V3.25  2006-04-21 add enum value 704 to 705 under Hh3cLswTypeOfSlot by zhangxianguo
--                      add enum value 505 to 506 under Hh3cLswTypeOfSlot by zhangjianfeng
--                      add enum value 341 to 349 under Hh3cLswTypeOfSlot by zhaiyingying
--                      add enum value 177 to 178 under hh3cLswPortType by zhangjianfeng
--                      add enum value 179 to 180 under hh3cLswPortType by zhangxianguo
--    V3.26  2006-07-12 add enum value 507 to 509 in Hh3cLswTypeOfSlot by wangyahui
--                      modify enum name 502 and 503 of Hh3cLswTypeOfSlot by wangyahui
--                      add enum value 350 to 357 under Hh3cLswTypeOfSlot by zhaiyingying
--                      Modify description of enum element(3) in Hh3cLswTypeOfSlot by zhangxianguo
--    V3.27  2006-08-31 add enum value 510 to 514 in Hh3cLswTypeOfSlot by wangyahui
--                      add enum value 800 to 801 in Hh3cLswTypeOfSlot by luoguixing
--    V3.28  2006-10-26 add enum value 358 to 370 under Hh3cLswTypeOfSlot by zhaiyingying
--                      add enum value 183 under hh3cLswPortType by zhaiyingying
--                      add enum value 515 to 526 in Hh3cLswTypeOfSlot by wangyahui
--                      modify enum 505 and 506 of Hh3cLswTypeOfSlot by wangyahui
--                      add enum value 181 to 182 in hh3cLswPortType by wangyahui
--    V3.29  2006-11-02 add enum value 527 to 536 in Hh3cLswTypeOfSlot by wangyahui
--                      modify description of 511 to 513 in Hh3cLswTypeOfSlot by wangyahui
--           2006-11-10 add enum value 371 to 378 under Hh3cLswTypeOfSlot by shuxiongtao
--           2006-11-08 add enum value 184 to 185 under hh3cLswPortType by zhaiyingying
--    V3.30  2007-03-19 add enum value 537 in Hh3cLswTypeOfSlot by wangyahui
--    V3.31  2007-04-25 add enum value 538 to 542 in Hh3cLswTypeOfSlot by wangyahui
--                      add enum value 379 to 380 under Hh3cLswTypeOfSlot by zhaiyingying
--                      add enum value 706 in Hh3cLswTypeOfSlot by zhangzongyi
--    V3.32  2007-05-28 add enum value 707 in Hh3cLswTypeOfSlot by ligaoxu
--                      add enum value 381 to 392 in Hh3cLswTypeOfSlot by shuxiongtao
--                      modify name of enum value 371 and 374 in Hh3cLswTypeOfSlot by shuxiongtao
--                      add enum value 186 in hh3cLswPortType by jinzhaoqiong
--    V3.33  2007-07-09 add enum value 543 to 551 in Hh3cLswTypeOfSlot by Zhangjianfeng
--                      add enum value 552 to 554 in Hh3cLswTypeOfSlot by wangyahui
--    V3.34  2007-07-26 add enum value 708 in Hh3cLswTypeOfSlot by Xiuyihong
--    V3.35  2007-08-27 add enum value 187 to 188 in hh3cLswPortType by ruanhan
--                      add enum value 802 to 804 in Hh3cLswTypeOfSlot by luoguixing
--                      add enum value 393 to 397 under Hh3cLswTypeOfSlot by shuxiongtao
--    V3.36  2007-09-25 add enum value 555 to 559 in Hh3cLswTypeOfSlot by wangyahui
--                      add enum value 805 in Hh3cLswTypeOfSlot by luoguixing
--                      add enum value 398 to 399 in Hh3cLswTypeOfSlot by hexuefei
--    V3.37  2007-10-16 add enum value 189 in hh3cLswPortType by liaoxin
--    V3.38  2007-11-20 add enum value 400 to 407 in Hh3cLswTypeOfSlot by shuxiongtao
--    V3.39  2007-12-27 add enum value 560 to 568 in Hh3cLswTypeOfSlot by wangyahui
--    V3.40  2008-01-30 add enum value 408 in Hh3cLswTypeOfSlot by hexuefei
--                      add enum value 569 to 572 in Hh3cLswTypeOfSlot by wangyahui
--    V3.41  2008-02-20 add enum value 573 to 574 in Hh3cLswTypeOfSlot by zhangjianfeng
--                      modify name and comments of enum value 546 in Hh3cLswTypeOfSlot by zhangjianfeng
--                      add enum value 575 to 576 in Hh3cLswTypeOfSlot by wangyahui
--    V3.42  2008-03-31 add enum value 806 to 808 in Hh3cLswTypeOfSlot by luoguixing
--                      add enum value 709 to 715 under Hh3cLswTypeOfSlot by wangcong
--                      add enum value 191 to 196 under hh3cLswPortType by wangcong
--                      add enum value 409 to 431 in Hh3cLswTypeOfSlot by zhaiyingying
--                      add enum value 432 in Hh3cLswTypeOfSlot by shuxiongtao
--    V3.43  2008-04-29 add enum value 577 to 589 in Hh3cLswTypeOfSlot by wangyahui
--    V3.44  2008-07-28 add enum value 590 to 592 in Hh3cLswTypeOfSlot by wangyahui
--                      add enum value 809 to 810 in Hh3cLswTypeOfSlot by luoguixing
--    V3.45  2008-08-26 modify name of enum value 379 and 399 in Hh3cLswTypeOfSlot by wangwei
--                      modify description of 408 in Hh3cLswTypeOfSlot by wangwei
--                      modify name and description of enum value 804 in Hh3cLswTypeOfSlot by wangwei
--                      add enum value 433 to 434 in Hh3cLswTypeOfSlot by wangwei
--                      add enum value 593 to 595 in Hh3cLswTypeOfSlot by wangyahui
--    V3.46  2008-10-13 add enum value 197 in hh3cLswPortType by ruanhan
--                      add enum value 811 in Hh3cLswTypeOfSlot by luoguixing
--                      add enum value 596 and 601 in Hh3cLswTypeOfSlot by wangyahui
--    V3.47  2008-12-01 add enum value 725 in Hh3cLswTypeOfSlot by ruanhan
--                      add enum value 602 to 619 in Hh3cLswTypeOfSlot by wangyahui
--                      add enum value 435 to 442 in Hh3cLswTypeOfSlot by zhaiyingying
--                      modify name of enum value 546 in Hh3cLswTypeOfSlot by zhangjianfeng
--                      add enum value 443 in Hh3cLswTypeOfSlot by shuxiongtao
--    V3.48  2008-12-25 add enum value 620 to 622 in Hh3cLswTypeOfSlot by wangyahui
--                      add enum value 716 to 718 in Hh3cLswTypeOfSlot by zhangshilin
--                      add enum value 444 to 445 in Hh3cLswTypeOfSlot by wangchang
--    V3.49  2009-01-05 add enum value 446 to 452 in Hh3cLswTypeOfSlot by wangchang
--                      add enum value 719 in Hh3cLswTypeOfSlot by zhangshilin
--                      add enum value 623 to 633 in Hh3cLswTypeOfSlot by wangyahui
--    V3.50  2009-03-19 add enum value 453 to 464 in Hh3cLswTypeOfSlot by huyinxing
--    V3.51  2009-07-02 add enum value 634 to 637 in Hh3cLswTypeOfSlot by wangyahui
--                      add enum value 465 to 468 in Hh3cLswTypeOfSlot by zhaiyingying
--                      add enum value 469 to 472 in Hh3cLswTypeOfSlot by huyinxing
--                      add enum value 198 in hh3cLswPortType by huyinxing
--                      add enum value 199 in hh3cLswPortType by zhangjianfeng
--    V3.52  2009-08-28 add enum value 638 to 640 in Hh3cLswTypeOfSlot by wangyahui
--    V3.53  2009-11-09 add enum value 726 in Hh3cLswTypeOfSlot by ruanhan
--                      add enum value 641 in Hh3cLswTypeOfSlot by wangyahui
--                      add enum value 473 to 477 in Hh3cLswTypeOfSlot by yudongyang
--                      add enum value 478 to 485 in Hh3cLswTypeOfSlot by heweibin
--    V3.54  2009-12-31 add enum value 200 to 201 in hh3cLswPortType by zhanghaiyang
--                      add enum value 642 to 651 in Hh3cLswTypeOfSlot by wangyahui
--                      add enum value 486 in Hh3cLswTypeOfSlot by yudongyang
--                      add enum value 727 to 728 in Hh3cLswTypeOfSlot by xiaobing
--                      add enum value 652 to 659 in Hh3cLswTypeOfSlot by wangyahui
--                      add enum value 487 to 488 in Hh3cLswTypeOfSlot by huyinxing
--                      add enum value 660 to 662 in Hh3cLswTypeOfSlot by wangyahui
--                      add enum value 202 to 203 in hh3cLswPortType by yangdonghong
--    V3.55  2010-03-03 Added hh3cLswSysPhyMemory, hh3cLswSysMemory,
--                      hh3cLswSysMemoryUsed, hh3cLswSysMemoryRatio by songhao
--                      add enum value 812 in Hh3cLswTypeOfSlot by mashuhang
--                      add enum value 489 to 497 in Hh3cLswTypeOfSlot by liubuxiang
--                      add enum value 498 to 499 in Hh3cLswTypeOfSlot by shikejun
--                      add enum value 900 in Hh3cLswTypeOfSlot by yangqiulin
--                      add enum value 901 to 902 in Hh3cLswTypeOfSlot by huyinxing
--    V3.56  2010-08-29 add enum value 903 to 904 in Hh3cLswTypeOfSlot by huyinxing
--                      add enum value 905 to 907 in Hh3cLswTypeOfSlot by shikejun
--                      add enum value 663 to 685 in Hh3cLswTypeOfSlot by wangyahui
--                      add enum value 813 in Hh3cLswTypeOfSlot by mashuhang
--                      add enum value 729 in Hh3cLswTypeOfSlot by zhangshilin
--                      add enum value 908 to 913 in Hh3cLswTypeOfSlot by yangbin
--                      add enum value 914 to 918 in Hh3cLswTypeOfSlot by huyinxing
--                      add enum value 919 to 927 in Hh3cLswTypeOfSlot by langgaoyi
--                      add hh3cLswFabricTable by songhao
--    V3.57  2011-01-31 add enum value 686 to 691 in Hh3cLswTypeOfSlot by wangyahui
--                      add enum value 928 to 929 in Hh3cLswTypeOfSlot by langgaoyi
--                      add hh3cLswSysTemperature, hh3cLswSlotPhyMemory,
--                      hh3cLswSlotMemory, hh3cLswSlotMemoryUsed,
--                      hh3cLswSlotMemoryRatio and hh3cLswSlotTemperature by songhao
--    V3.58  2011-04-23 Add enum value 930 in Hh3cLswTypeOfSlot by liuhui
--                      Add enum value 814 to 815 in Hh3cLswTypeOfSlot by mashuhang
--                      Add enum value 692 to 694 in Hh3cLswTypeOfSlot by wangyahui
--                      Add enum value 204 in hh3cLswPortType by yangliming
--    V3.59  2011-06-30 Add enum value 695, 1201 to 1211 in Hh3cLswTypeOfSlot by wangyahui
--                      Add enum value 205 to 207 in hh3cLswPortType by gaoruichang
--    V3.60  2011-08-31 Add enum value 696 to 697 in Hh3cLswTypeOfSlot by langgaoyi
--                      Add enum value 208 in hh3cLswPortType by wangshunli
--                      Add enum value 931 to 933 in Hh3cLswTypeOfSlot by langgaoyi
--                      Add enum value 934 in Hh3cLswTypeOfSlot by zhaohonghai
--    V3.61  2012-04-20 Add enum value 935 to 938, 942 in Hh3cLswTypeOfSlot by wangjiangnan
--                      Add enum value 1212 to 1218 in Hh3cLswTypeOfSlot by wangyahui
--                      Add enum value 939 to 941 in Hh3cLswTypeOfSlot by herui
--                      Modify name of enum value 205 to 207 in hh3cLswPortType by xvman
--                      Add enum value 943 to 945 in Hh3cLswTypeOfSlot by langgaoyi
--                      Add enum value 209, 211 in hh3cLswPortType by wangyahui
--                      Add enum value 730 to 731 in Hh3cLswTypeOfSlot by panxiyuan
--                      Add enum value 210 in hh3cLswPortType by panxiyuan
--                      Add enum value 946 to 948 in Hh3cLswTypeOfSlot by zhangheng
--                      Add enum value 949 to 956 in Hh3cLswTypeOfSlot by zhengjiang
--                      Add enum value 957 in Hh3cLswTypeOfSlot by zhaohonghai
--                      Add enum value 212 in hh3cLswPortType by wangyahui
--                      Add enum value 732 in Hh3cLswTypeOfSlot by houchengshuai
--                      Add enum value 1219 to 1230 in Hh3cLswTypeOfSlot by wangyahui
--    V3.62  2013-01-07 Add enum value 733 in Hh3cLswTypeOfSlot by shixuemei
--                      Add enum value 958 to 959 in Hh3cLswTypeOfSlot by zhaohonghai
--                      Add enum value 960 to 965, 996 in Hh3cLswTypeOfSlot by zhangheng
--                      Add enum value 966 to 988 in Hh3cLswTypeOfSlot by yebiaoxiang
--                      Add enum value 989 to 995 in Hh3cLswTypeOfSlot by zhaohonghai
--                      Add enum value 1231 to 1255 in Hh3cLswTypeOfSlot by wangyahui
--                      Add enum value 1400 to 1410 in Hh3cLswTypeOfSlot by qizhenglin
--                      Add enum value 213 to 219 under hh3cLswPortType by yebiaoxiang
--                      Modify the name of subidentifier 673, 1214, 1215 in Hh3cLswTypeOfSlot by by wangyahui
--                      Added hh3cLswSlotPktBufFree, hh3cLswSlotPktBufInit,
--                      hh3cLswSlotPktBufMin, hh3cLswSlotPktBufMiss by jixugang
--    V3.63  2013-04-26 Add enum value 1256 to 1269 in Hh3cLswTypeOfSlot by wangyahui
--                      Add enum value 220 to 222 under hh3cLswPortType by jiangyongjiang
--                      Modify name of enum value 975 to 982 in hh3cLswPortType by lihaijun
--                      Add enum value 997 to 1015 in Hh3cLswTypeOfSlot by chenke
--                      Add enum value 1016 to 1018 in Hh3cLswTypeOfSlot by jiangyongjiang
--                      Add enum value 1270 to 1273 in Hh3cLswTypeOfSlot by sunzhenxing
--                      Add hh3cLswSlotRunTime by qianhaiyun
--                      Add hh3cLswNetworkHealthMonitor for reserving by wangcong
--    V3.64  2013-10-10 Add enum value 1274 to 1279, 1293 to 1296 in Hh3cLswTypeOfSlot by lihaijun
--                      Add enum value 1019 to 1024 in Hh3cLswTypeOfSlot by zhaohonghai
--                      Add enum value 1280 to 1287, 1298 to 1306 in Hh3cLswTypeOfSlot by sunzhenxing
--                      Add enum value 1025, 1028, 1029, 1050 in Hh3cLswTypeOfSlot by jiangyongjiang
--                      Add enum value 1026 to 1027, 1030 to 1049 in Hh3cLswTypeOfSlot by chenke
--                      Add enum value 1288 to 1292, 1297 in Hh3cLswTypeOfSlot by wujili
--                      Modify name of enum value 1234 to 1236 in Hh3cLswTypeOfSlot by lihaijun
--                      Add enum value 223 to 224 under hh3cLswPortType by jiangyongjiang
--                      Add hh3cLswSysMemRev, hh3cLswSysPhyMemRev, hh3cLswSysMemUsedRev and
--                      hh3cLswSlotMemRev, hh3cLswSlotPhyMemRev, hh3cLswSlotMemUsedRev by fangliwen
--    V3.65  2014-01-26 Add enum value 734 to 739 in Hh3cLswTypeOfSlot by panxiyuan
--                      Modify name of enum value 1032 to 1041 in Hh3cLswTypeOfSlot by chenke
--                      Add enum value 1051 to 1055 in Hh3cLswTypeOfSlot by zhaohonghai
--                      Add enum value 1056 to 1058 in Hh3cLswTypeOfSlot by chenke
--                      Add enum value 1307 to 1313 in Hh3cLswTypeOfSlot by wujili
--                      Add enum value 1314 to 1316 in Hh3cLswTypeOfSlot by lihaijun
--                      Add enum value 1317 to 1319 in Hh3cLswTypeOfSlot by sunzhenxing
--                      Add enum value 1320 to 1326 in Hh3cLswTypeOfSlot by jiangyongjiang
--    V3.66  2013-12-21 Add hh3cLswSlotModelDesc and hh3cLswExtendModelTable by zushuzhi
--           2014-04-25 Add enum value 1059 to 1069 in Hh3cLswTypeOfSlot by youhua
--                      Add enum value 1070 to 1102 in Hh3cLswTypeOfSlot by chenke
--                      Add enum value 1103 to 1107 in Hh3cLswTypeOfSlot by lihaijun
--                      Add enum value 1108 in Hh3cLswTypeOfSlot by zhaohonghai
--                      Add enum value 1327 to 1328 in Hh3cLswTypeOfSlot by sunzhenxing
--                      Add enum value 1329 to 1331 in Hh3cLswTypeOfSlot by lihaijun
--                      Add enum value 1332 to 1371 in Hh3cLswTypeOfSlot by jiangyongjiang
--                      Add enum value 1372 to 1373 in Hh3cLswTypeOfSlot by sunzhenxing
--                      Modify enum value 1400, remove 1401 to 1410 in Hh3cLswTypeOfSlot by qizhenglin
--                      Modify name of enum value 733 in Hh3cLswTypeOfSlot by chenke
--                      Add enum value 225 to 232 under hh3cLswPortType by pantao
--    V3.67  2014-05-10 Add hh3cLswCpuTable by fangliwen
--           2014-09-18 Add enum value 1109 to 1117 in Hh3cLswTypeOfSlot by chenke
--                      Add enum value 1118 to 1119, 1375 to 1376 in Hh3cLswTypeOfSlot by lihaijun
--                      Add enum value 1374, 1382 to 1385 in Hh3cLswTypeOfSlot by jiangyongjiang
--                      Add enum value 1377 to 1381, 1386 to 1389 in Hh3cLswTypeOfSlot by sunzhenxing
--                      Modify description of 1010 in Hh3cLswTypeOfSlot by chenke
--                      Modify name of enum value 1320 to 1325, 1332 to 1371 in Hh3cLswTypeOfSlot by jiangyongjiang
--    V3.68  2015-04-18 Add enum value 748 in Hh3cLswTypeOfSlot by wangshunli
--                      Add enum value 1120 to 1125, 1127 to 1128, 1390 to 1397,
--                                     1647 to 1649, 1667 to 1673 in Hh3cLswTypeOfSlot by lihaijun
--                      Add enum value 1126 in Hh3cLswTypeOfSlot by chenke
--                      Add enum value 1129 to 1144 in Hh3cLswTypeOfSlot by youhua
--                      Add enum value 1398, 1399, 1600 to 1605, 1623 to 1646
--                                     1650 to 1652, 1660 to 1666, 1674 to 1685
--                                     in Hh3cLswTypeOfSlot by jiangyongjiang
--                      Add enum value 1606 to 1622 in Hh3cLswTypeOfSlot by sunzhenxing
--                      Add enum value 1653 to 1659 in Hh3cLswTypeOfSlot by zhaiwanqing
--                      Add enum value 233 to 237, 239 to 253 under hh3cLswPortType by pantao
--                      Add enum value 238 under hh3cLswPortType by chenke
--                      Modify name of enum value 1315 and 1316 in Hh3cLswTypeOfSlot by lihaijun
--    V3.69  2016-04-02 Add enum value 749 in Hh3cLswTypeOfSlot by wangshunli
--                      Add enum value 750 in Hh3cLswTypeOfSlot by yangjianlin
--                      Add enum value 751 to 752 under Hh3cLswTypeOfSlot by mengfanhua
--                      Add enum value 753 to 756 under Hh3cLswTypeOfSlot by songkeke
--                      Add enum value 1145, 1149 in Hh3cLswTypeOfSlot by youhua
--                      Add enum value 1146 to 1148, 1150 to 1154 in Hh3cLswTypeOfSlot by chenke
--                      Add enum value 1686 to 1694, 1710 to 1722, 1742 to 1760, 1767 to 1784, 1789 to 1793
--                                     in Hh3cLswTypeOfSlot by jiangyongjiang
--                      Add enum value 1695 to 1696 in Hh3cLswTypeOfSlot by zhaiwanqing
--                      Add enum value 1697 to 1709, 1723 to 1741, 1761 to 1766, 1785 to 1788, 1794 to 1805
--                                     in Hh3cLswTypeOfSlot by lihaijun
--                      Modify name of enum value 1128 in Hh3cLswTypeOfSlot by lihaijun
--                      Modify description of enum value 1673 in Hh3cLswTypeOfSlot by lihaijun
--                      Add enum value 254 to 262, 264 to 265 under hh3cLswPortType by guolei
--                      Add enum value 263 under hh3cLswPortType by zhanghuimin
--    V3.70  2018-04-17 Add enum value 266 in hh3cLswPortType by guolei
--                      Add enum value 1806 to 1829 in Hh3cLswTypeOfSlot by jiangyongjiang
--                      Add enum value 1830 to 1841 in Hh3cLswTypeOfSlot by lihaijun
--                      Add enum value 757 to 758 in Hh3cLswTypeOfSlot by wangshunli
--                      Add enum value 1842 in Hh3cLswTypeOfSlot by zhaoshihong
--                      Add enum value 1843 to 1846 in Hh3cLswTypeOfSlot by jiangyongjiang
--                      Add enum value 759 in Hh3cLswTypeOfSlot by mengfanhua
--                      Add enum value 1847 in Hh3cLswTypeOfSlot by jiangyongjiang
--                      Add enum value 1848 to 1849 in Hh3cLswTypeOfSlot by lihaijun
--                      Add enum value 1850 to 1852 in Hh3cLswTypeOfSlot by jiangyongjiang
--                      Add enum value 1853 to 1857 in Hh3cLswTypeOfSlot by lihiajun
--                      Add enum value 1863 to 1893 in Hh3cLswTypeOfSlot by jiangyongjiang
--                      Add enum value 1894 to 1895 in Hh3cLswTypeOfSlot by lihaijun
--                      Add enum value 1896 in Hh3cLswTypeOfSlot by jiangyongjiang
--                      Add enum value 267 in hh3cLswPortType by guolei
--                      Add enum value 1897 to 1904 in Hh3cLswTypeOfSlot by jiangyongjiang
--                      Add enum value 1905 in Hh3cLswTypeOfSlot by liuyanpeng
--                      Add enum value 1906 to 1907 in Hh3cLswTypeOfSlot by jiangyongjiang
--                      Add enum value 1908 in Hh3cLswTypeOfSlot by liuyanpeng
--                      Add enum value 1171 to 1181 in Hh3cLswTypeOfSlot by chenke
--                      Add enum value 1909 to 1910 in Hh3cLswTypeOfSlot by lihaijun
--                      Add enum value 1911 to 1935 in Hh3cLswTypeOfSlot by jiangyongjiang
--                      Add enum value 1936 to 1938 in Hh3cLswTypeOfSlot by zhangkun
--                      Add enum value 1939 to 1941 in Hh3cLswTypeOfSlot by jiangyongjiang
--                      Add enum value 1182 in Hh3cLswTypeOfSlot by youhua
--                      Add enum value 1942 Hh3cLswTypeOfSlot by lihaijun
--                      Add enum value 1943 to 1953  Hh3cLswTypeOfSlot by jiangyongjiang
--                      Add enum value 1183 to 1196 in Hh3cLswTypeOfSlot by chenke
--                      Add enum value 763 to 764  in Hh3cLswTypeOfSlot by sunfang
--                      Add enum value 1954 to 1957  Hh3cLswTypeOfSlot by lihaijun
--                      Add enum value 1958 to 1972  Hh3cLswTypeOfSlot by jiangyongjiang
--                      Add enum value 1973 to 1979  Hh3cLswTypeOfSlot by lihaijun
--                      Add enum value 274 to 279  Hh3cLswTypeOfSlot by guolei
--                      Add enum value 765  in Hh3cLswTypeOfSlot by mengfanhua
--                      Add enum value 1980 to 1981, 1986 to 1997 Hh3cLswTypeOfSlot by jiangyongjiang
--                      Add enum value 740 to 747  Hh3cLswTypeOfSlot by xvman
--                      Add enum value 2004 to 2005 in Hh3cLswTypeOfSlot by lihaijun
--                      Add enum value 2006 to 2008 in Hh3cLswTypeOfSlot by jiangyongjiang
--                      Add enum value 2009 to 2015 in Hh3cLswTypeOfSlot by lihaijun
--                      Add enum value 1401 to 1424 in Hh3cLswTypeOfSlot by chenke
--                      Add enum value 766 to 768 in Hh3cLswTypeOfSlot by wangshunli
--                      Add enum value 769 to 770 in Hh3cLswTypeOfSlot by yangjianlin
--                      Add enum value 2016 to 2017 in Hh3cLswTypeOfSlot by jiangyongjiang
--                      Add enum value 2018 to 2021 in Hh3cLswTypeOfSlot by llihaijun
--                      Add enum value 2022 to 2033 in Hh3cLswTypeOfSlot by jianyongjiang
--                      Add enum value 281 to 283 in hh3cLswPortType by wangshunli
--                      Add enum value 284 to 285 in hh3cLswPortType by guolei
--                      Add enum value 771 to 775 in Hh3cLswTypeOfSlot by wangshunli
--           2015-07-14 Add hh3cLswSlotPktBufThreshold by zhangji
--           2016-03-26 Add hh3cLswFrameClassType, hh3cLswFrameDisplayId and
--                      hh3cLswFrameName by zushuzhi
--           2017-01-12 Add enum Value 11 to 32 in hh3cLswCpuEntry by yanfang
--           2017-02-10 Add hh3cLswPowerTable  hh3cLswTransceiverTable hh3cLswFanTable by xuzhihui
--                      Add hh3cLswFrameSerialNumber hh3cLswSlotSerialNumber hh3cLswSubslotSerialNumber by xuzhihui
--           2017-05-13 Add hh3cLswCpuGrouptable by yuhaiyan
--           2017-07-25 Add hh3cLswCoreTable by wangweihui
--    V3.71  2018-04-17 Modify name of enum value 1822 adn 1825 in Hh3cLswTypeOfSlot by jiangyongjiang
--           2018-05-09 Add enum value 2034 to 2047 in Hh3cLswTypeOfSlot by jiangyongjiang
--           2018-06-28 Add enum value 2048 to 2049 in Hh3cLswTypeOfSlot by lihaijun
--           2018-09-04 Add enum value 2050 to 2060 in Hh3cLswTypeOfSlot by jiangyongjiang
--           2018-03-18 Add enum value 1425 to 1456 in Hh3cLswTypeOfSlot by chenke
--           2018-11-05 Add enum value 286 in hh3cLswPortType by guolei
--           2019-01-03 Add enum value 288 in hh3cLswPortType by qinjuan
--    V3.72  2019-01-22 Add hh3cLswCoreMinorThreshold hh3cLswCoreRecoveryThreshold by wangweihui
--           2019-04-10 Add enum value 2077 in Hh3cLswTypeOfSlot by jiangyongjiang
--           2019-04-17 Add enum value 2082 to 2108 in Hh3cLswTypeOfSlot by jiangyongjiang
--           2019-04-19 Modify name of enum value 2091 in Hh3cLswTypeOfSlot by jiangyongjiang
--           2019-04-26 Add enum value 2109 to 2111 in Hh3cLswTypeOfSlot by maoyun
--           2019-05-09 Add enum value 2113 to 2116 in Hh3cLswTypeOfSlot by lihaijun
--           2019-05-17 Add enum value 2130 in Hh3cLswTypeOfSlot by maoyun
--           2019-05-17 Add enum value 2119 to 2129 in Hh3cLswTypeOfSlot by jiangyongjiang
--           2019-05-29 Add enum value 2142 to 2146 in Hh3cLswTypeOfSlot by jiangyongjiang
--           2019-05-29 Add enum value 2147 to 2148 in Hh3cLswTypeOfSlot by maoyun
--           2019-06-17 Add enum value 2149 to 2155 in Hh3cLswTypeOfSlot by chenke
--           2019-06-17 Add enum value 2156 to 2169 in Hh3cLswTypeOfSlot by lihaijun
--           2019-06-20 Add enum value 2170 to 2173 in Hh3cLswTypeOfSlot by jiangyongjiang
--           2019-06-20 Add enum value 2174 to 2175 in Hh3cLswTypeOfSlot by lihaijun
--    V3.73  2019-09-18 Add enum value 293 to 294 in hh3cLswPortType by wangzilong
--           2019-10-12 Add enum value 2198 to 2208 in Hh3cLswTypeOfSlot by jiangyongjiang
--           2019-10-16 Add enum value 2209 in Hh3cLswTypeOfSlot by lihaijun
--    V3.74  2019-11-21 Modify oid of hh3cLswFrameSerialNumber and hh3cLswFrameClassType by tianruichuan
--           2019-11-27 Add enum value 2213 to 2217 in Hh3cLswTypeOfSlot by lihaijun
--                      Add enum value 2218 to 2222, 2225 to 2226 in Hh3cLswTypeOfSlot by jiangyongjiang
--                      Add enum value 2223 to 2224 in Hh3cLswTypeOfSlot by maoyun
--           2019-12-26 Add enum value 2227 in Hh3cLswTypeOfSlot by chenke
--    V3.75  2020-01-07 Add enum value 2228 to 2229 in Hh3cLswTypeOfSlot by chenke
--           2020-01-21 Add enum value 2230 in Hh3cLswTypeOfSlot by jiangyongjiang
--           2020-02-03 add enum value 816 to 819 in Hh3cLswTypeOfSlot by luoguixing
--    V3.76  2020-02-12 Add enum value 295 to 296 in hh3cLswPortType by wangzilong
--           2020-02-25 Add enum value 2231 to 2232 in Hh3cLswTypeOfSlot by chenke
--           2020-02-26 Add enum value 2233 to 2236 in Hh3cLswTypeOfSlot by lihaijun
--           2020-03-05 Add enum value 2237 in Hh3cLswTypeOfSlot by zhanglili
--    V3.77  2020-03-10 Add enum value 2238 to 2239 in Hh3cLswTypeOfSlot by zhanglili
--           2020-03-20 Add enum value 297 in hh3cLswPortType by wangzilong
--           2020-03-31 Add enum value 2240 to 2256  in Hh3cLswTypeOfSlot by jiangyongjiang
--           2020-03-31 Add enum value 2257 in Hh3cLswTypeOfSlot by zhanglili
--    V3.78  2020-04-14 Add enum value 2258 in Hh3cLswTypeOfSlot by jiangyongjiang
--           2020-05-06 Add enum value 2259 in Hh3cLswTypeOfSlot by zhanglili
--           2020-05-07 Add enum value 2260 in Hh3cLswTypeOfSlot by lihaijun
--           2020-05-07 Moidfy enum value 2233 to 2236 in Hh3cLswTypeOfSlot by lihaijun
--    V3.79  2020-06-01 Moidfy enum value 2231 in Hh3cLswTypeOfSlot by zhanglili
--           2020-06-01 Add enum value 2261 in Hh3cLswTypeOfSlot by zhanglili
--           2020-06-04 Add enum value 2262 to 2274 in Hh3cLswTypeOfSlot by jiangyongjiang
--           2020-06-04 Add enum value 2275 in Hh3cLswTypeOfSlot by zhanglili
--    V3.80  2020-07-01 Add enum value 2276 in Hh3cLswTypeOfSlot by zhanglili
--           2020-07-06 Add enum value 820 in Hh3cLswTypeOfSlot by luoguixing
--    V3.81  2020-07-30 Add enum value 2277 to 2291 in Hh3cLswTypeOfSlot by jingyongjiang
--           2020-07-31 Add enum value 2292 in Hh3cLswTypeOfSlot by qichenglu
--           2020-07-31 Moidfy enum value 2186 in Hh3cLswTypeOfSlot by qichenglu
--           2020-08-04 Add enum value 2293 to 2295 in Hh3cLswTypeOfSlot by jingyongjiang
--    V3.82  2020-08-17 Add enum value 788 to 790 in Hh3cLswTypeOfSlot by zhouqin
--           2020-08-24 Add enum value 2296 to 2301 in Hh3cLswTypeOfSlot by jingyongjiang
--           2020-08-26 Add enum value 2302 to 2307 in Hh3cLswTypeOfSlot by zhanglili
--    V3.83  2020-09-10 Moidfy enum value 2303 in Hh3cLswTypeOfSlot by zhanglili
--           2020-09-16 Add enum value 298 to 299 in hh3cLswPortType by wangzilong
--           2020-08-26 Add enum value 2308 to 2326 in Hh3cLswTypeOfSlot by zhanglili
--    V3.84  2020-10-20 Add enum value 2327 to 2355 in Hh3cLswTypeOfSlot by jiangyongjiang
--    V3.85  2020-11-12 Add enum value 2356 to 2359 in Hh3cLswTypeOfSlot by liuhaijun
--           2020-12-03 Add enum value 2360 to 2361 in Hh3cLswTypeOfSlot by jiangyongjiang
--           2020-12-08 Add enum value 821 in Hh3cLswTypeOfSlot by luoguixing
--    V3.86  2020-12-10 Add enum value 2362 in Hh3cLswTypeOfSlot by jiangyongjiang
--           2020-12-25 Add enum value 300 to 304 in hh3cLswPortType by wangzilong
--           2021-01-08 Add enum value 781 in Hh3cLswTypeOfSlot by zhouqin
--           2020-12-10 Add enum value 2363 in Hh3cLswTypeOfSlot by lihaijun
--    V3.87  2021-03-08 Add enum value 2364 to 2377 in Hh3cLswTypeOfSlot by jiangyongjiang
--    V3.88  2021-03-22 Add enum value 305  in hh3cLswPortType by wangzilong
--           2021-03-25 Add enum value 2378 to 2380 in Hh3cLswTypeOfSlot by jiangyongjiang
--    V3.89  2021-04-29 Add enum value 2381 to 2393 in Hh3cLswTypeOfSlot by jiangyongjiang
--           2021-05-10 Add enum value 2394 to 2397 in Hh3cLswTypeOfSlot by zhanglili
--    V3.90  2021-05-15 Add enum value 306 to 311 in Hh3cLswTypeOfSlot by wangzilong
--           2021-05-24 Add enum value 2398 to 2406 in Hh3cLswTypeOfSlot by lihaijun
--           2021-05-26 Add enum value 2407 to 2408 in Hh3cLswTypeOfSlot by jiangyongjiang
--           2021-05-27 Modify enum value 2356 to 2358 and Del enum value 2403 to 2406 in Hh3cLswTypeOfSlot by lihaijun
--           2021-06-03 Add enum value 2410 to 2428 in Hh3cLswTypeOfSlot by jiangyongjiang
--    V3.91  2021-07-07 Add enum value 2429 to 2436 in Hh3cLswTypeOfSlot by zhanglili
--           2021-07-08 Add enum value 2437 to 2472 in Hh3cLswTypeOfSlot by jiangyongjiang
--    V3.92  2021-08-03 Add enum value 312 to 314 in Hh3cLswTypeOfSlot by wangzilong
--           2021-07-07 Add hh3cLswSysSerialNumber by caohao
--    V3.93  2021-09-09 Add enum value 2473 in Hh3cLswTypeOfSlot by zhanglili
--           2021-09-14 Add enum value 2474 to 2476 in Hh3cLswTypeOfSlot by jiangyongjiang
--    V3.94  2021-10-11 Add enum value 2477 to 2479 in Hh3cLswTypeOfSlot by zhanglili
--    V3.95  2021-10-19 Add enum value 2480 in Hh3cLswTypeOfSlot by sunyuyan
--           2021-11-04 Add enum value 2481 to 2484 in Hh3cLswTypeOfSlot by liuhaijun
--           2021-11-04 Add enum value 315 to 317 in Hh3cLswTypeOfSlot by wangzilong
--           2021-11-05 Add enum value 2485 to 2490 in Hh3cLswTypeOfSlot by zhanglili
--    V3.96  2021-12-03 Add enum value 2491 to 2496,2500 to 2503 in Hh3cLswTypeOfSlot by jiangyongjiang
--           2021-12-06 Add enum value 2504 to 2508 in Hh3cLswTypeOfSlot by zhuyuchao
--           2021-12-08 Add enum value 2509 to 2522 in Hh3cLswTypeOfSlot by zhanglili
--    V3.97  2021-12-28 Add enum value 2533 to 2530 in Hh3cLswTypeOfSlot by jiangyongjiang
--           2021-12-28 Modify enum value 2458 to 2500 in Hh3cLswTypeOfSlot by jiangyongjiang
--           2022-01-06 Add enum value 2531 to 2533 in Hh3cLswTypeOfSlot by zhanglili
--           2022-01-12 Add enum value 2534 to 2541 in Hh3cLswTypeOfSlot by jiangyongjiang
--           2022-01-12 Add enum value 2542 to 2544 in Hh3cLswTypeOfSlot by licong
--    V3.98  2022-01-21 Add enum value 2545 in Hh3cLswTypeOfSlot by jiangyongjiang
--           2022-02-11 Add enum value 2546 to 2561 in Hh3cLswTypeOfSlot by jiangyongjiang
--    V3.99  2022-02-09 Add hh3cLswOutputPowerTable by liwenxiao
--           2022-03-11 Add enum value 2562 to 2568 in Hh3cLswTypeOfSlot by niujiahao
--    V4.00  2022-03-18 Add enum value 782 in Hh3cLswTypeOfSlot by qiuxianglong
--           2022-03-24 Add enum value 2569 in Hh3cLswTypeOfSlot by niujiahao
--           2022-04-11 Add enum value 2570 to 2576 in Hh3cLswTypeOfSlot by jiangyongjiang
--    V4.01  2022-04-28 Add enum value 2582 in Hh3cLswTypeOfSlot by jiangyongjiang
--           2022-05-07 Add enum value 2583 to 2615  in Hh3cLswTypeOfSlot by jiangyongjiang
--           2022-05-07 Add enum value 2616 to 2617  in Hh3cLswTypeOfSlot by niujiahao
--           2022-05-10 Add enum value 2618 to 2635  in Hh3cLswTypeOfSlot by jiangyongjiang
--           2022-03-18 Added hh3cLswFrameTotalPower and hh3cLswSysTotalPower by fangliwen
--    V4.02  2022-06-14 Modify enum value 2586,2590,2606 in Hh3cLswTypeOfSlot by jiangyongjiang
--           2022-06-20 Add enum value 315 to 317 in Hh3cLswTypeOfSlot by wangzilong
--    V4.03  2022-07-04 Add enum value 323 in Hh3cLswTypeOfSlot by wangzilong
--           2022-07-05 Add enum value 2646 to 2651 in Hh3cLswTypeOfSlot by niujihao
--    V4.04  2022-08-09 Add enum value 2652 to 2660 in Hh3cLswTypeOfSlot by jiangyongjiang
--    V4.05  2022-08-23 Add enum value 2661 to 2663 in Hh3cLswTypeOfSlot by niujiahao
--           2022-09-06 Add enum value 2664 to 2683 in Hh3cLswTypeOfSlot by jiangyongjiang
--           2022-09-08 Add enum value 2684 to 2687 in Hh3cLswTypeOfSlot by niujiahao
--    V4.06  2022-10-13 Add enum value 2691 to 2692 in Hh3cLswTypeOfSlot by jiangyongjiang
--           2022-10-14 Add enum value 324 to 333 in Hh3cLswTypeOfSlot by wangzilong
--    V4.07  2022-10-28 Add enum value 2693 to 2699 in Hh3cLswTypeOfSlot by jiangyongjiang
--           2022-11-02 Add enum value 334 in Hh3cLswTypeOfSlot by wangzilong
--           2022-11-09 Add enum value 2700 to 2701 in Hh3cLswTypeOfSlot by niujiahao
--           2022-11-14 Add enum value 2702 to 2711 in Hh3cLswTypeOfSlot by jiangyongjiang
--    V4.08  2022-12-05 Add enum value 2712 in Hh3cLswTypeOfSlot by yangmingjue
--           2022-12-05 Add enum value 2713 to 2730 in Hh3cLswTypeOfSlot by jiangyongjiang
--           2022-11-04 Add hh3cLswFrameNominalPower hh3cLswFramePowerRedundancyType hh3cLswSlotPower by fangliwen
--    V4.09  2023-01-06 Modify enum 2715,2716,2720 to 2722 in Hh3cLswTypeOfSlot by jiangyongjiang
--           2023-01-11 Add enum value 2732 to 2733 in Hh3cLswTypeOfSlot by lihaijun
--           2023-01-12 Add enum value 2734 to 2735 in Hh3cLswTypeOfSlot by jiangyongjiang
--           2023-01-18 Add enum value 2736 in Hh3cLswTypeOfSlot by niujiahao
--           2023-01-31 Add enum value 2737 in Hh3cLswTypeOfSlot by qichenglu
--    V4.10  2023-02-17 Add hh3cSlotCurrentVoltage and hh3cSlotCurrent by hezheng
--           2023-02-22 Add enum value 2747 to 2750 in Hh3cLswTypeOfSlot by jiangyongjiang
--    V4.11  2023-03-24 Add enum value 2751 in Hh3cLswTypeOfSlot by niujiahao
--           2023-04-06 Add enum value 335 in Hh3cLswTypeOfSlot by wangzilong
--           2023-04-14 Add enum value 2756 to 2757 in Hh3cLswTypeOfSlot by jiangyongjiang
--           2023-03-01 Add hh3cSysProductName hh3cSysProductVersion hh3cSysPatchPlatVersion by shenhongxia
--    V4.12  2023-05-16 Add enum value 2758 to 2771 in Hh3cLswTypeOfSlot by jiangyongjiang
--           2023-05-22 Add enum value 336 to 348 in Hh3cLswTypeOfSlot by wangzilong
--    V4.13  2023-05-26 Add enum value 2772 to 2774 in Hh3cLswTypeOfSlot by jiangyongjiang
--    V4.14  2023-07-18 Add enum value 2775 to 2779 in Hh3cLswTypeOfSlot by jiangyongjiang
--    V4.15  2023-08-02 Add enum value 2780 to 2781 in Hh3cLswTypeOfSlot by jiangyongjiang
--           2023-08-16 Add enum value 2782 to 2786 in Hh3cLswTypeOfSlot by niujiahao
--           2023-08-09 Add enum value 822 to 825 in Hh3cLswTypeOfSlot by luoguixing
--           2023-08-16 Add enum value 2787 to 2790 in Hh3cLswTypeOfSlot by zhaoyunpeng
--    V4.16  2023-09-15 Add enum value 2791 to 2799 in Hh3cLswTypeOfSlot by jiangyongjiang
--           2023-04-25 Modify hh3cSlotCurrentVoltage and hh3cSlotCurrent from String to Integer32 by zhaoyunfei
--           2023-05-25 Add hh3cFrameCapacityPower hh3cFrameResidualPower hh3cFrameNormalPowerNum
--                      hh3cSlotTemperatureThreshold hh3cSlotNominalPower hh3cSlotNormalPowerNum by zhaomangyu
--           2023-06-09 Add hh3cSlotPatchVersion by shenhongxia
--                      Modify size in hh3cSysPatchPlatVersion by shenhongxia
--    V4.17  2023-10-11 Add enum value 2800 to 2812 in Hh3cLswTypeOfSlot by niujiahao
--           2023-11-08 Add enum value 2783 in Hh3cLswTypeOfSlot by niujiahao
--    V4.18  2023-11-13 Add enum value 826 to 827 in Hh3cLswTypeOfSlot by luoguixing
--           2023-11-17 Add enum value 2887 to 2895 in Hh3cLswTypeOfSlot by jiangyongjiang
--           2023-11-17 Add enum value 2896 to 2911 in Hh3cLswTypeOfSlot by niujiahao
--    V4.19  2023-12-27 Add enum value 2912 to 2915 in Hh3cLswTypeOfSlot by niujiahao
--    V4.20  2024-01-11 Add enum value 2916 to 2921 in Hh3cLswTypeOfSlot by jiangyongjiang
--           2024-01-15 Add enum value 2922 in Hh3cLswTypeOfSlot by niujiahao
--           2024-01-15 Add enum value 2923 to 2924 in Hh3cLswTypeOfSlot by jiangyongjiang
--           2024-01-15 Add enum value 2925 in Hh3cLswTypeOfSlot by niujiahao
--           2024-01-16 Add enum value 2926 in Hh3cLswTypeOfSlot by lihaijun
--           2024-01-16 Add enum value 2927 in Hh3cLswTypeOfSlot by niujiahao
--           2024-01-18 Add enum value 2928 in Hh3cLswTypeOfSlot by jiangyongjiang
--           2024-01-30 Add enum value 357 to 359 in Hh3cLswTypeOfSlot by wangzilong
--           2024-01-31 Add enum value 2929 to 2931 in Hh3cLswTypeOfSlot by wanghaijun
--    V4.21  2024-02-02 Add enum value 2932 to 2937 in Hh3cLswTypeOfSlot by wanghaijun
--           2024-01-30 Add enum value 360 in Hh3cLswTypeOfSlot by niujiahao
--           2024-02-02 Add enum value 2938 to 2939, 2941 to 2943 in Hh3cLswTypeOfSlot by niujiahao
--           2024-02-06 Add enum value 2944 to 2946 in Hh3cLswTypeOfSlot by wanghaijun
--           2024-02-14 Add enum value 2947 in Hh3cLswTypeOfSlot by niujiahao
--           2024-03-07 Add enum value 2948 in Hh3cLswTypeOfSlot by wanghaijun
--           2024-03-08 Add enum value 2949 to 2955 in Hh3cLswTypeOfSlot by niujiahao
--    V4.22  2024-03-15 Add enum value 2956 to 2972 in Hh3cLswTypeOfSlot by wanghaijun
--           2024-03-15 Add enum value 361 to 362 in Hh3cLswTypeOfSlot by wangzilong
--           2024-04-15 Add enum value 2973 to 2975 in Hh3cLswTypeOfSlot by niujiahao
--    V4.23  2024-04-18 Add enum value 2976 to 2984 in Hh3cLswTypeOfSlot by wanghaijun
--           2024-04-26 Modify enum value 2534 to 2541 in Hh3cLswTypeOfSlot by wanghaijun
--           2024-04-30 Add enum value 2985, 3000 to 3005 in Hh3cLswTypeOfSlot by niujiahao
--           2024-04-30 Add enum value 2986 to 2999 in Hh3cLswTypeOfSlot by wanghaijun
--           2024-05-09 Add enum value 828 to 831 in Hh3cLswTypeOfSlot by luoguixing
--           2024-05-16 Del enum value 327 in Hh3cLswTypeOfSlot by wangzilong
--           2024-05-16 Add enum value 3006 in Hh3cLswTypeOfSlot by chaopeng
--           2024-05-16 Add enum value 3007 in Hh3cLswTypeOfSlot by wanghaijun
--    V4.24  2024-05-23 Add enum value 3008 to 3016 in Hh3cLswTypeOfSlot by wanghaijun
--           2024-05-29 Modify enum value 2916 in Hh3cLswTypeOfSlot by wanghaijun
--           2024-05-29 Add enum value 831 to 833 in Hh3cLswTypeOfSlot by luoguixing
--           2024-06-12 Add enum value 3017 to 3018 in Hh3cLswTypeOfSlot by niujiahao
--           2024-06-12 Add enum value 3022 in Hh3cLswTypeOfSlot by niujiahao
--           2024-06-14 Del enum value 2928 in Hh3cLswTypeOfSlot by jiangyongjiang
--    V4.25  2024-06-17 Add enum value 3023 to 3024 in Hh3cLswTypeOfSlot by niujiahao
--           2024-06-21 Add enum value 3025 in Hh3cLswTypeOfSlot by wanghaijun
--           2024-06-17 Add enum value 3026 to 3027 in Hh3cLswTypeOfSlot by niujiahao
--           2024-06-27 Add enum value 3028 to 3031 in Hh3cLswTypeOfSlot by qichenglu
--           2024-06-27 Add enum value 3032 to 3036 in Hh3cLswTypeOfSlot by wanghaijun
--           2024-06-17 Add enum value 3027 to 3040 in Hh3cLswTypeOfSlot by niujiahao
--           2024-06-27 Add enum value 363 to 366 in Hh3cLswTypeOfSlot by wanghaijun
--           2024-07-09 Add enum value 367 to 383 in Hh3cLswTypeOfSlot by mayulei
--           2024-06-17 Add enum value 3041 in Hh3cLswTypeOfSlot by majianhe
--           2024-06-17 Add enum value 3042 to 3045 in Hh3cLswTypeOfSlot by heyujie
--    V4.26  2024-08-12 Add enum value 3046 to 3060 in Hh3cLswTypeOfSlot by wanghaijun
--           2024-08-23 Add enum value 384 to 386 in Hh3cLswTypeOfSlot by mayulei
--    V4.27  2024-09-12 Add enum value 3061 to 3062 in Hh3cLswTypeOfSlot by wanghaijun
--           2024-09-20 Add enum value 387 in Hh3cLswTypeOfSlot by niujiahao
--           2024-09-25 Modify enum value 3047 in Hh3cLswTypeOfSlot by wanghaijun
--           2024-09-25 Del enum value 3060 in Hh3cLswTypeOfSlot by wanghaijun
--           2024-09-12 Add enum value 3063 to 3064 in Hh3cLswTypeOfSlot by niujiahao
--           2024-09-29 Add enum value 3065 to 3074 in Hh3cLswTypeOfSlot by wanghaijun
--           2024-10-14 Modify enum value 3019 to 3021 in Hh3cLswTypeOfSlot by majianhe
--           2024-10-14 Add enum value 783 in Hh3cLswTypeOfSlot by qiuxianglong 11426
--           2024-10-14 Add hh3cComponentLicense and hh3cComponentTable by fangliwen
--    V4.28  2024-10-17 Modify enum value 3073 in Hh3cLswTypeOfSlot by wanghaijun
--           2024-10-22 Add enum value 388 to 389 in Hh3cLswTypeOfSlot by mayulei
--           2024-10-24 Add enum value 3075 to 3076 in Hh3cLswTypeOfSlot by majianhe
--           2024-10-31 Add enum value 3060 in Hh3cLswTypeOfSlot by renhaili
--           2024-11-05 Add enum value 390 in Hh3cLswTypeOfSlot by niujiahao
--    V4.29  2024-11-15 Add enum value 3078 to 3081 in Hh3cLswTypeOfSlot by niujiahao
--           2024-12-02 Add enum value 3082 to 3083 in Hh3cLswTypeOfSlot by liuhaijun
--    V4.30  2024-12-11 Add enum value 3084 in Hh3cLswTypeOfSlot by majianhe
--           2024-12-13 Add enum value 3085 to 3089 in Hh3cLswTypeOfSlot by qichenglu
--           2024-12-24 Modify enum value 3043 in Hh3cLswTypeOfSlot by lihaijun
--           2024-12-30 Add enum value 390 in Hh3cLswTypeOfSlot by niujiahao
--           2024-12-30 Add enum value 391 to 392 in Hh3cLswTypeOfSlot by xialihui
--           2024-12-31 Add enum value 3090 to 3094 in Hh3cLswTypeOfSlot by wanghaijun
--    V4.31  2025-01-21 Add enum value 3095 to 3098 in Hh3cLswTypeOfSlot by wanghaijun
--           2025-01-21 Add enum value 3099 to 3102 in Hh3cLswTypeOfSlot by niujiahao
--           2025-02-18 Del enum value 3027 in Hh3cLswTypeOfSlot by niujiahao
--    V4.32  2025-02-25 Add enum value 393 to 394 in Hh3cLswTypeOfSlot by mayulei
--           2025-02-27 Add enum value 395 to 398 in Hh3cLswTypeOfSlot by wangzhilong
--           2025-02-27 Add enum value 3103 to 3109 in Hh3cLswTypeOfSlot by niujiahao
--           2025-03-04 Add enum value 3110 in Hh3cLswTypeOfSlot by wanghaijun
--           2025-03-11 Add enum value 3111 in Hh3cLswTypeOfSlot by wanghaijun
--           2025-03-20 Add enum value 399 in Hh3cLswTypeOfSlot by wanghaijun
--           2025-03-11 Add enum value 3112 to 3122 in Hh3cLswTypeOfSlot by wanghaijun
--           2025-04-11 Add enum value 3123 to 3125 in Hh3cLswTypeOfSlot by renhaili
--           2025-04-11 Add enum value 3126 to 3127 in Hh3cLswTypeOfSlot by renhaili
--    V4.33  2025-04-15 Add enum value 3128 to 3133 in Hh3cLswTypeOfSlot by wanghaijun
--           2025-04-20 Add hh3cCpuGroupUsageTable by shenhongxia
--    V4.34  2025-06-11 Add enum value 3139 to 3140 in Hh3cLswTypeOfSlot by niujiahao
--           Modify enum value 3089 in Hh3cLswTypeOfSlot by mayulei
--           Add enum value 3141 in Hh3cLswTypeOfSlot by majianhe
--           Add enum value 3142 in Hh3cLswTypeOfSlot by niujiahao
--    V4.35  2025-07-09 Add enum value 3143 to 3151 in Hh3cLswTypeOfSlot by wanghaijun
--                      Add enum value 3152 to 3155 in Hh3cLswTypeOfSlot by chaopeng
--                      Add enum value 3156 to 3159 in Hh3cLswTypeOfSlot by mayulei
--    V4.36  2025-08-06 Add enum value 3160 in Hh3cLswTypeOfSlot by niujiahao
--                      Add enum value 3161 in Hh3cLswTypeOfSlot by wanghaijun
--                      Add enum value 3162 in Hh3cLswTypeOfSlot by niujiahao
--                      Add enum value 3163 to 3175 in Hh3cLswTypeOfSlot by wanghaijun
--    V4.37  2025-09-19 Add enum value 3176 in Hh3cLswTypeOfSlot by niujiahao
--                      Add enum value 3177 to 3184 in Hh3cLswTypeOfSlot by chaopeng
--                      Modify enum value 3091,3092 in Hh3cLswTypeOfSlot by wanghaijun
--                      Add enum value 3185 in Hh3cLswTypeOfSlot by wanghaijun
--                      Add hh3cDevAdmRlmTable by yuhaiyan
--    V4.38  2025-10-28 Add enum value 3186 in Hh3cLswTypeOfSlot by niujiahao

-- ==================================================================
HH3C-LSW-DEV-ADM-MIB DEFINITIONS ::= BEGIN
IMPORTS
    DisplayString, DateAndTime, TEXTUAL-CONVENTION
        FROM SNMPv2-TC
    MODULE-IDENTITY, OBJECT-TYPE, IpAddress, Unsigned32, Integer32, Counter64
        FROM SNMPv2-SMI
    hh3clswCommon
        FROM HH3C-OID-MIB
    CounterBasedGauge64
        FROM HCNUM-TC
    SnmpAdminString
        FROM SNMP-FRAMEWORK-MIB;

-- ==================================================================
--
-- ======================= definition begin =========================
--
-- ==================================================================

-- system information: hh3cLswDeviceAdmin
-- ==================================================================
    hh3cLswDeviceAdmin MODULE-IDENTITY
        LAST-UPDATED "202508110000Z"
        ORGANIZATION
            "New H3C Technologies Co., Ltd."
        CONTACT-INFO
            "Platform Team New H3C Technologies Co., Ltd.
             Hai-Dian District Beijing P.R. China
             http://www.h3c.com
             Zip: 100085"
        DESCRIPTION
            "Private MIB files contain basic information about the device."
        REVISION "202508110000Z"
        DESCRIPTION
        "Add hh3cDevAdmRlmTable"
        REVISION "202507090000Z"
        DESCRIPTION
        "Add enumerate value in Hh3cLswTypeOfSlot"
        REVISION "202506110000Z"
        DESCRIPTION
        "Add enumerate value in Hh3cLswTypeOfSlot"
        REVISION "202504200000Z"
        DESCRIPTION
        "Add hh3cCpuGroupUsageTable"
        REVISION "202406280000Z"
        DESCRIPTION
            "Add hh3cComponentLicense and hh3cComponentTable"
        REVISION "202406200000Z"
        DESCRIPTION
            "Add hh3cFrameCapacityPower hh3cFrameResidualPower hh3cFrameNormalPowerNum
             hh3cSlotTemperatureThreshold hh3cSlotNominalPower hh3cSlotNormalPowerNum"
        REVISION "202306140000Z"
        DESCRIPTION
            "Add hh3cSlotPatchVersion and modify size in hh3cSysPatchPlatVersion."
        REVISION "202305250000Z"
        DESCRIPTION
            "Modify hh3cSlotCurrentVoltage and hh3cSlotCurrent from String to Integer32."
        REVISION "202304250000Z"
        DESCRIPTION
            "Add hh3cSysProductName hh3cSysProductVersion hh3cSysPatchPlatVersion."
        REVISION "202303010000Z"
        DESCRIPTION
            "Add hh3cSlotCurrentVoltage and hh3cSlotCurrent."
        REVISION "202302230000Z"
        DESCRIPTION
            "The latest baseline."
        REVISION "202211040000Z"
        DESCRIPTION
            "Add hh3cLswFramePowerRedundancyType and hh3cLswSlotPower hh3cLswFrameNominalPower."
        REVISION "202203180000Z"
        DESCRIPTION
            "Add hh3cLswFrameTotalPower and hh3cLswSysTotalPower."
        REVISION "202202090000Z"
        DESCRIPTION
            "Add hh3cLswOutputPowerTable."
        REVISION "201911210000Z"
        DESCRIPTION
            "Modify oid of hh3cLswFrameSerialNumber and hh3cLswFrameClassType."
        REVISION "201901220000Z"
        DESCRIPTION
            "Add Add hh3cLswCoreMinorThreshold hh3cLswCoreRecoveryThreshold"
        REVISION "201707250000Z"
        DESCRIPTION
            "Add hh3cLswCoreTable"
        REVISION "201705130000Z"
        DESCRIPTION
            "Add hh3cLswCpuGroupTable"
        REVISION "201702100000Z"
        DESCRIPTION
            "Add hh3cLswPowerTable  hh3cLswTransceiverTable hh3cLswFanTable
             Add hh3cLswFrameSerialNumber hh3cLswSlotSerialNumber hh3cLswSubslotSerialNumber"
        REVISION "201701120000Z"
        DESCRIPTION
            "Add enum Value 11 to 32 to hh3cLswCpuEntry"
        REVISION "201603260000Z"
        DESCRIPTION
            "Add hh3cLswFrameClassType, hh3cLswFrameDisplayId and hh3cLswFrameName"
        REVISION "201510080000Z"
        DESCRIPTION
            "Add hh3cLswSlotPktBufThreshold."
        REVISION "200104040000Z"
        DESCRIPTION
            "The first baseline."
        ::= { hh3clswCommon  18 }

    Hh3cLswTypeOfSlot ::= TEXTUAL-CONVENTION
        STATUS      current
        DESCRIPTION "The type of slots for lan switch devices."
        SYNTAX INTEGER {
            type-NULL(0),           -- NULL
            type-10OR100M(1),           -- 10M/100M Ethernet Copper Interface Module
            type-1000BASE-LX-SM(2),     -- 1000BASE-X Module (SMF, LC)
            type-1000BASE-SX-MM(3),     -- 1000BASE-X Module (MMF, SC)
            type-1000BASE-TX(4),        --
            type-100M-SINGLEMODE-FX(5),     -- 100M Ethernet Single Mode Optical Interface Module
            type-100M-MULTIMODE-FX(6),      -- 100M Ethernet Multi-mode Optical Interface Module
            type-100M-100BASE-TX(7),        -- 100M Ethernet copper Interface Module(RJ45)
            type-100M-HUB(8),           -- 100M Base-TX transportation Interface Module
            type-VDSL(9),           -- VDSL
            type-STACK(10),         -- GigaStack Module
            type-1000BASE-ZENITH-FX(11),    -- 1000M Ethernet Single Mode Optical Interface Module(1550nm,70km,LC)
            type-1000BASE-LONG-FX(12),      -- 1000M Ethernet Single Mode Optical Interface Module(1550nm,40km,LC)
            type-ADSL(13),          -- ADSL
            type-4T10OR100-4FX100SM(14),    -- 4-Port Single Mode Optical Interface and 4-Port 10M/100M Ethernet Interface Module
            type-4T10OR100-4FX100MM(15),    -- 4-Port Multi-mode Optical Interface and 4-Port 10M/100M Ethernet Interface Module
            type-VSPL(16),          -- VDSL Board
            type-ASPL(17),          -- ADSL Board
            type-1000M-SFP(18),         -- 1000BASE-X SFP Module
            type-LS82O2CM(19),          -- ATM OC-3c/STM-1 Daughter Card (SFP)
            type-LS82P2CM(20),          -- POS OC-3c/STM-1 Daughter Card (SFP)
            type-LS82O4GM(21),          -- MPLS 1000BASE-X Daughter Card (GBIC)
            type-LS82GB4C(22),          -- 1000BASE-X Daughter Card (GBIC)
            type-LS82GT4C(23),          -- 1000BASE-T Daughter Card (RJ-45)
            type-LS82ST4C(24),          -- GigaStack Daughter Card
            bOARD-TYPE-LS82DSPU(25),        -- Dual Service Processing Module
            bOARD-TYPE-LS81GP8U(26),        -- Gigabit Ethernet Interface Process Module
            bOARD-TYPE-LS82GT20(27),        -- 1000BASE-T Module (RJ-45)
            bOARD-TYPE-LS82FE48(28),        -- 10/100BASE-TX Module (RJ-45)
            type-LS82T24B(29),          -- 24-Port 10/100BASE-TX (RJ-45) and 2 Port 1000BASE-X (GBIC) Module
            type-LSB1SRPA(30),          --
            type-LSB1FT48A(31),         -- 48-Port 10Base-T/100Base-TX Auto-sensing Fast Ethernet Board A
            type-LSB1FT48B(32),         -- 48-Port 10Base-T/100Base-TX Auto-sensing Fast Ethernet Board B
            type-LSB1F48GA(33),         -- 32-Port 10Base-T/100Base-TX Auto-sensing Fast Ethernet and 4-Port 1000Base-X (SFP) GE Board A
            type-LSB1F48GB(34),         -- 32-Port 10Base-T/100Base-TX Auto-sensing Fast Ethernet and 4-Port 1000Base-X (SFP) GE Board B
            type-LSB1FP20A(35),         -- 20-Port 100Base-FX (SFP) Fast Ethernet Board A
            type-LSB1FP20B(36),         -- 20-Port 100Base-FX (SFP) Fast Ethernet Board B
            type-FT48A(37),         -- 48-Port 10Base-T/100Base-TX Auto-sensing Fast Ethernet Interface Module
            type-GP4U(38),          -- 1000Base-X (SFP)  GE Interface Module
            type-GP2U(39),          -- 1000Base-X (SFP)  GE Interface Module
            type-TGX1A(40),         -- 10GBASE-R  (XENPAK) Interface Module
            type-1000BASE-LX-SM-IR-SC(41),  -- 1000M Ethernet Single Mode Optical Interface Module(1310nm,10km,SC)
            type-1000BASE-SX-MM-SR-SC(42),  -- 1000M Ethernet Multi-mode Optical Interface Module(850nm,500m,SC)
            type-1000BASE-T-RJ45(43),       -- 1000M Ethernet Copper Interface Module(RJ45)
            type-100BASE-FX-SM-IR-SC(44),   -- 100M Ethernet Single Mode Optical SubCard
            type-100BASE-FX-MM-SR-SC(45),   -- 100M Ethernet Multi-mode Optical SubCard
            type-GIGA-STACK-1M-PC(46),      -- GigaStack Daughter SubCard
            type-1000BASE-LX-SM-VLR-LC(47), -- 1000M Ethernet Single Mode Optical SubCard(1550nm,70km,LC)
            type-1000BASE-LX-SM-LR-LC(48),  -- 1000M Ethernet Single Mode Optical SubCard(1550nm,40km,LC)
            type-100BASE-FX-SM-LR-SC(49),   -- 100M Ethernet Single Mode Optical SubCard(1310nm,15km,SC)
            type-1000BASE-X-GBIC(50),       --
            type-100M-SINGLEMODE-FX-LC(51), -- 100M Ethernet Single-mode Optical SubCard(1310nm,2km,SC)
            type-100M-MULTIMODE-FX-LC(52),  -- 100M Ethernet Multi-mode Optical SubCard(1310nm,2km,SC)
            type-1000BASE-4SFP(53),     -- 4-Port 1000BASE-FX Single Mode Fiber Optic Transceivers LR with SC Connector
            type-1000BASE-4GBIC(54),        -- 4-Port 1000BASE-X Module(GBIC)
            type-1000BASE-FIXED-4SFP(55),   -- 4-Port 1000BASE-FX Single Mode Fiber Optic Transceivers LR with SC Connector
            type-1000BASE-FIXED-4GBIC(56),  -- 4-Port 1000BASE-X Module(GBIC)
            type-LSB1GP12A(57),         -- 12-Port 1000Base-X (SFP) GE Board A
            type-LSB1GP12B(58),         -- 12-Port 1000Base-X (SFP) GE Board B
            type-LSB1TGX1A(59),         -- 1-Port 10GBASE-R (XENPAK) Board A
            type-LSB1TGX1B(60),         -- 1-Port 10GBASE-R (XENPAK) Board B
            type-LSB1P4G8A(61),         -- 4*155M POS Optical Interface Module 8-Port 1000Base-X (SFP) GE and 4-Port 155M POS Board A
            type-LSB1P4G8B(62),         -- 4*155M POS Optical Interface Module 8-Port 1000Base-X (SFP) GE and 4-Port 155M POS Board B
            type-LSB1A4G8A(63),         -- 4*155M ATM Optical Interface Module 8-Port 1000Base-X (SFP) GE and 4-Port 155M ATM Board A
            type-LSB1A4G8B(64),         -- 4*155M ATM Optical Interface Module 8-Port 1000Base-X (SFP) GE and 4-Port 155M ATM Board B
            type-FT48C(65),         -- 48-Port 10Base-T/100Base-TX Auto-sensing Fast Ethernet Board C
            type-FP20(66),                  -- 20-port 100BASE-TX Module
            bOARD-TYPE-LS81FT48(67),        -- 48-Port 10/100BASE-TX Module (RJ-45)
            bOARD-TYPE-LS81GB8U(68),        -- 8-Port 1000BASE-X Module (GBIC)
            bOARD-TYPE-LS81GT8U(69),        -- 8-Port 1000BASE-T Module (RJ-45)
            bOARD-TYPE-LS81FS24(70),        -- 24-Port 100BASE-FX Module (SMF,MT-RJ)
            bOARD-TYPE-LS81FM24(71),        -- 24-Port 100BASE-FX Module (MMF,MT-RJ)
            bOARD-TYPE-LS82GP20(72),        -- Switching and Route Processing Board B (main board)
            type-LSB1SRPB(73),          --
            type-LSB1F32GA(74),         -- 32-Port Fast Ethernet + 4-Port Gigabit Ethernet module A
            type-LSB1F32GB(75),         -- 32-Port Fast Ethernet + 4-Port Gigabit Ethernet module B
            type-LSB2FT48A(76),         -- 48-Port 10Base-T/100Base-TX Auto-sensing Fast Ethernet Board A (ver 2)
            type-LSB2FT48B(77),         -- 48-Port 10Base-T/100Base-TX Auto-sensing Fast Ethernet Board B (ver 2)
            type-LSB1GT12A(78),         -- 12 Port 10/100/1000 Base-T  Interface Module
            type-LSB1GT12B(79),         -- 12 Port 10/100/1000 Base-T  Interface Module
            type-PC4U(80),          -- 4 Port155M POS(SFP) Interface Module
            type-FT32A(81),         -- 32 Port 10/100 Base-T FE Interface Module
            type-GT4U(82),          -- 4 Port 10/100/1000 Base-T  Interface Module
            bOARD-TYPE-LS83FP20A(83),       --
            bOARD-TYPE-LS82HGMU(84),        --
            type-LSB1GP8TB(85),         --
            type-LSB1GP8TC(86),         --
            type-LSB1GT8PB(87),         --
            type-LSB1GT8PC(88),         --
            type-LSB1FT48C(89),         -- 48-Port 100Base-TX Ethernet Interface module C
            type-LSB1FP20C(90),         -- 20-Port 100Base-FX(SFP) Fast Ethernet Interface Module C
            type-LSB1F32GC(91),         -- 32-Port Fast Ethernet + 4-Port Gigabit Ethernet interface module C
            type-LSB1GT12C(92),         -- 12-Port 10/100/1000 Base-T  Interface Module C
            type-LSB1GP12C(93),         -- 12-Port 1000Base-X(SFP) GE Interface Module C
            type-LSB1P4G8C(94),         -- 8-Port 1000Base-X(SFP) GE + 4-Port 155M POS Interface Module C
            type-LSB1TGX1C(95),         -- 1-Port 10GBase-R/X  Ethernet XENPAK Optical Interface Module C
            type-LSB1GT24B(96),         -- 24-Ports 10/100/1000Base-T Ethernet Interface Module B
            type-LSB1GT24C(97),         -- 24-Ports 10/100/1000Base-T Ethernet Interface Module C
            type-LSB1GP24B(98),         -- 24-Ports 1000Base-X Ethernet Interface Module B
            type-LSB1GP24C(99),         -- 24-Ports 1000Base-X Ethernet Interface Module C
            type-LSB1XP2B(100),         -- 2-Port 10GBase-R/W Ethernet XFP Optical Interface Module B
            type-LSB1XP2C(101),         -- 2-Port 10GBase-R/W Ethernet XFP Optical Interface Module C
            type-LSB1GV48B(102),        -- 48-Ports 10/100/1000Base-T Ethernet Interface Module B
            type-LSB1GV48C(103),        -- 48-Ports 10/100/1000Base-T Ethernet Interface Module C
            type-LSB1SRPC(104),         -- Switching and Route Processing Board C
            type-LSB1SRP1N0(105),       -- Switching and Route Processing Board 1N0
            type-LSB1SRP1N1(106),       -- Switching and Route Processing Board 1N1
            type-LSB1SRP1N2(107),       -- Switching and Route Processing Board 1N2
            type-GT24(108),         --
            type-GP24(109),         --
            type-XP2(110),          --
            type-GV48(111),         --
            type-LSG1GP8U(112),         -- 8 Port 1000BASE Module (SFP)
            type-LSG1GT8U(113),         -- 8 Port 1000BASE-T Module (RJ45)
            type-LSG1TG1U(114),         -- 1 Port 10GBASE Module(XENPAK)
            type-LSG1TD1U(115),         -- 1 Port 10GBASE-CX4 Module(IB4X)
            type-LSB2FT48C(116),        -- 48-Ports 100Base-TX Ethernet Interface module C
            type-LSB1GT48B(117),        -- 48-Ports 10/100/1000Base-T Ethernet Interface Module B
            type-LSB1GT48C(118),        -- 48-Ports 10/100/1000Base-T Ethernet Interface Module C
            type-LS81GT48(119),             -- 48 Port Gigabit Ethernet Electric Interface Unit

            type-LS81SRPG0(120),        -- Salience III, Switch and Route Processing Board
            type-LS81SRPG1(121),        -- Salience III Plus
            type-LS81SRPG2(122),        -- Salience III Lite
            type-LS81SRPG3(123),        -- Salience III Edge

--          type-LS81SRPG(124),              Switch And Route Processing Unit, Salience III. not used. not used.

            type-SR01SRPUB(125),                -- Switching and Route Processing Unit
            type-SR01SRPUA(126),                -- Switching and Route Processing Unit
            type-SR01GP12L(127),                -- 12-Port 1000Base-X Ethernet SFP Optical Interface Line Card(L)
            type-SR01GP12W(128),                -- 12-Port 1000Base-X Ethernet SFP Optical Interface Line Card(W)
            type-SR01FT48L(129),                -- 48-Port 10/100Base-TX Ethernet RJ45 Electrical Interface Line Card (L)
            type-SR01FT48W(130),                -- 48-Port 10/100Base-TX Ethernet RJ45 Electrical Interface Line Card (W)
            type-SR01XK1W(131),                 -- 1-Port 10GBase-R Ethernet XENPAK Optical Interface Line Card (W)
            type-SR01FP20W(132),                -- 20-Port 100Base-FX Ethernet SFP Optical Interface Line Card (W)
            type-SR01GT12W(133),                -- 12-Port 10/100/1000Base-T Ethernet RJ45 Electrical Interface Line Card (W)
            type-SR01F32GL(134),                -- 32-Port 10/100Base-TX Ethernet RJ45 Electrical Interface + 4-Port 1000Base-X Ethernet SFP Optical interface Line Card (L)
            type-SR01F32GW(135),                -- 32-Port 10/100Base-TX Ethernet RJ45 Electrical Interface  + 4-Port 1000Base-X  Ethernet SFP Optical interface Line Card (W)
            type-SR01GT8PL(136),                -- 8-Port 10/100/1000Base-T Ethernet RJ45 Electrical Interface + 4-Port 1000Base-X Ethernet SFP Optical Line Card (L)
            type-SR01GT8PW(137),                -- 8-Port 10/100/1000Base-T Ethernet RJ45 Electrical Interface + 4-Port 1000Base-X Ethernet SFP Optical Line Card (W)
            type-SR01P4G8W(138),                -- 4-Port 155M POS Optical Interface + 8-Port 1000Base-X Ethernet SFP Optical Interface Line Card (W)
            type-LSA1FP8U(139),                 -- 8 Ports 100Base-FX Ethernet SFP Card

            type-LSB1SP4B(140),                 -- 4-Port OC-48 POS SFP Optical Interface Board B
            type-LSB1SP4C(141),                 -- 4-Port OC-48 POS SFP Optical Interface Board C
            type-LSB1UP1B(142),                 -- 1-Port OC-192 POS XFP Optical Interface Board B
            type-LSB1UP1C(143),                 -- 1-Port OC-192 POS XFP Optical Interface Board C
            type-LSB1XP4B(144),                 -- 4-Port 10GBase Ethernet XFP Optical Interface Board B
            type-LSB1XP4C(145),                 -- 4-Port 10GBase Ethernet XFP Optical Interface Board C
            type-SP4(146),                      -- 4-Port OC-48 POS SFP Optical Interface Module
            type-UP1(147),                      -- 1-Port OC-192 POS XFP Optical Interface Module
            type-XP4(148),                      -- 4-Port 10GBase Ethernet XFP Optical Interface Module

            type-LS81VSNP(149),                 -- VerSatile Network Processing Board
            type-LS81T12P(150),                 -- 12-Port 1000Base-T Gigabit Ethernet Interface(RJ45)+4-Port 1000BASE-X  Gigabit Ethernet Optical Interface Board(SFP,LC)
            type-LS81P12T(151),                 -- 12-Port 1000BASE-X Gigabit Ethernet Optical Interface(SFP,LC)+4-Port 1000BASE-T Gigabit Ethernet Interface Board(RJ45)
            type-LS81GP8UB(152),                -- 8-Port 1000M Ethernet Optical Interface Board(SFP,LC),LC Connector
            type-LS81FT48E(153),                -- 48-Port 100M Ethernet Electrical Interface Switch Unit(RJ45)
            type-LS81GP4UB(154),                -- 4-Port 1000M Ethernet Optical Interface Board(SFP,LC)
            type-LS81GT8UE(155),                -- 8-Port 1000M Ethernet Electrical Interface Switch Unit (RJ45)
            type-LS81GT48A(156),                -- 48 Port Gigabit Ethernet Electric Interface Unit
            type-LS81FP48(157),                 -- 48 Port 100M Ethernet Optical Interface Board(SFP,LC)

            type-LSB1XK1B(158),                 -- 1-Port 10GBase-R Ethernet XENPAK Optical Interface Board B
            type-LSB1XK1C(159),                 -- 1-Port 10GBase-R Ethernet XENPAK Optical Interface Board C

            type-SR01SRPUC(160),                -- Switching and Route Processing Unit C
            type-SR01SRPUD(161),                -- Switching and Route Processing Unit D
            type-SR01SRPUE(162),                -- Switching and Route Processing Unit E

            type-LSB1SRP1N3(163),               -- Switching and Route Process Unit, Clock Module
            type-LSB1VP2B(164),                 -- 2*10G Resilient Packet Ring Interface Line Card (B)
            type-LSB1NATB(165),                 -- NAT Service Processing Card (B)
            type-LSB1VPNB(166),                 -- VPN Service Processing Card (B)

            type-LSGP8P(167),                   -- 8-Port 1000M SFP Module
            type-LSXK1P(168),                   -- 1-Port 10G Xenpak Module
            type-LSXP2P(169),                   -- 2-Port 10G XFP Module

            type-LS81FT48F(170),                -- 48-Port 100M Ethernet Electrical Interface Switch Unit(RJ45)

            type-LS81PT8G(171),                 -- 8 Port 1000BASE-X Gigabit Passive Optical Line Interface Board
            type-LS81PT4G(172),                 -- 4 Port 1000BASE-X Gigabit Passive Optical Line Interface Board

            type-LSSTK24G(173),                 -- 2-Port 24G Cascade Port Module

            type-LS82GT20A(174),                -- 20-Port 1000Base-T Gigabit Ethernet Electrical Interface Board(RJ45), BCM5697
            type-LS82GP20A(175),                -- 20-Port 1000BASE-X Gigabit Ethernet Optical Interface Board(SFP,LC), BCM5697
            type-LS81TGX1C(176),                -- 1-Port 10G Base-R Ethernet Board

            type-VP2(177),                      -- 2*10G Resilient Packet Ring Interface Module
            type-LSA1FB8U(178),                 -- 8-Port 100Base-Fx BIDI Ethernet Board

            type-LS81T12PE(179),                -- 12-Port 1000Base-T GE Interface+4-Port 1000BASE-X GE Optical Interface Board(SFP,LC)
            type-LS81P12TE(180),                -- 12-Port 1000BASE-X GE Optical Interface(SFP,LC)+4-Port 1000 BASE-T GE Interface Board(RJ45)

            type-LSB1SRP2N0(181),               -- Switching and Route Process Unit,12*LPU
            type-LSB1SRP2N3(182),               -- Switching and Route Process Unit, Clock Module
            type-LSB1GV48DB(183),               -- 48 Ports 1000Base-T Ethernet Interface Line Card with POE(DB)
            type-LSB1FW8B(184),                 -- Firewall Service Processing Board with 8GE (B)
            type-LSB1IPSEC8B(185),              -- VPN Service Processing Board with 8GE (B)
            type-LSB1IDSB(186),                 -- IDS Service Processing Board (B)
            type-LSB1IPSB(187),                 -- IPS Service Processing Board (B)
            type-LSB2FT48CA(188),               -- 48 Ports 100Base-TX Ethernet Line Card (CA)
            type-LSB1FP20CA(189),               -- 20 Ports 100Base-FX Ethernet Interface Service Card (CA)
            type-LSB1F32GCA(190),               -- 32 Ports FE and 4 Ports GE Line Card(CA)
            type-LSB1P4G8CA(191),               -- 4 Ports OC-3c POS and 8 Ports GE Line Card(CA)
            type-LSB1GT12CA(192),               -- 12 Ports 1000Base-T Ethernet Interface Line Card(CA)
            type-LSB1GT24CA(193),               -- 24 Ports 1000Base-T Ethernet Interface Line Card(CA)
            type-LSB1GP12CA(194),               -- 12 Ports 1000Base Ethernet Optical Interface Service Card(CA)
            type-LSB1GP24CA(195),               -- 24 Ports 1000Base-X Ethernet Interface Line Card (CA)
            type-LSB1GT8PCA(196),               -- 8 Ports 1000Base-T Ethernet Interface & 4 Ports 1000Base-X Ethernet SFP Interface Line Card(CA)
            type-LSB1XP2CA(197),                -- 2-Port 10GBase-R/W Ethernet XFP Optical Interface Card(CA)
            type-LSB1XK1CA(198),                -- 10GBase-R Ethernet XENPAK Optical Interface Line Card(CA)
            type-LSB1XP4CA(199),                -- 4-Port 10GBase-R/X Ethernet Optical Interface Line Card(CA)
            type-LSB1UP1CA(200),                -- Single Port OC-192c POS XFP Optical Interface Card(CA)
            type-LSB1SP4CA(201),                -- 4-Port OC-48c POS SFP Optical Interface Card(CA)
            type-LSB1VP2CA(202),                -- 2*10G RPR Process Unit(CA)
            type-SR01FT48WA(203),               -- 48 Ports 100Base-TX Ethernet Line Card (WA)
            type-SR01FP20WA(204),               -- 20 Ports 100Base-FX Ethernet Interface Service Card (WA)
            type-SR01F32GWA(205),               -- 32 Ports FE and 4 Ports GE Line Card(WA)
            type-SR01P4G8WA(206),               -- 4 Ports OC-3c POS and 8 Ports GE Line Card(WA)
            type-SR01GT12WA(207),               -- 12 Ports 1000Base-T Ethernet Interface Line Card(WA)
            type-SR01GT24WA(208),               -- 24 Ports 1000Base-T Ethernet Interface Line Card(WA)
            type-SR01GP12WA(209),               -- 12 Ports 1000Base Ethernet Optical Interface Service Card(WA)
            type-SR01GP24WA(210),               -- 24 Ports 1000Base-X Ethernet Interface Line Card (WA)
            type-SR01GT8PWA(211),               -- 8 Ports 1000Base-T Ethernet Interface & 4 Ports 1000Base-X Ethernet SFP Interface Line Card(WA)
            type-SR01XP2WA(212),                -- 2-Port 10GBase-R/W Ethernet XFP Optical Interface Card(WA)
            type-SR01XK1WA(213),                -- 10GBase-R Ethernet XENPAK Optical Interface Line Card(WA)
            type-SR01UP1WA(214),                -- Single Port OC-192c POS XFP Optical Interface Card(WA)
            type-SR01SP4WA(215),                -- 4-Port OC-48c POS SFP Optical Interface Card(WA)
            type-GP8U(216),                     -- 8-Port 1000Base-X SFP Optical Interface Module
            type-LSEXP1P(217),                  -- Single 10G SFP Optical Interface Module
            type-LSEXK1P(218),                  -- Single 10G XENPAK Interface Module
            type-LSEXS1P(219),                  -- Single 10G STACK Interface Module

            type-LS81GP48(220),                 -- 48-Port 1000M Ethernet Optical Interface Board(SFP,LC),LC Connector
            type-LS81GT48B(221),                -- 48-Port 1000Base-T Gigabit Ethernet Interface Board(RJ45)
            type-LS81T16P(222),                 -- 16-Port 1000Base-T Gigabit Ethernet Interface(RJ45) + 8-Port 1000BASE-X Gigabit Ethernet Optical Interface Board(SFP,LC)
            type-LS81T32P(223),                 -- 32-Port 1000Base-T Gigabit Ethernet Interface(RJ45) + 16-Port 1000BASE-X Gigabit Ethernet Optical Interface Board(SFP,LC)
            type-LS81TGX2(224),                 -- 2-Port 10GBASE Ethernet Interface Board(XFP,LC)
            type-LS81TGX4(225),                 -- 4-Port 10GBASE Ethernet Interface Module(XFP,LC),XG

            type-LSB1GV48DA(226),               -- 48 Ports 1000Base-T Ethernet Interface Line Card with POE(DA)
            type-SR01GV48VB(227),               -- 48 Ports 1000Base-T Ethernet Interface Line Card with POE(VB)

            type-LSB1GT24DB(228),               -- 24 Ports 1000Base-T Ethernet Interface Line Card(DB)
            type-LSB1GP24DB(229),               -- 24 Ports 1000Base-X Ethernet Interface Line Card(DB)
            type-LSB1GP24DC(230),               -- 24 Ports 1000Base-X Ethernet Interface Line Card(DC)
            type-LSB1FW8DB(231),                -- 8-port 1000BASE-X (SFP) Firewall Service Card(DB)
            type-LSB1IPSEC8DB(232),             -- 8-port 1000BASE-X (SFP) IPSEC Service Card(DB)
            type-SR01GT24VB(233),               -- 24 Ports 1000Base-T Ethernet Interface Line Card(VB)
            type-SR01GP24VC(234),               -- 24 Ports 1000Base-X Ethernet Interface Line Card(VC)
            type-SR01VP2WA(235),                -- 2*10G RPR Process Unit(WA)
            type-SR01FW8VB(236),                -- 8-port 1000BASE-X (SFP) Firewall Service Card(VB)
            type-SR01IPSEC8VB(237),             -- 8-port 1000BASE-X (SFP) IPSEC Service Card(VB)
            type-SR01NATL(238),                 -- NAT Service Processing Card (L)
            type-SR01VPNL(239),                 -- VPN Service Processing Card (L)

            type-LSB1GP24CB(240),               -- 24 Ports 1000Base-X Ethernet Interface Line Card(CB)
            type-LSB1GP48DB(241),               -- 48-Port Gigabit Ethernet Optical Interface Line Card(DB)
            type-LSB1XP2CB(242),                -- 2-Port 10Gigabit Ethernet Optical Interface Card(CB)
            type-XP4L(243),                     -- 4 Port 1000BASE Optic Interface Module (XFP)
            type-LSB1XP4LDB(244),               -- 4-Port 10GBase-R/W Ethernet XFP Optical Interface Line Speed Card(DB)
            type-LSB1XP4LDC(245),               -- 4-Port 10GBase-R/W Ethernet XFP Optical Interface Line Speed Card(DC)
            type-AHP4(246),                     -- 2-Port OC-3 ATM and 2-Port OC-3/12 ATM Interface Module (SFP)
            type-LSB1AHP4GCA(247),              -- 2-Port OC-3 ATM and 2-Port OC-3/12 ATM and 8-Port 1000Base-X Ethernet Optical Interface Line Card(CA)
            type-CLP4(248),                     -- 4 Ports OC-3/STM-1 CPOS Optical Interface Module(SFP)
            type-LSB1CLP4GCA(249),              -- 4 Ports OC-3/STM-1 CPOS Optical Interface and 4-Port 1000Base-X Ethernet Optical Interface Line Card(CA)
            type-ET32(250),                     -- 32-Port Channelized E1/T1 Interface Module
            type-LSB1ET32GCA(251),              -- 32-Port Channelized E1/T1 Interface and 4-Port 1000Base-X Ethernet Optical Interface Line Card(CA)
            type-LSB1IDSDB(252),                -- Intrusion Detection Service Card(DB)
            type-LSB1SRP2N1(253),               -- Switching and Route Processing Board,8*LPU

            bOARD-TYPE-LS82SRPB(254),           --
            bORAD-TYPE-LS83SRPC(255),           --
            type-Main(256),                     --

            type-LSB1SRP2N2(257),               -- Switching and Route Processing Board,5*LPU
            type-LSB1NAMB(258),                 -- NAM Service Processing Card (B)
            type-RSP2(259),                     -- 2*2.5G Resilient Packet Ring Interface
            type-LSB1RSP2CA(260),               -- 2*2.5G Resilient Packet Ring Interface Line Card(CA)
            type-SR01XP4LVC(261),               -- 4-Port 10GBase-R/W Ethernet XFP Optical Interface Line Speed Card(VC)
            type-SR01AHP4GWA(262),              -- 2-Port OC-3 ATM and 2-Port OC-3/12 ATM and 8-Port 1000Base-X Ethernet Optical Interface Line Card(WA)
            type-SR01CLP4GWA(263),              -- 4 Ports OC-3/STM-1 CPOS Optical Interface and 4-Port 1000Base-X Ethernet Optical Interface Line Card(WA)
            type-SR01ET32GWA(264),              -- 32-Port Channelized E1/T1 Interface and 4-Port 1000Base-X Ethernet Optical Interface Line Card(WA)
            type-SR01IDSVB(265),                -- Intrusion Detection Service Card(VB)
            type-SR01SRPUF(266),                -- Switching and Route Processing Board,12*LPU
            type-SR01NAML(267),                 -- NAM Service Processing Card (L)
            type-SR01RSP2WA(268),                -- 2*2.5G Resilient Packet Ring Interface Line Card(WA)
            type-LSPM1XP1P(269),                -- 1-Port 10G XFP Module
            type-LSPM1XP2P(270),                -- 2-Port 10G XFP Module
            type-LSPM1CX2P(271),                -- 2-Port 10G CX4 Module
            type-STK-1000BASE-T(272),           -- Single Port 1000BASE-T Stack Ethernet Interface Card
--
-- 273 to 299 reserved for other product
--


--
-- 300 to 499 reserved for advanced switchs part I
--
            type-LSB1SRP1M0(300),               -- Switching and Route Process Unit,2*LPU or 3*LPU
            type-LSB1SRP1M1(301),               -- Switching and Route Process Unit
            type-LSB1GP12DB(302),               -- 12 Ports 1000Base Ethernet Optical Interface Service Card(DB)
            type-LSB1GT12DB(303),               -- 12 Ports 1000Base-T Ethernet Interface Line Card(DB)
            type-LSB1XK1DB (304),               -- 10GBase-R Ethernet XENPAK Optical Interface Line Card(DB)
            type-LSB1XP2DB (305),               -- 2-Port 10GBase-R/W Ethernet XFP Optical Interface Card(DB)
            type-LSB1XP2DC (306),               -- 2-Port 10GBase-R/W Ethernet XFP Optical Interface Card(DC)
            type-LSB1GT48LDB(307),              -- 48-Port Gigabit Ethernet RJ45 Electrical Interface Card (DB)
            type-LSB1XP4TDB(308),               -- 4-Port 10GBase-R/W Ethernet XFP Optical Interface Line Speed Test Card(DB)
            type-LSB1XP4TDC(309),               -- 4-Port 10GBase-R/W Ethernet XFP Optical Interface Line Speed Test Card(DC)
            type-LSB1RSP2DC(310),               -- 2*2.5G Resilient Packet Ring Interface Line Card(DC)
            type-LSB1VP2DC (311),               -- 2*10G Resilient Packet Ring Process Unit(DC)
            type-LSB1XP4DB (312),               -- 4-Port 10GBase-R/X Ethernet Optical Interface Line Card(DB)
            type-LSB1SRP2E0(313),               -- Switching and Route Process Unit,12*LPU
            type-LSB1SRP2E1(314),               -- Switching and Route Process Unit,8*LPU
            type-LSB1SRP2E2(315),               -- Switching and Route Process Unit,5*LPU
            type-LSB1SRP2E3(316),               -- Switching and Route Process Unit, Clock module
            type-SR01SRPUQ(317),                -- Switching and Route Processing Unit Q
            type-AHP1(318),                     -- 1-Port OC-12c(3c)/STM-4(1) ATM Optical Interface Module(SFP)
            type-AHP2(319),                     -- 2-Port OC-12c(3c)/STM-4(1) ATM Optical Interface Module(SFP)
            type-CLP1(320),                     -- 1-Port OC-3/STM-1 CPOS Optical Interface Module(SFP)
            type-CLP2(321),                     -- 2-Port OC-3/STM-1 CPOS Optical Interface Module(SFP)
            type-ET16(322),                     -- 16-Port Channelized E1/T1 Interface Module
            type-LSB1SRP1NA0(323),              -- Switching and Route Process Unit,12*LPU
            type-LSB1SRP1NA1(324),              -- Switching and Route Process Unit,8*LPU
            type-LSB1SRP1NA2(325),              -- Switching and Route Process Unit,5*LPU
            type-LSB1SRP1NA3(326),              -- Switching and Route Process Unit, Clock module
            type-SR01AHP1GWA(327),              -- 1-Port OC-12c(3c)/STM-4(1) ATM Optical Interface and 4-Port 1000Base-X Ethernet Optical Interface Line Card(WA)
            type-SR01AHP2GWA(328),              -- 2-Port OC-12c(3c)/STM-4(1) ATM Optical Interface and 4-Port 1000Base-X Ethernet Optical Interface Line Card(WA)
            type-SR01CLP1GWA(329),              -- 1-Port OC-3/STM-1 CPOS Optical Interface and 4-Port 1000Base-X Ethernet Optical Interface Line Card(WA)
            type-SR01CLP2GWA(330),              -- 2-Port OC-3/STM-1 CPOS Optical Interface and 4-Port 1000Base-X Ethernet Optical Interface Line Card(WA)
            type-SR01ET16GWA(331),              -- 16-Port Channelized E1/T1 Interface and  4-Port 1000Base-X Ethernet Optical Interface Line Card(WA)
            type-SR01GP12VB (332),              -- 12-Port Gigabit Ethernet Optical Interface Card(VB)
            type-SR01XK1VB(333),                -- 1-Port 10Gigabit Ethernet Optical Interface Card(VB)
            type-SR01XP2VC(334),                -- 2-Port 10GBase-RW Ethernet XFP Optical Interface Line Card(VC)
            type-SR01XP4LVB(335),               -- 4-Port 10GBase-R/W Ethernet XFP Optical Interface Line Speed Card(VB)
            type-SR01SRPUEA(336),               -- Switching and Route Process Unit, Clock Module
            type-LSB1SRP1N4(337),               -- Switching and Route Process Unit, 12*LPU
            type-LSB1SRP1N5(338),               -- Switching and Route Process Unit, 8*LPU
            type-LSB1SRP1N6(339),               -- Switching and Route Process Unit, 5*LPU
            type-LSB1SRP1N7(340),               -- Switching and Route Process Unit, Clock Module
            type-LSB1SRP2N4(341),               -- Switching and Route Process Unit, 12*LPU
            type-LSB1SRP2N5(342),               -- Switching and Route Process Unit, 8*LPU
            type-LSB1SRP2N6(343),               -- Switching and Route Process Unit, 5*LPU
            type-LSB1SRP2N7(344),               -- Switching and Route Process Unit, Clock Module
            type-LSB1SRP1NA4(345),              -- Switching and Route Process Unit, 12*LPU
            type-LSB1SRP1NA5(346),              -- Switching and Route Process Unit, 8*LPU
            type-LSB1SRP1NA6(347),              -- Switching and Route Process Unit, 5*LPU
            type-LSB1SRP1NA7(348),              -- Switching and Route Process Unit, Clock Module
            type-LSB2GV48DA(349),               -- 48-Ports 1000Base-T Ethernet Interface Line Card with POE(DA)
            type-LSB1RGP2GDB(350),              -- 2-Port GE RPR and 8-Port GE Optical Interface Service Card(DB)
            type-LSB1RGP4GDB(351),              -- 4-Port GE RPR and 8-Port GE Optical Interface Service Card(DB)
            type-LSB2GP24DB(352),               -- 24-Port 1000BASE-X  Interface Module(DB),(SFP,LC)
            type-LSB2GP24DC(353),               -- 24-Port 1000BASE-X  Interface Module(DC),(SFP,LC)
            type-LSB2GT24DB(354),               -- 24-Port 10/100/1000BASE-T Interface Module(DB),(RJ45)
            type-LSB2FW8DB (355),               -- 8-Port 1000BASE-X Interface Firewall Service Module(DB),(SFP,LC)
            type-LSB2IPSEC8DB(356),             -- 8-Port 1000BASE-X Interface IPSEC Service Module(DB),(SFP,LC)
            type-LSB2GV48DB(357),               -- 48-Port 10/100/1000BASE-T Interface Module(DB),(PoE,RJ45)
            type-RGP2(358),                     -- 2-Port GE Resilient Packet Ring Interface Module
            type-RGP4(359),                     -- 4-Port GE Resilient Packet Ring Interface Module
            type-SR02FW8VB(360),                -- 8-Port 1000BASE-X Interface Firewall Service Module(VB),(SFP,LC)
            type-SR02IPSEC8VB(361),             -- 8-Port 1000BASE-X Interface IPSEC Service Module(VB),(SFP,LC)
            type-LSB2SRP1N0(362),               -- Switching and Route Process Unit, 12*LPU
            type-LSB2SRP1N1(363),               -- Switching and Route Process Unit, 8*LPU
            type-LSB2SRP1N2(364),               -- Switching and Route Process Unit, 5*LPU
            type-LSB2SRP1N3(365),               -- Switching and Route Process Unit, Clock module
            type-LSB2SRP1N4(366),               -- Switching and Route Process Unit, 12*LPU
            type-LSB2SRP1N5(367),               -- Switching and Route Process Unit, 8*LPU
            type-LSB2SRP1N6(368),               -- Switching and Route Process Unit, 5*LPU
            type-LSB2SRP1N7(369),               -- Switching and Route Process Unit, Clock module
            type-SR02SRPUE (370),               -- Switching and Route Process Unit, Clock module
            type-SR01LN1BQH0(371),              -- Single XG Service Board(BQH)
            type-SR01DXP1L (372),               -- 1-Port 10GBASE-R/W Ethernet Optical Interface Card,(XFP,LC)
            type-SR01DGP10L(373),               -- 10-Port 1000BASE-X Optical Interface Card,(SFP,LC)
            type-SR01DRSP2L(374),               -- 2-Port 2.5G RPR Optical Interface Card,(SFP,LC)
            type-SR01DRUP1L(375),               -- 1-Port 10G RPR Optical Interface Card,(XFP,LC)
            type-SR01DGP20R(376),               -- 20-Port 1000BASE-X Optical Interface Card,(SFP,LC)
            type-SR01DPLP8L(377),               -- 8-Port 155M POS Optical Interface Card,(SFP,LC)
            type-SR01DXP2R (378),               -- 2-Port 10GBASE-R/W Ethernet Optical Interface Card,(XFP,LC)
            type-LSB1FW2A0(379),                -- Gigabit Firewall Card, 4 Gigabit Port for Management
            type-LSB1GP48LDB(380),              -- 48-Port Line Rate Gigabit Ethernet Optical Interface Card(DB)
            type-SR01LN1BNA0(381),              -- Single XG Service Board(BNA)
            type-SR01LN2BQH0(382),              -- Dual XG Service Board(BQH)
            type-SR01LN2BNA0(383),              -- Dual XG Service Board(BNA)
            type-SR01DGT20R(384),               -- 20-Port 10/100/1000BASE-T Electrical Interface Card,(RJ45)
            type-SR01DPSP4L(385),               -- 4-Port 2.5G POS Optical Interface Card(SFP,LC)
            type-SR01DPUP1L(386),               -- 1-Port 10G POS Optical Interface Card,(XFP,LC)
            type-SR01DPL2G6L(387),              -- 2-Port 155M POS Optical Interface(SFP,LC)+6-Port 1000BASE-X Optical Interface Card(SFP,LC)
            type-SR01DPH2G6L(388),              -- 2-Port 622M POS Optical Interface(SFP,LC)+6-Port 1000BASE-X Optical Interface Card(SFP,LC)
            type-SR01DPS2G4L(389),              -- 2-Port 2.5G POS Optical Interface(SFP,LC)+4-Port 1000BASE-X Optical Interface Card(SFP,LC)
            type-SR01DCL1G8L(390),              -- 1-Port 155M CPOS Optical Interface(SFP,LC)+8-Port 1000BASE-X Optical Interface Card(SFP,LC)
            type-SR01DCL2G8L(391),              -- 2-Port 155M CPOS Optical Interface(SFP,LC)+8-Port 1000BASE-X Optical Interface Card(SFP,LC)
            type-SR01DET8G8L(392),              -- 8-Port E1/T1 Electrical Interface(RJ45)+8-Port 1000BASE-X Optical Interface Card(SFP,LC)
            type-SR02SRP2E3(393),               -- Switching and Route Process Unit, Clock Module
            type-SR02SRP1E3(394),               -- Switching and Route Process Unit, Clock Module
            type-SR02SRP1M3(395),               -- Switching and Route Process Unit, Clock Module
            type-SR01DQCP4L(396),               -- 4-Port OC-3c/OC-12c/OC-48c POS/GE Optical Interface Card,(SFP,LC)
            type-SR01DTCP8L(397),               -- 8-Port OC-3c/OC-12c POS/GE Optical Interface Card,(SFP,LC)
            type-LSB1AFC1A0(398),               -- Anomaly Flow Cleaner Board
            type-LSB1SSL1A0(399),               -- SSL VPN High-end Board
            type-IMNAM(400),                    -- Net Analysis Service Processing Board
            type-IMNAT(401),                    -- Network Address Translation Service Processing Board
            type-PICAHP1L(402),                 -- 1-Port OC-12c/STM-4c ATM Optical Interface Card,(SFP,LC)
            type-PICALP4L(403),                 -- 4-Port OC-3c/STM-1c ATM Optical Interface Card,(SFP,LC)
            type-PICCHP4L(404),                 -- 4-Port 622M CPOS Optical Interface Card(SFP,LC)
            type-PICCHS1G4L(405),               -- 1-Port 622M CPOS Optical Interface(Channelized to E3/T3)+4-Port 1000BASE-X Optical Interface Card(SFP,LC)
            type-PICCLS4G4L(406),               -- 4-Port 155M CPOS Optical Interface(Channelized to E3/T3)+4-Port 1000BASE-X Optical Interface Card(SFP,LC)
            type-PICCSP1L(407),                 -- 1-Port 2.5G CPOS Optical Interface Card(SFP,LC)
            type-LSB1ACG1A0(408),               -- Application Control Gateway Board
            type-LST1MRPNC1(409),               -- Management and Route Process Unit
            type-LST1SF18B1(410),               -- Switch Fabric Card
            type-LST1SF08B1(411),               -- Switch Fabric Card
            type-LST1GT48LEC1(412),             -- 48-Port 10/100/1000BASE-T Interface Module(LEC),(RJ45)
            type-LST1GP48LEC1(413),             -- 48-Port 1000BASE-X Interface Module (LEC),(SFP,LC)
            type-LST1XP4LEC1(414),              -- 4-Port 10GBASE-R/W Interface Module (LEC),(XFP,LC)
            type-LST1XP8LEC1(415),              -- 8-Port 10GBASE-R/W Interface Module (LEC),(XFP,LC)
            type-LSR1SRP2B1(416),               -- Switching and Route Process Unit
            type-LSR1SRP2C1(417),               -- Switching and Route Process Unit
            type-LSR1SRP2B2(418),               -- Switching and Route Process Unit
            type-LSR1SRP2C2(419),               -- Switching and Route Process Unit
            type-LSR1GT24LEC1(420),             -- 16-Port 10/100/1000BASE-T Interface and 8-port 1000BASE-T/1000BASE-X Combo Interface Service Card(LEC)
            type-LSR1GP24LEB1(421),             -- 16-Port 1000BASE-X Interface and 8-port 1000BASE-T/1000BASE-X Combo Interface Service Card(LEB)
            type-LSR1GP24LEC1(422),             -- 16-Port 1000BASE-X Interface and 8-port 1000BASE-T/1000BASE-X Combo Interface Service Card(LEC)
            type-LSR1GT48LEB1(423),             -- 48-Port 10/100/1000BASE-T Interface Module(LEB),(RJ45)
            type-LSR1GT48LEC1(424),             -- 48-Port 10/100/1000BASE-T Interface Module(LEC),(RJ45)
            type-LSR1GP48LEB1(425),             -- 48-Port 1000BASE-X Interface Module(LEB),(SFP,LC)
            type-LSR1GP48LEC1(426),             -- 48-Port 1000BASE-X Interface Module(LEC),(SFP,LC)
            type-LSR2GV48REB1(427),             -- 48-Port 10/100/1000BASE-T Interface Module(REB),(PoE,RJ45)
            type-LSR1XP2LEB1(428),              -- 2-Port 10GBase-R/W Interface Module (LEB),(XFP,LC)
            type-LSR1XP2LEC1(429),              -- 2-Port 10GBase-R/W Interface Module (LEC),(XFP,LC)
            type-LSR1XP4LEB1(430),              -- 4-Port 10GBase-R/W Interface Module (LEB),(XFP,LC)
            type-LSR1XP4LEC1(431),              -- 4-Port 10GBase-R/W Interface Module (LEC),(XFP,LC)
            type-IMFW(432),                     -- Firewall Service Processing Board
            type-LSB1LB1A0(433),                -- Load Balance Board
            type-LSB1IPS1A0(434),               -- Gigabit IPS Card
            type-LST1GT48LEB1(435),             -- 48-Port 10/100/1000BASE-T Interface Module(LEB),(RJ45)
            type-LST1GP48LEB1(436),             -- 48-Port 1000BASE-X Interface Module (LEB),(SFP,LC)
            type-LST1XP4LEB1(437),              -- 4-Port 10GBASE-R/W Interface Module (LEB),(XFP,LC)
            type-LST1XP8LEB1(438),              -- 8-Port 10GBASE-R/W Interface Module (LEB),(XFP,LC)
            type-LST1XP32REB1(439),             -- 32-Port 10GBASE-R Interface Module (REB),(SFP+,LC)
            type-LST1XP32REC1(440),             -- 32-Port 10GBASE-R Interface Module (REC),(SFP+,LC)
            type-LSR1FW2A1(441),                -- Firewall Service Module
            type-LSR1SSL1A1(442),               -- SSL VPN Service Module
            type-SR01DET32G2L(443),             -- 32-Port E1/T1 75ohm Electrical Interface(DB56 Female Socket)+2-Port 1000BASE-X Optical Interface Card(SFP,LC)
            type-LSR1GP24LEF1(444),             -- 16-Port 1000BASE-X Interface and 8-port 1000BASE-T/1000BASE-X Combo Interface Service Card(LEF)
            type-LSR1XP4LEF1(445),              -- 4-Port 10GBASE-R/W Interface Module (LEF),(XFP,LC)
            type-LSR1LB1A1(446),                -- Load Balance Module
            type-LSR1NSM1A1(447),               -- NetStream Module
            type-LSR1ACG1A1(448),               -- Application Control Gateway Service Module
            type-LSR1IPS1A1(449),               -- Intrusion Protection System Service Module
            type-LSR2GP24LEB1(450),             -- 16-Port 1000BASE-X Interface and 8-port 1000BASE-T/1000BASE-X Combo Interface Service Card(LEB)
            type-LSR2GT24LEB1(451),             -- 16-Port 10/100/1000BASE-T Interface and 8-port 1000BASE-T/1000BASE-X Combo Interface Service Card(LEB)
            type-LSR2GT48LEB1(452),             -- 48-Port 10/100/1000BASE-T Interface Module(LEB),(RJ45)
            type-SPC-GP24L(453),                -- 24-Port 1000BASE-X Interface Service Card,(SFP,LC)
            type-SPC-GT48L(454),                -- 48-Port 10/100/1000BASE-T Interface Module,(RJ45)
            type-SPC-GP48L(455),                -- 48-Port 1000BASE-X Interface Module,(SFP,LC)
            type-SPC-XP2L(456),                 -- 2-Port 10GBASE-R/W Interface Service Card,(XFP,LC)
            type-SPC-XP4L(457),                 -- 4-Port 10GBase-R/W Interface Module,(XFP,LC)
            type-SR06SRP2E3(458),               -- SDI,Routing Switch Processing Board
            type-SPE-2010-E(459),               -- SDI,Single XG Service Board
            type-SPE-2020-E(460),               -- SDI,Dual XG Service Board
            type-SPC-XP4L-S-SDI(461),           -- SDI 4-Port 10GBase-R/W Interface Module,(XFP,LC)
            type-SPC-GT48L-SDI(462),            -- SDI 48-Port 10/100/1000BASE-T Interface Module,(RJ45)
            type-SPC-GP48L-S-SDI(463),          -- SDI 48-Port 1000BASE-X Interface Module,(SFP,LC)
            type-SR02OPMA0(464),                -- Single Mode 1310&1550nm Optical Protect Board(LC)
            type-LSR1XP16REB1(465),             -- 16-Port 10GBASE-R Interface Module (REB),(SFP+,LC)
            type-LSR1GP48LEF1(466),             -- 48-Port 1000BASE-X Interface Module (LEF),(SFP,LC)
            type-LST1GP48LEF1(467),             -- 48-Port 1000BASE-X Interface Module (LEF),(SFP,LC)
            type-LST1XP8LEF1(468),              -- 8-Port 10GBASE-R/W Interface Module (LEF),(XFP,LC)
            type-SPE-1010-II(469),              -- Single XG Service Board-II
            type-SPE-1010-E-II(470),            -- Enhanced Single XG Service Board-II
            type-SPE-1020-II(471),              -- Double XG Service Board-II
            type-SPE-1020-E-II(472),            -- Enhanced Double XG Service Board-II
            type-LST1FW2A1(473),                -- Firewall Board (LEC)
            type-LST1NSM1A1(474),               -- NetStream Service Board (LEC)
            type-LST1LB1A1(475),                -- Load Balancing Board (LEC)
            type-LST1ACG1A1(476),               -- Application Control Gateway Board Module (LEC)
            type-LST1IPS1A1(477),               -- Gigabit Intrusion Prevention System Module
            type-LSR1DRUP1L1(478),              -- 1-Port OC-192c/STM-64c RPR Optical Interface Card,(XFP,LC)
            type-LSR1DPUP1L1(479),              -- 1-Port OC-192c/STM-64c POS Optical Interface Card,(XFP,LC)
            type-LSR1DPSP4L1(480),              -- 4-Port OC-48c/STM-16c POS Optical Interface Card,(SFP,LC)
            type-LSR1DTCP8L1(481),              -- 8-Port OC-3c/OC-12c POS/GE Optical Interface Card,(SFP,LC)
            type-LSR1DXP1L1(482),               -- 1-Port 10GBASE-R/W Ethernet Optical Interface Card,(XPF,LC)
            type-LSR1DGP10L1(483),              -- 10-Port 1000BASE-X Optical Interface Card,(SFP,LC)
            type-LSR1LN1BNL1(484),              -- Single Service Processing Board
            type-LSR1LN2BL1(485),               -- Dual Serivice Processing Board
            type-LSR1SRP2D1(486),               -- Switching and Route Process Unit With Clock
            type-IM-NAT-II(487),                -- Network Address Translation Service Processing Board,II
            type-IM-NAM-II(488),                -- Net Analysis Service Processing Board,II
            type-CR-MRP-I(489),                 -- Management and Route Unit With OAM Module and Clock Module
            type-CR-SF18C(490),                 -- Switch Fabric Card
            type-CR-SF08C(491),                 -- Switch Fabric Card
            type-CR-SPC-XP8LEF(492),            -- 8-Port 10GBASE-R/W Interface Module,(XFP,LC)
            type-CR-SPC-XP4LEF(493),            -- 4-Port 10GBASE-R/W Interface Module,(XFP,LC)
            type-CR-SPC-GP48LEF(494),           -- 48-Port 1000BASE-X Interface Module,(SFP,LC)
            type-CR-SPC-GT48LEF(495),           -- 48-Port 10/100/1000BASE-T Interface Module
            type-CR-SPE-3020-E(496),            -- Double XG Service Board (Enhanced)
            type-CR-SPC-PUP4L-E(497),           -- 4-Port 10G POS Optical Interface Module,(XFP,LC)
            type-LST1SF08C1(498),               -- Switch Fabric Card
            type-LST1SF18C1(499),               -- Switch Fabric Card

--
-- 500 to 699 reserved for secondary switchs part I
--
            type-LS81GP16TM(500),               -- 12-port 1000BASE-X SFP Interface and 4-port 1000BASE-T/1000BASE-X Combo Interface Metro Switch and Route Processing Board
            type-LS81VP4C(501),                 -- 4-port 1000BASE-X SFP Interface Virtual Daughter Card
            type-LS8M1PT8P0(502),               -- 8-Port 1000BASE-PX Optical Line Interface Board, SFP Req
            type-LS8M1PT8GB0(503),              -- 8-Port 1000BASE-PX20 Gigabit Passive Optical Line Interface Board B(20km, SFF), SC Connector
            type-LS8M1PT4GB0(504),              -- 4-Port 1000BASE-PX20 Gigabit Passive Optical Line Interface Board B(20km, SFF), SC Connector
            type-LS81GP2R(505),                 -- 2-Port 1000M Ethernet Optical Interface RPR Board
            type-LS81GP4R(506),                 -- 4-Port 1000M Ethernet Optical Interface RPR Board
            type-LS81IPSECA(507),               -- IPSec Service Board
            type-LS81FWA(508),                  -- Firewall Service Board
            type-LS82VSNP(509),                 -- Versatile Network Processing Service Module (PBR/NAT/NetStream) with 12-port 1000BASE-X SFP, XGBUS Uplink
            type-LSQ1GV48SA(510),               -- 48-Port 1000Base-T Gigabit Ethernet Interface Board(RJ45)
            type-LSQ1SRPB(511),                 -- Salience VI
            type-LSQ1SRP2XB(512),               -- Salience VI-10GE
            type-LSQ1SRP1CB(513),               -- Salience VI-Turbo
            type-LSQ1FV48SA(514),               -- 48-Port 100M Ethernet Electrical Interface Switch Unit(RJ45)
            type-LSD1MPUA(515),                 -- Main Control Unit
            type-LSD1GP20A0(516),               -- 16-port 1000BASE-X SFP Interface and 4-port 1000BASE-T/1000BASE-X Combo Interface Line Card
            type-LSD1GP20TA0(517),              -- 16-port 1000BASE-X SFP Interface and 4-port 1000BASE-T/1000BASE-X Combo Interface and 16 1000BASE-T Interface Line Card
            type-LSD1GP36A0(518),               -- 32-port 1000BASE-X SFP Interface and 4-port 1000BASE-T/1000BASE-X Combo Interface Line Card
            type-LSD1GP20XA0(519),              -- 16-port 1000BASE-X SFP Interface and 4-port 1000BASE-T/1000BASE-X Combo Interface and 2-port 10GBASE-X XFP Interface Line Card
            type-LSD1GP20EA0(520),              -- 16-port 1000BASE-X SFP Interface and 4-port 1000BASE-T/1000BASE-X Combo Interface and 2-port GE RPR Interface Line Card
            type-LSD1GP20RA0(521),              -- 16-port 1000BASE-X SFP Interface and 4-port 1000BASE-T/1000BASE-X Combo Interface and 2-port OC48 RPR Interface Line Card
            type-LSD1GP16A0(522),               -- 16-port 1000BASE-X SFP Ethernet Interface SubCard
            type-LSD1GT16A0(523),               -- 16-port 1000BASE-T Ethernet Interface SubCard
            type-LSD1XP2A0(524),                -- 2-port 10GBASE-X XFP Ethernet Interface SubCard
            type-LSD1EP2A0(525),                -- 2-port 1000BASE-T Ethernet RPR Interface SubCard
            type-LSD1RP2A0(526),                -- 2-port OC48 RPR Interface SubCard
            type-LSQ1GV48SC(527),               -- 48-Port 1000Base-T Gigabit Ethernet Interface Board(RJ45)-POE
            type-LSQ1FP48SA(528),               -- 48 Port 100M Ethernet Optical Interface Board(SFP,LC)
            type-LSQ1GP24SC(529),               -- 24 Port 1000BASE-X Ethernet Optical Interface Board(SFP,LC)
            type-LSQ1GT24SC(530),               -- 24-Port 1000BASE-T Ethernet Interface Board (RJ45)
            type-LSQ1TGX2SC(531),               -- 2-Port 10GBASE Ethernet Optical Interface Board(XFP,LC)
            type-LSQ1GP12EA(532),               -- 12-Port 1000BASE-X Ethernet Optical Interface Board(SFP,LC)
            type-LSQ1TGX1EA(533),               -- 1-Port 10GBASE Ethernet Optical Interface Module(XFP,LC)
            type-LSQ1P24XGSC(534),              -- 24-Port 1000BASE-X Gigabit Ethernet Optical Interface(SFP,LC)+2-Port 10GBASE Ethernet Optical Interface Board(XFP,LC)
            type-LSQ1T24XGSC(535),              -- 24-Port 1000BASE-T Gigabit Ethernet Interface(RJ45)+2-Port 10GBASE Ethernet Optical Interface Board(XFP,LC)
            type-LS81TGX1B(536),                -- 1 Port 10GBase-R Ethernet Interface Board(XENPAK,SC)
            type-LSQ1PT4PSC0(537),              -- 4-Port 1000Base-PX Optical Line Terminal(EPON OLT SFP,SC)+8-Port 1000BASE-X Optical Interface Board(SFP,LC)
            type-LS81SRPG13(538),               -- Salience V, Switch and Route Processing Board
            type-LS81SRPG14(539),               -- Salience V Edge
            type-LS81SRPG15(540),               -- Salience V Plus
            type-LSQ1GP48SC0(541),              -- 48-Port 1000BASE Ethernet Optical Interface Board(SFP,LC)
            type-LSQ1GP12SC0(542),              -- 12-Port 1000BASE-X Ethernet Optical Interface Board(SFP,LC)
            type-LSD1SRPA0(543),                -- Salience VIII 160
            type-LSD1SRPB0(544),                -- Salience VIII 480
            type-LSD1SRPC0(545),                -- Salience VIII 800
            type-LSD1GT16PES0(546),             -- 16-Port 10/100/1000BASE-T and 8-Port 100/1000BASE-X SFP Interface Card
            type-LSD1GP24ES0(547),              -- 24-Port 1000BASE-X Ethernet SFP Interface Card
            type-LSD1GT24XES0(548),             -- 24-Port 10/100/1000BASE-T and 2-port 10GBASE-X Ethernet XFP Optical Interface Card
            type-LSD1GP24XES0(549),             -- 24-Port 1000BASE-X Ethernet SFP interface and 2-port 10GBASE-X Ethernet XFP Optical Interface Card
            type-LSD1XP2ES0(550),               -- 2-Port 10GBASE-X Ethernet XFP Optical Interface Card
            type-LSD1GP48ES0(551),              -- 48-Port 1000BASE-X Ethernet SFP Interface Card
            type-LSQ1MPUA0(552),                -- Master Process Board
            type-LSQ1MPUA1(553),                -- Master Process Unit
            type-LSQ1FWBSC0(554),               -- Gigabit Firewall Card, 4 Gigabit Port for Management
            type-LSQ1PT8PSC0(555),              -- 8-Port 1000Base-PX Optical Line Terminal(EPON OLT SFP,SC)+8-Port 1000BASE-X Optical Interface Board(SFP,LC)
            type-LSQ1PT16PSC0(556),             -- 16-Port 1000Base-PX Optical Line Terminal(EPON OLT SFP,SC)+8-Port 1000BASE-X Optical Interface Board(SFP,LC)
            type-SA11MPUA0(557),                -- SmartEngine I-Lite
            type-SA11MPUB0(558),                -- SmartEngine I
            type-LSQ1AFCBSC0(559),              -- Anomaly Flow Cleaner Board
            type-LSQ1MPUB0(560),                -- Salience VI-Lite
            type-LSQ1MPUB1(561),                -- Salience VI-Lite
            type-LSQ1PT4PSC1(562),              -- 4-Port 1000Base-PX Optical Line Terminal(EPON OLT SFP,SC)+8-Port 1000BASE-X Optical Interface Board(SFP,LC)
            type-LSQ1PT8PSC1(563),              -- 8-Port 1000Base-PX Optical Line Terminal(EPON OLT SFP,SC)+8-Port 1000BASE-X Optical Interface Board(SFP,LC)
            type-LSQ1PT16PSC1(564),             -- 16-Port 1000Base-PX Optical Line Terminal(EPON OLT SFP,SC)+8-Port 1000BASE-X Optical Interface Board(SFP,LC)
            type-LSQ1FP48USA0(565),             -- 48-Port 100M Ethernet Optical Interface Switch Unit(SFP,LC)
            type-LSQ1FP48USA1(566),             -- 48-Port 100M Ethernet Optical Interface Switch Unit(SFP,LC)
            type-LSQ1FV48USA0(567),             -- 48-Port 100M Ethernet Electrical Interface Switch Unit(RJ45),PoE
            type-LSQ1FV48USA1(568),             -- 48-Port 100M Ethernet Electrical Interface Switch Unit(RJ45),PoE
            type-LSQ1SRPD0(569),                -- Switch and Route Processing Unit, Salience VI-Plus
            type-LSQ1CGP24TSC0(570),            -- Switching and Routing Processing Unit with 24 1000BASE-X Gigabit Ethernet Optical Ports,including 8 Combo Ports,SFP Req.
            type-LSQ1GP24TSC0(571),             -- 16-Port 1000BASE-X Gigabit Ethernet Optical(SFP,LC) And 8-Port 10/100/1000BASE-T RJ45/1000BASE-X SFP Combo Interface Board
            type-LSQ1ACGASC0(572),              -- Application Control Gateway Board
            type-LSD1XP1ES0(573),               -- 1-Port 10GBASE-X Ethernet XFP Optical Interface Card
            type-LSD1GP12ES0(574),              -- 12-Port 1000BASE-X Ethernet SFP Interface Card
            type-LSQ1SRP12GB0(575),             -- Switch And Route Processing Unit with 12 1000BASE Ethernet Optical Interfaces(SFP,LC),Salience VI-GE
            type-LSQ1GV40PSC0(576),             -- 40-Port 10/100/1000BASE-T Electrical(RJ45) And 8-Port 1000BASE-X Optical Ethernet Interface Board(SFP,LC),PoE
            type-LSQ1FWBSC1(577),               -- Firewall Board
            type-LSQ1NSMSC0(578),               -- NetStream Board
            type-LSQ1NSMSC1(579),               -- NetStream Board
            type-LSQ1AFDBSC0(580),              -- Anomaly Flow Detector Board
            type-LS81MPUB(581),                 -- Salience IV
            type-LS81FP48XL(582),               -- 48-Port 100M Ethernet Optical Interface Module,(SFP,LC)
            type-LS81FT48XL(583),               -- 48-Port 10/100M Ethernet Electrical Interface Module(RJ45)
            type-LS81GP12XL(584),               -- 12-Port 1000/100M Ethernet Optical Interface Module(SFP,LC)
            type-LS81GP24XL(585),               -- 24-Port 1000/100M Ethernet Optical Interface Module(SFP,LC)
            type-LS81GP48XL(586),               -- 48-Port 1000/100M Ethernet Optical Interface Module(SFP,LC)
            type-LS81GT24XL(587),               -- 24-Port 10/100/1000M Ethernet Electrical Interface Module(RJ45)
            type-LS81GT48XL(588),               -- 48-Port 10/100/1000M Ethernet Electrical Interface Module(RJ45)
            type-LS81TGX2XL(589),               -- 2-Port 10GBASE Ethernet Optical Interface Module(XFP,LC)
            type-LSQ1GV48SD0(590),              -- 48-Port 1000Base-T Gigabit Ethernet Interface Board(RJ45),PoE
            type-LSQ1GP48EB0(591),              -- 48-Port Enhanced 1000BASE-X Ethernet Optical Interface Board(SFP,LC)
            type-LSQ1IPSSC0(592),               -- Gigabit IPS Card
            type-LSQ1GV48SD1(593),              -- 48-Port 1000Base-T Gigabit Ethernet Interface Board(RJ45),PoE
            type-LSQ1GP48SD0(594),              -- 48-Port 1000BASE-X Gigabit Ethernet Optical Interface(SFP,LC) Interface Board
            type-LSQ1GP48SD1(595),              -- 48-Port 1000BASE-X Gigabit Ethernet Optical Interface(SFP,LC) Interface Board
            type-LSQ1SRPA0(596),                -- Salience VI-Smart
            type-LSQ1SRPA1(597),                -- Salience VI-Smart
            type-LSQ2FP48SA0(598),              -- 48 Port 100M Ethernet Optical Interface Board(SFP,LC)
            type-LSQ2FP48SA1(599),              -- 48 Port 100M Ethernet Optical Interface Board(SFP,LC)
            type-LSQ2FT48SA0(600),              -- 48-Port 100M Ethernet Electrical Interface Switch Unit(RJ45)
            type-LSQ2FT48SA1(601),              -- 48-Port 100M Ethernet Electrical Interface Switch Unit(RJ45)
            type-LSQ1GV24PSC0(602),             -- 24-Port 10/100/1000BASE-T Electrical(RJ45) Interface Board,including 4 Combo Ports,SFP Req,PoE,No Spell
            type-LSQ1GV24PSC1(603),             -- 24-Port 10/100/1000BASE-T Electrical(RJ45) Interface Board,including 4 Combo Ports,SFP Req,PoE,No Spell
            type-LSQ1CGV24PSC0(604),            -- Switching and Routing Processing Unit with 24 10/100/1000BASE-T Electrical Ports(RJ45),including 4 Combo Ports,SFP Req,PoE,No Spell
            type-LSQ1CGV24PSC1(605),            -- Switching and Routing Processing Unit with 24 10/100/1000BASE-T Electrical Ports(RJ45),including 4 Combo Ports,SFP Req,PoE,No Spell
            type-LSQ1GP24TEB0(606),             -- 16-Port 1000BASE-X Gigabit Ethernet Optical Interface(SFP,LC)+8-Port Combo Interface Board
            type-LSQ1GP24TEB1(607),             -- 16-Port 1000BASE-X Gigabit Ethernet Optical Interface(SFP,LC)+8-Port Combo Interface Board
            type-LSQ1GP24TSD0(608),             -- 16-Port 1000BASE-X Gigabit Ethernet Optical Interface(SFP,LC)+8-Port Combo Interface Board
            type-LSQ1GP24TSD1(609),             -- 16-Port 1000BASE-X Gigabit Ethernet Optical Interface(SFP,LC)+8-Port Combo Interface Board
            type-LSQ1GP24TXSD0(610),            -- 16-Port GE Optical Interface(SFP,LC)+8-Port Combo Interface+2-Port 10GE Optical Interface Board(XFP,LC)
            type-LSQ1GP24TXSD1(611),            -- 16-Port GE Optical Interface(SFP,LC)+8-Port Combo Interface+2-Port 10GE Optical Interface Board(XFP,LC)
            type-LSQ1TGX2EB0(612),              -- 2-Port 10GBASE Ethernet Optical Interface Board(XFP,LC)
            type-LSQ1TGX2EB1(613),              -- 2-Port 10GBASE Ethernet Optical Interface Board(XFP,LC)
            type-LSQ1TGX2SD0(614),              -- 2-Port 10GBASE Ethernet Optical Interface Board(XFP,LC)
            type-LSQ1TGX2SD1(615),              -- 2-Port 10GBASE Ethernet Optical Interface Board(XFP,LC)
            type-LSQ1TGX4SD0(616),              -- 4-Port 10GBASE Ethernet Optical Interface Board(XFP,LC)
            type-LSQ1TGX4SD1(617),              -- 4-Port 10GBASE Ethernet Optical Interface Board(XFP,LC)
            type-LSQ1TGX8SD0(618),              -- 8-Port 10GBASE Ethernet Optical Interface Board(XFP,LC)
            type-LSQ1TGX8SD1(619),              -- 8-Port 10GBASE Ethernet Optical Interface Board(XFP,LC)
            type-LSQ1GP48EB1(620),              -- 48-Port Enhanced 1000BASE-X Ethernet Optical Interface Board(SFP,LC)
            type-LSQ1TGX4EB0(621),              -- 4-Port 10GBASE Ethernet Optical Interface Board(XFP,LC)
            type-LSQ1TGX4EB1(622),              -- 4-Port 10GBASE Ethernet Optical Interface Board(XFP,LC)
            type-LSQ1GP12SC3(623),              -- 12-Port 1000BASE-X Ethernet Optical Interface Board(SFP,LC)
            type-LSQ1GP24TSC3(624),             -- 16-Port 1000BASE-X Gigabit Ethernet Optical(SFP,LC) And 8-Port 10/100/1000BASE-T RJ45/1000BASE-X SFP Combo Interface Board
            type-LSQ1GP48SC3(625),              -- 48-Port 1000BASE Ethernet Optical Interface Board(SFP,LC)
            type-LSQ1GV48SC3(626),              -- 48-Port 1000Base-T Gigabit Ethernet Interface Board(RJ45),PoE
            type-LSQ1MPUA3(627),                -- Master Process Board
            type-LSQ1SRP1CB3(628),              -- Salience VI-Turbo
            type-LSQ1SRPA3(629),                -- Salience VI-Smart
            type-LSQ2FP48SA3(630),              -- 48 Port 100M Ethernet Optical Interface Board(SFP,LC)
            type-LSQ2FT48SA3(631),              -- 48-Port 100M Ethernet Electrical Interface Switch Unit(RJ45)
            type-LSQ1MPUB3(632),                -- Salience VI-Lite
            type-LSQ1CGP24TSC3(633),            -- Switching and Routing Processing Unit with 24 1000BASE-X Gigabit Ethernet Optical Ports,including 8 Combo Ports,SFP Req.
            type-LSQ1MPUB4(634),                -- Salience VI-Lite
            type-LSQ1SRPD4(635),                -- Salience VI-Plus
            type-LSQ1SSLSC0(636),               -- SSL VPN Service Board(B)
            type-LSQ1LBSC0(637),                -- Gigabit Load Balancing Card
            type-LSQ1NAT24SC0(638),             -- NAT/NetStream-Supported Line Processing Unit with 24 10/100/1000BASE-T Electrical Ports(RJ45),including Combo Ports,Upgradeable to PoE
            type-LSQ1SRP12GB4(639),             -- Salience VI-GE
            type-LSQ1TGS8SC0(640),              -- 8-Port 10GBASE Ethernet SFP+ Optical Interface Board
            type-LSQ3PT4PSC0(641),              -- 4-Port 1000Base-PX Optical Line Terminal(EPON OLT SFP,SC)+8-Port 1000BASE-X Optical Interface Board(SFP,LC)
            type-EWPXM2MPUB0(642),              -- Salience VI-Lite
            type-EWPXM2SRP12GB0(643),           -- Salience VI-GE
            type-EWPXM2SRPD0(644),              -- Salience VI-Plus
            type-EWPXM2GP24TSD0(645),           -- 16-Port 1000BASE-X Ethernet Optical Interface(SFP Req.)+8-Port Combo Interface Module
            type-EWPXM2GP24TXSD0(646),          -- 16-Port 1000BASE-X Ethernet Optical Interface(SFP Req.)+8-Port Combo Interface+2-Port 10GE Optical Interface(XFP Req.) Module
            type-EWPXM2TGX4SD0(647),            -- 4-Port 10GBASE Ethernet Optical Interface Module,XFP Req
            type-EWPXM2GP48SD0(648),            -- 48-Port 1000BASE-X Gigabit Ethernet Optical Interface Module,SFP Req
            type-EWPXM2GP24TSC0(649),           -- 24-Port 1000BASE-X/100BASE-FX Optical  Interface Module,including 8 Combo Ports,SFP Req
            type-EWPXM2TGX2SC0(650),            -- 2-Port 10GBASE Ethernet Optical Interface Module,XFP Req
            type-EWPXM2GP48SC0(651),            -- 48-Port 1000BASE-X/100BASE-FX Ethernet Optical Interface Module,SFP Req
            type-LS7500-GP48-SC(652),           -- 48-Port 1000BASE-X/100BASE-FX Ethernet Optical Interface Module(SFP,LC)
            type-LS7500-GP48-SD(653),           -- 48-Port 1000BASE-X Gigabit Ethernet Optical Interface Module(SFP,LC)
            type-LS7500-GT48-SC(654),           -- 48-Port 10/100/1000BASE-TX Ethernet Interface Module(RJ45)
            type-LS7500-GT48-SD(655),           -- 48-Port 10/100/1000BASE-T Ethernet Interface Module(RJ45)
            type-LS7500-SRPG1(656),             -- Main Control Unit
            type-LS7500-SRPG2(657),             -- Salience VI-Lite
            type-LS7500-XP4-SD(658),            -- 4-Port 10GBASE Ethernet Optical Interface Module(XFP,LC)
            type-LS7500-XP8-SD(659),            -- 8-Port 10GBASE Ethernet Optical Interface Module(XFP,LC)
            type-LSQ4PT4PSC0(660),              -- 4-Port 1000Base-PX Optical Line Terminal(EPON OLT SFP,SC)+8-Port 1000BASE-X Optical Interface Board(SFP,LC)
            type-LSQ4PT8PSC0(661),              -- 8-Port 1000Base-PX Optical Line Terminal(EPON OLT SFP,SC)+8-Port 1000BASE-X Optical Interface Board(SFP,LC)
            type-LSQ4PT16PSC0(662),             -- 16-Port 1000Base-PX Optical Line Terminal(EPON OLT SFP,SC)+8-Port 1000BASE-X Optical Interface Board(SFP,LC)
            type-LSQ1GP24TSA0(663),             -- 16-Port 1000BASE-X Gigabit Ethernet Optical(SFP,LC) And 8-Port 10/100/1000BASE-T RJ45/1000BASE-X SFP Combo Interface Board
            type-LSQ1GV24PSA0(664),             -- 24-Port 10/100/1000BASE-T Electrical(RJ45) Interface Board,including 4 Combo Ports,SFP Req,Upgradeable to PoE
            type-LSQ1SRPD3(665),                -- Salience VI-Plus
            type-LSQ1SUPA0(666),                -- Supervisor Engine Board
            type-LSU1FAB04A0(667),              -- Switch Fabric Board
            type-LSU1FAB08A0(668),              -- Switch Fabric Board
            type-LSU1TGS8EA0(669),              -- 8-Port 10GBASE Ethernet SFP+ Optical Interface Board(EA)
            type-LSU1TGS8EB0(670),              -- 8-Port 10GBASE Ethernet SFP+ Optical Interface Board
            type-LSU1TGS8SE0(671),              -- 8-Port 10GBASE Ethernet SFP+ Optical Interface Board(SE)
            type-LSUTGS16SC0(672),              -- 16-Port 10GBASE Ethernet SFP+ Optical Interface Board
            type-LSU1SUPA0(673),                -- Supervisor Engine Board
            type-LSU1GP24TXEA0(674),            -- 16-Port 1000BASE-X Optical Interface(SFP,LC)+8-Port Combo Interface+2-Port 10GE Optical Interface Board(XFP,LC)(EA)
            type-LSU1GP24TXEB0(675),            -- 16-Port 1000BASE-X Optical Interface(SFP,LC)+8-Port Combo Interface+2-Port 10GE Optical Interface Board(XFP,LC)(EB)
            type-LSU1GP24TXSE0(676),            -- 16-Port 1000BASE-X Optical Interface(SFP,LC)+8-Port Combo Interface+2-Port 10GE Optical Interface Board(XFP,LC)(SE)
            type-LSU1GP48EA0(677),              -- 48-Port 1000BASE-X Gigabit Ethernet Optical Interface(SFP,LC) Interface Board(EA)
            type-LSU1GP48EB0(678),              -- 48-Port Enhanced 1000BASE-X Ethernet Optical Interface Board(SFP,LC)(EB)
            type-LSU1GP48SE0(679),              -- 48-Port 1000BASE Ethernet Optical Interface Board(SFP,LC)(SE)
            type-LSU1GT48EA0(680),              -- 48-Port 1000Base-T Gigabit Ethernet Interface Board(RJ45)(EA)
            type-LSU1GT48SE0(681),              -- 48-Port 1000Base-T Gigabit Ethernet Interface Board(RJ45)(SE)
            type-LSU1TGX4EA0(682),              -- 4-Port 10GBASE Ethernet Optical Interface Board(XFP,LC)(EA)
            type-LSU1TGX4EB0(683),              -- 4-Port 10GBASE Ethernet Optical Interface Board(XFP,LC)(EB)
            type-LSU1TGX4SE0(684),              -- 4-Port 10GBASE Ethernet Optical Interface Board(XFP,LC)(SE)
            type-LSQ1FAB08A0(685),              -- Switching Fabric Board
            type-EWPX2WCMD0(686),               -- Access Controller Card
            type-LSQ1WCMD0(687),                -- Access Controller Card
            type-LSQ1IAGSC0(688),               -- Wireless&IAG Service Card
            type-LSU1GP24TSE0(689),             -- 16-Port 1000BASE-X Optical Interface(SFP,LC)+8-Port Combo Interface Board(SE)
            type-LSQ1TGS16SC0(690),             -- 16-Port 10GBASE Ethernet SFP+ Optical Interface Board
            type-EWPX2TGS16SC0(691),            -- 16-Port 10GBASE Ethernet SFP+ Optical Interface Board
            type-LSQ1SUPA3(692),                -- Supervisor Engine Board
            type-LSQ1FAB04A3(693),              -- 320G Switch Fabric Board
            type-LSQ1FAB08A3(694),              -- 640G Switch Fabric Board
            type-LSQ1GT48SC0(695),              -- 48-Port 1000Base-T Gigabit Ethernet Interface Board(RJ45)
            type-LSR2SRP2C1(696),               -- Management and Route Process Unit
            type-LSR2SRP2C2(697),               -- Management and Route Process Unit

--
-- 700 to 799 reserved for primary switchs
--
            type-1000BASE-X-COMBO(701),         -- Single port 10/100/1000BASE-T/1000BASE-X Combo Interface Board
            type-EPON-1000M(702),               -- Optical Network Unit Interface Board
            type-1000BASE-FIXED-2SFP-T-2RJ45(703),         -- 2 port 10/100/1000BASE-T and 2 port 1000BASE-X Interface Board
            type-100M-1550-BIDI(704),           -- 100BASE-X BIDI Interface Board,Tx 1550nm, Rx 1310nm
            type-100M-1310-BIDI(705),           -- 100BASE-X BIDI reverse Interface Board,Tx 1310nm, Rx 1550nm
            type-1000BASE-FIXED-4RJ45-4SFP-COMBO(706),     -- 4 port 10/100/1000BASE-T and 4 port 1000BASE-X COMBO Interface Board
            type-LSH1PK2T(707),                 -- OSM Interface Board
            type-LSPM2GP2P(708),                -- 2-Port 1000BASE-X SFP Module
            type-LSWM1GT16P(709),               -- 16-Port 10/100/1000BASE-T Ethernet Electrical Interface Module
            type-LSWM1GP16P(710),               -- 16-Port 100/1000BASE-X Ethernet Optical Interface Module
            type-LSWM1XP2P(711),                -- 2-Port 10G Ethernet XFP Optical Interface Module
            type-LSWM1XP4P(712),                -- 4-Port 10G Ethernet XFP Optical Interface Module
            type-LSWM1SP2P(713),                -- 2-Port 10G Ethernet SFP PLUS Optical Interface Module
            type-LSWM1SP4P(714),                -- 4-Port 10G Ethernet SFP PLUS Optical Interface Module
            type-LSWM148POEM(715),              -- 48 Port Mid Power PoE Module
            type-LSWM1FW10(716),                -- RMI CPU XLR 732, with Firewall software
            type-LSWM1WCM10(717),               -- RMI CPU XLR 732, with Wireless Access Controller software
            type-LSWM1IPS10(718),               -- RMI CPU XLR 732, with IPS/AV software
            type-LSWM1WCM20(719),               -- RMI CPU XLR 408, with Wireless Access Controller software
            type-LSPM2SP2P(725),                -- 2-Port 10G Ethernet SFP PLUS Optical Interface Module
            type-LSPM2SP2PA(726),               -- 2-Port Second Version SFP+ Module
            type-LSP5GP8P(727),                 -- 8-Port 1G Ethernet SFP Optical Interface Module
            type-LSP5GT8P(728),                 -- 8-Port 10/100/1000BASE-T Ethernet Electrical Interface Module
            type-LSWM1FC4P(729),                -- 4-Port 8G Fibre Channel Interface Module
            type-LSW1XGT4P0(730),               -- 4-Port 10G Ethernet Copper Interface Module
            type-LSW1XGT2P0(731),               -- 2-Port 10G Ethernet Copper Interface Module
            type-LSP1XGT2P(732),                -- 2-Port 10G Ethernet Copper Interface Board
            type-LSPM3XGT2P(733),               -- 2-Port 1/10G BASE-T Ethernet Copper Interface Module
            type-LSWM2QP2P(734),                -- 2-Port QSFP+ Interface Module
            type-LSWM2XGT2PM(735),              -- 2-Port 10G Ethernet Copper Interface Module with MACsec
            type-LSWM2SP2PM(736),               -- 2-Port SFP+ Interface Module with MACsec
            type-LSWM2SP8PM(737),               -- 8-Port SFP+ Interface Module with MACsec
            type-LSWM2SP8P(738),                -- 8-Port SFP+ Interface Module
            type-LSWM2XGT8PM(739),              -- 8-Port 10G Ethernet Copper Interface Module with MACsec
            type-LSWM18QC(740),                 -- 8-Port QSFP+ Module
            type-LSWM124XG2Q(741),              -- 24-Port SFP+ and 2-Port QSFP+ Module
            type-LSWM124XGT2Q(742),             -- 24-Port 10G BASE-T and 2-Port QSFP+ Module
            type-LSWM124XG2QL(743),             -- 24-Port SFP+ and 2-Port QSFP+ Module
            type-LSWM124XG2QFC(744),            -- 24-Port 8G Fibre Channel Interface and 2-Port QSFP+ Module
            type-LSWM18QC0(745),                -- 8-Port QSFP+ Module
            type-LSWM124XGT2Q0(746),            -- 24-Port 10G BASE-T and 2-Port QSFP+ Module
            type-LSWM124XG2QL0(747),            -- 24-Port SFP+ and 2-Port QSFP+ Module
            type-LSP6G4T6P(748),                -- 6-Port SFP and 2-port 10/100/1000BASE-T COMBO and 2 port 10/100/1000BASE-T Interface Module
            type-LSPM6QP2PS(749),               -- 2-Port QSFP+ Stack Interface Module
            type-LSWM12H2Q(750),                -- 2-Port QSSP28 and 2-Port QSFP+ Module
            type-LSWM18CQ(751),                 -- 8-Port QSFP28 Module
            type-LSWM116Q(752),                 -- 16-Port QSFP+ Module
            type-LSPM6FWD(753),                 -- Next Generation Firewall Module
            type-DS-3E-2XT-H(754),              -- 2-Port 10G Ethernet Copper Interface Module with MACsec
            type-DS-3E-2XF-H(755),              -- 2-Port SFP+ Interface Module with MACsec
            type-DS-3E-2QX-H(756),              -- 2-Port QSFP+ Stack Interface Module
            type-LSPM4G4T6P(757),               -- 6-Port SFP and 2-port 10/100/1000BASE-T COMBO and 2 port 10/100/1000BASE-T Interface Module
            type-LSWM4SP8PM(758),               -- 8-Port SFP+ Interface Module with MACsec
            type-LSWM124TG2H(759),              -- 24-Port SFP28 and 2-Port QSFP28 Module

            type-LSWM2ZQP2P(763),               -- 2-Port QSFP28 Module
            type-LSWM2ZSP8P(764),               -- 8-Port SFP28 Module
            type-LSWM18CQMSEC(765),             -- 8-Port QSFP28 MACSEC Module
            type-LSWM2MGT8P(766),               -- 8-Port SmartGE (5/2.5/1G) Interface Module
            type-LSWM2XMGT8P(767),              -- 8-Port SmartGE (10/5/2.5/1G) Interface Module
            type-LSWM2ZSP2P(768),               -- 2-Port SFP28 Interface Module
            type-LSWM116FC(769),                -- 16-Port SFP28 Ethernet Optical Interface Module with 16G/32G FC
            type-LSWM216FC(770),                -- 16-Port SFP28 Ethernet Optical Interface Module with 16G/32G FC
            type-LSWM2SP2PB(771),               -- 2-Port SFP+ Interface Module
            type-LSWM2SP4PB(772),               -- 4-Port SFP+ Interface Module
            type-LSWM2SP24P(773),               -- 24-Port SFP+ Interface Module
            type-LSWM2SP12P2Q(774),             -- 12-Port SFP+ and 2-Port QSFP+ Interface Module
            type-LSWM2SP12P2QA(775),            -- 12-Port SFP+ and 2-Port QSFP+ Interface Module with wider size
            type-LSWM18CQMSEC-Z(778),           -- 8-Port QSFP28 MACSEC Module
            type-LSWM124XG2QFC-Z(779),          -- 24-Port 8G Fibre Channel Interface and 2-Port QSFP+ Module
            type-LSWM124TG2H-Z(780),            -- 24-Port SFP28 and 2-Port QSFP28 Module
            type-LSWM116HC(781),                -- 16-Port QSFP28 Ethernet Optical Interface Module
            type-10GBASE-T-MACSEC-2P-MOD(782),  -- 2*1G/2.5G/5G/10G BASE-T Ethernet Interface Board(RJ45)
            type-S66-2QF(783),                  -- 2-Port QSFP+ Interface Module
--
-- 800 to 899 reserved for WLAN products
--
            type-WX5002MPU(800),                -- Wireless Lan Control Board with 2-port 1000BASE-T/1000BASE-X Combo Interface
            type-LS8M1WCMA(801),                -- Wireless Lan Service Board
            type-EWPX1G24XA0(802),              -- 24-Port 1000BASE-T Gigabit Ethernet Interface(RJ45) and 4-port 1000BASE-T/1000BASE-X Combo Interface and 2-port 10GBASE Interface Line Card
            type-LSQ1WCMB0(803),                -- 1 Port 10GBASE Interface Board
            type-LSB1WCM2A0(804),               -- Wireless Controller Module Board
            type-EWPX1WCMB0(805),               -- 1 Port 10GBASE Interface Board
            type-EWPX1G24XC0(806),              -- 24-Port 1000BASE-T Gigabit Ethernet Interface(RJ45) and 4-port 1000BASE-T/1000BASE-X Combo Interface Line Card
            type-EWPX1WCMC0(807),               -- 1-Port 1000BASE-T Gigabit Ethernet of wireless Lan Service Board
            type-EWPX1FWA0(808),                -- Firewall Service Board
            type-EWPX1G10XC0(809),              -- 8-Port 1000BASE-T Gigabit Ethernet Interface(RJ45) and 2-port 1000BASE-X SFP Interface Line Card
            type-EWPX1WCM10C0(810),             -- 1-Port 1000BASE-T Gigabit Ethernet of wireless Lan Service Board
            type-LSR1WCM2A1(811),               -- 1-Port 1000BASE-T Gigabit Ethernet of wireless Lan Service Board
            type-EWPX1WAP0(812),                -- Encryption Card
            type-EWPX1WCMD0(813),               -- 2 Port 10GBASE Interface Board
            type-EWPX1G24XCE0(814),             -- 24-Port 1000BASE-T Gigabit Ethernet Interface(RJ45) and 4-port 1000BASE-T/1000BASE-X Combo Interface Line Card
            type-EWPX1WCMCE0(815),              -- 2-Port 1000BASE-T Gigabit Ethernet of wireless Lan Service Board
            type-EWPX1G24XD0(816),              -- 4-Port 10GBASE-T and 24-Port 1000BASE-T Gigabit Ethernet Interface(RJ45) and 4-port 1000BASE-T/1000BASE-X Combo Interface Line Card
            type-EWPXM1XG03(817),               -- 8GE and 2SFP Plus Interface Board  of wireless Lan Service Board
            type-EWPXM2X(818),                  -- 2SFP Plus Interface Board  of wireless Lan Service Board
            type-EWPXM8G(819),                  -- 8GE Interface Board  of wireless Lan Service Board
            type-IOT-CARD-C1K(820),             -- IoT Service Board for Wireless Controller
            type-EWPXM1BSTX80(821),             -- 8GE and 8*SFP Plus(or 2*40Ge)Interface Board  of wireless Lan Service Board
            type-EWPM1WBCD0ENT(822),            -- WBC Service Board for Wireless Controller
            type-EWPXM1XG20(823),               -- 2SFP Plus Interface Board  of wireless Lan Service Board
            type-EWPM1WBCE0ENT (824),           -- WBC Service Board for Wireless Controller
            type-LSEM1WBC120G0(825),            -- 4-Port 40GBASE-T of WBC Service Board for Wireless Controller
            type-EWPXM1XG04(826),               -- 4-Port 10GBASE-T of wireless Lan Service Board
            type-EWPXM1GE08(827),               -- 8-Port GE of wireless Lan Service Board
            type-EWPXM3XG03(828),               -- 8GE and 2SFP Plus Interface Board  of wireless Lan Service Board
            type-EWPXM1XG03-Z(829),             -- 8GE and 2SFP Plus Interface Board  of wireless Lan Service Board
            type-EWPXM1XG20-Z(830),             -- 2SFP Plus Interface Board  of wireless Lan Service Board
            type-AC2048-8GT2XF(831),            -- 8GE and 2SFP Plus Interface Board  of wireless Lan Service Board
            type-EWPXM1XG03I(832),              -- 8GE and 2SFP Plus Interface Board  of wireless Lan Service Board
            type-EWPXM1XG20I(833),              -- 2SFP Plus Interface Board  of wireless Lan Service Board
--
-- 900 to 1199 reserved for advanced switchs part II
--
            type-LSR1DRSP2L1(900),              -- 2-Port OC-48c/STM-16c RPR Optical Interface Card(SFP,LC)
            type-PIC-CLF2G8L(901),              -- 2-Port 155M CPOS Optical Interface(SFP,LC)+8-Port 1000BASE-X Optical Interface Card(SFP,LC)
            type-PIC-CLF4G8L(902),              -- 4-Port 155M CPOS Optical Interface(SFP,LC)+8-Port 1000BASE-X Optical Interface Card(SFP,LC)
            type-SR02SRP2F3(903),               -- Routing Switch Processing Board(2F)
            type-SR02SRP1F3(904),               -- Routing Switch Processing Board(1F)
            type-LST1GT48LEA1(905),             -- 48-Port 10/100/1000BASE-T Interface Module(LEA),(RJ45)
            type-LST1GP48LEA1(906),             -- 48-Port 1000BASE-X Interface Module(LEA),(SFP,LC)
            type-LST2XP8LEA1(907),              -- 8-Port 10GBASE-R Interface Module(LEA),(SFP+,LC)
            type-LST1GT48LEY1(908),             -- 48-Port 10/100/1000BASE-T Interface Module(LEY),(RJ45)
            type-LST1GP48LEY1(909),             -- 48-Port 1000BASE-X Interface Module(LEY),(SFP,LC)
            type-LST1XP32REY1(910),             -- 32-Port 10GBASE-R Interface Module(REY),(SFP+,LC)
            type-LST1XP8LEY1(911),              -- 8-Port 10GBASE-R/W Interface Module(LEY),(XFP,LC)
            type-LST1GP48LEZ1(912),             -- 48-Port 1000BASE-X Interface Module(LEZ),(SFP,LC)
            type-LST1XP8LEZ1(913),              -- 8-Port 10GBASE-R/W Interface Module(LEZ),(XFP,LC)
            type-IM-FW-II(914),                 -- Firewall Service Processing Board-II
            type-IM-IPS(915),                   -- Intrusion Prevention System Service Processing Board
            type-IM-SSL(916),                   -- SSL VPN Service Processing Board
            type-IM-LB(917),                    -- Load Balance Service Processing Board
            type-IM-ACG(918),                   -- Application Control Gateway Service Processing Board
            type-LSR1XP16REC1(919),             -- 16-Port 10GBASE-R Interface Module(REC),(SFP+,LC)
            type-LST2XP8LEB1(920),              -- 8-Port 10GBASE-R Interface Module(LEB),(SFP+,LC)
            type-LST2XP8LEC1(921),              -- 8-Port 10GBASE-R Interface Module(LEC),(SFP+,LC)
            type-LST2XP8LEF1(922),              -- 8-Port 10GBASE-R Interface Module(LEF),(SFP+,LC)
            type-LST2XP4LEB1(923),              -- 4-Port 10GBase-R Interface Module(LEB),(SFP+,LC)
            type-LST2XP4LEC1(924),              -- 4-Port 10GBase-R Interface Module(LEC),(SFP+,LC)
            type-LST2XP32REB1(925),             -- 32-Port 10GBASE-R Interface Module(REB),(SFP+,LC)
            type-LST2XP32REC1(926),             -- 32-Port 10GBASE-R Interface Module(REC),(SFP+,LC)
            type-LSR1WCM3A1(927),               -- Access Controller Module
            type-LST1XP16LEB1(928),             -- 16-Port 10GBASE-R Interface Module (LEB),(SFP+,LC)
            type-LST1XP16LEC1(929),             -- 16-Port 10GBASE-R Interface Module (LEC),(SFP+,LC)
            type-CR-SPC-XP4L-E-I(930),          -- 4-Port 10GBASE-R/W Optical Interface Module,(XFP,LC)
            type-LST2MRPNC1(931),               -- Management and Route Process Unit
            type-LST2SF08C1(932),               -- Switch Fabric Card
            type-LST2SF18C1(933),               -- Switch Fabric Card
            type-SR02SRP2G3(934),               -- Routing Switch Processing Board(2G)
            type-CR-SPE-3020-E-I(935),          -- Dual Service Processing Board
            type-CR-SPC-PUP4L-E-I(936),         -- 4-Port 10G POS Optical Interface Board(Enhanced),(XFP,LC)
            type-CR-SPC-XP4LEF-I(937),          -- 4-Port 10GBASE-R/W Interface Module (LEF),(XFP,LC)
            type-CR-SPC-XP8LEF-I(938),          -- 8-Port 10GBASE-R/W Interface Module (LEF),(XFP,LC)
            type-LST3XP8LEB1(939),              -- 8-Port 10GBASE-R Interface Module (LEB),(XFP,LC)
            type-LST3XP8LEC1(940),              -- 8-Port 10GBASE-R Interface Module (LEC),(XFP,LC)
            type-LST1FW3A1(941),                -- Firewall Board
            type-CR-IM-NAM1A(942),              -- CR1M1NAM1A1, Network Analysis Service Module, Domestic&Overseas Version
            type-LSR2SRP2B1(943),               -- Management and Route Process Unit
            type-LSR2SRP2B2(944),               -- Management and Route Process Unit
            type-LSR2SRP2D1(945),               -- Management and Route Process Unit
            type-LST3XP8LEY1(946),              -- 8-Port 10GBASE-R/W Interface Module (LEY),(XFP,LC)
            type-LST2XP32REY1(947),             -- 32-Port 10GBASE-R Interface Module(REY),(SFP+,LC)
            type-LST1XP16LEY1(948),             -- 16-Port 10GBASE-R Interface Module (LEY),(SFP+,LC)
            type-SR0M2SRP2G3(949),              -- Routing Switch Processing Board(2G)
            type-SR0M2SRP1G3(950),              -- Routing Switch Processing Board(1G)
            type-SPC-GP48LA(951),               -- 48-Port 1000BASE-X Interface Service Module,(SFP,LC)
            type-SPC-GT48LA(952),               -- 48-Port 10/100/1000BASE-T Interface Service Module,(RJ45)
            type-SPC-XP4LA(953),                -- 4-Port 10GBase-R/W Interface Service Module,(XFP,LC)
            type-SPC-XP2LA(954),                -- 2-Port 10GBASE-R/W Interface Service Module,(XFP,LC)
            type-SPC-GP24LA(955),               -- 16-Port 1000BASE-X Interface(SFP,LC)+8-Port Combo Interface Service Module
            type-SPC-XP16RA(956),               -- 16-Port 10GBASE-R Optical Interface Service Module(RA),(SFP+,LC)
            type-CR-IM-FW1A(957),               -- Firewall Service Processing Board
            type-SPC-XP16R(958),                -- 16-Port 10GBASE-R Optical Interface Service Module(R),(SFP+,LC)
            type-CR-IM-LB1A(959),               -- Load Balancing Service Processing Board
            type-LST1GT48LEC2(960),             -- 48-Port 10/100/1000BASE-T Interface Module(LEC),(RJ45)
            type-LST1GP48LEC2(961),             -- 48-Port 1000BASE-X Interface Module (LEC),(SFP,LC)
            type-LST1XP16LEC2(962),             -- 16-Port 10GBASE-R Interface Module (LEC),(SFP+,LC)
            type-LST2XP8LEC2(963),              -- 8-Port 10GBASE-R Interface Module(LEC),(SFP+,LC)
            type-LST2XP32REC2(964),             -- 32-Port 10GBASE-R Interface Module(REC),(SFP+,LC)
            type-CR-IM-MAC1A(965),              -- Master Access Control Service Module
            type-LST1XP48LFD1(966),             -- 48-Port 10GBASE-R Interface Module (LFD),(SFP+,LC)
            type-LST1XP40RFD1(967),             -- 40-Port 10GBASE-R Interface Module (RFD),(SFP+,LC)
            type-LST1XP40RFG1(968),             -- 40-Port 10GBASE-R/W Interface Module (RFG),(SFP+,LC)
            type-LST1XLP16RFD1(969),            -- 16-Port 40GBASE-R Interface Module (RFD),(QSFP+,LC)
            type-LST1CP4RFD1(970),              -- 4-Port 100GBASE-R Interface Module (RFD),(CFP,LC)
            type-LST1CP4RFG1(971),              -- 4-Port 100GBASE-R Interface Module (RFG),(CFP,LC)
            type-LST1SF08E1(972),               -- Switch Fabric Card
            type-LST1SF18E1(973),               -- Switch Fabric Card
            type-LST1MRPNE1(974),               -- Management and Route Process Unit
            type-LSX1CGX8FC0(975),              -- 8-Port 100GBASE-R Interface Module (FC),(CXP,MPO)
            type-LSX1CGX8FC1(976),              -- 8-Port 100GBASE-R Interface Module (FC),(CXP,MPO)
            type-LSX1QGS24FC0(977),             -- 24-Port 40GBASE-R Interface Module (FC),(QSFP+)
            type-LSX1QGS24FC1(978),             -- 24-Port 40GBASE-R Interface Module (FC),(QSFP+)
            type-LSX1TGS24FC0(979),             -- 24-Port 10GBASE-R Interface Module (FC),(SFP+,LC)
            type-LSX1TGS24FC1(980),             -- 24-Port 10GBASE-R Interface Module (FC),(SFP+,LC)
            type-LSX1TGS48FC0(981),             -- 48-Port 10GBASE-R Interface Module (FC),(SFP+,LC)
            type-LSX1TGS48FC1(982),             -- 48-Port 10GBASE-R Interface Module (FC),(SFP+,LC)
            type-LST1XP48LFD2(983),             -- 48-Port 10GBASE-R Interface Module (LFD),(SFP+,LC)
            type-LST1XP40RFD2(984),             -- 40-Port 10GBASE-R Interface Module (RFD),(SFP+,LC)
            type-LST1XP40RFG2(985),             -- 40-Port 10GBASE-R/W Interface Module (RFG),(SFP+,LC)
            type-LST1XLP16RFD2(986),            -- 16-Port 40GBASE-R Interface Module (RFD),(QSFP+)
            type-LST1CP4RFD2(987),              -- 4-Port 100GBASE-R Interface Module (RFD),(CFP)
            type-LST1CP4RFG2(988),              -- 4-Port 100GBASE-R Interface Module (RFG),(CFP)
            type-MPE-1004(989),                 -- Multi-Service Processing Engine
            type-MIC-GP4L(990),                 -- 4-Port 1000BASE-X COMBO Interface Card,(SFP,LC)
            type-MIC-GP8L(991),                 -- 8-Port 1000BASE-X Optical Interface Card,(SFP,LC)
            type-MIC-SP4L(992),                 -- 4-Port OC-3/STM-1 POS/CPOS/ATM or 1-Port OC-12/STM-4 POS/ATM Optical Interface Card,(SFP,LC)
            type-MIC-ET16L(993),                -- 16-Port E1/T1 Electrical Interface Card
            type-MIC-CLP4L(994),                -- 4-Port OC-3/STM-1 CPOS/POS Optical Interface Card,(SFP,LC)
            type-MIC-CLP2L(995),                -- 2-Port OC-3/STM-1 CPOS/POS Optical Interface Card,(SFP,LC)
            type-LST1IPS2A1(996),               -- Intrusion Prevention System Module
            type-SFC-04B(997),                  -- Switch Fabric Card(B Type)
            type-SFC-04D(998),                  -- Switch Fabric Card(D Type)
            type-SFC-08B(999),                  -- Switch Fabric Card(B Type)
            type-SFC-08D(1000),                 -- Switch Fabric Card(D Type)
            type-SFC-12B(1001),                 -- Switch Fabric Card(B Type)
            type-SFC-12D(1002),                 -- Switch Fabric Card(D Type)
            type-SR05SRP1H1(1003),              -- Routing Switch Processing Unit(1H)
            type-SPC-GP24LA1(1004),             -- 16-Port 1000BASE-X Ethernet Optical Interface(SFP,LC)+8-Port Combo Interface Module(A Type)
            type-SPC-GP24XP2LA(1005),           -- 16-Port 1000BASE-X Ethernet Optical Interface(SFP,LC)+8-Port Combo Interface+2-Port 10GE Optical Interface Module(XFP,LC)(A Type)
            type-SPC-GP48LA1(1006),             -- 48-Port 1000BASE-X Ethernet Optical Interface Module(SFP,LC)(A Type)
            type-SPC-GP48LB(1007),              -- 48-Port Enhanced 1000BASE-X Ethernet Optical Interface Module(SFP,LC)(B Type)
            type-SPC-XP2LA1(1008),              -- 2-Port 10GBASE Ethernet Optical Interface Module(XFP,LC)(A Type)
            type-SPC-XP4LA1(1009),              -- 4-Port 10GBASE Ethernet Optical Interface Module(XFP,LC)(A Type)
            type-SPC-XP4LB(1010),               -- 4-Port Enhanced 10GBASE Ethernet Optical Interface Module(XFP,LC)(B Type)
            type-SPC-XP8LA(1011),               -- 8-Port 10GBASE Ethernet Optical Interface Module(SFP+,LC)(A Type)
            type-SPC-XP8LB(1012),               -- 8-Port Enhanced 10GBASE Ethernet Optical Interface Module(SFP+,LC)(B Type)
            type-SPC-XP48LA(1013),              -- 48-Port 10GBASE Ethernet Optical Interface Module(SFP+,LC)(A Type)
            type-SPC-XLP8LA(1014),              -- 8-Port 40GBASE Ethernet Optical Interface Module(QSFP+,MPO)(A Type)
            type-SPC-GP24XP2LB(1015),           -- 16-Port 1000BASE-X Optical Interface(SFP,LC)+8-Port Combo Interface+2-Port 10GE Optical Interface Module(XFP,LC)(B Type)
            type-LST1MRPNE2(1016),              -- Management and Route Process Unit
            type-LST2FW3A1(1017),               -- Firewall Board
            type-LST1ADE1A1(1018),              -- Load Balancing Board
            type-CR-MRP-II(1019),               -- Management and Route Unit-II
            type-CR-SF08E(1020),                -- Switch Fabric Module(E)
            type-CR-SF18E(1021),                -- Switch Fabric Module(E)
            type-CR-SPC-XP40RC(1022),           -- 40-Port 10GBASE-R/W Optical Interface Module(RC),(SFP+,LC)
            type-CR-SPC-XP40RB(1023),           -- 40-Port 10GBASE-R Ethernet Optical Interface Module(RB),(SFP+,LC)
            type-CR-SPC-CP4RC(1024),            -- 4-Port 100GBASE Ethernet Optical Interface Module(RC),(CFP)
            type-LST1FW3C1(1025),               -- Firewall Board
            type-LSU1FWCEA0(1026),              -- Firewall Board
            type-SPC-GT48LA1(1027),             -- 48-Port 10/100/1000BASE-T Ethernet Interface Module(RJ45)(A Type)
            type-LST1XP20RFD1(1028),            -- 20-Port 10GBASE-R Interface Module (RFD),(SFP+,LC)
            type-LST1XP20RFD2(1029),            -- 20-Port 10GBASE-R Interface Module (RFD),(SFP+,LC)
            type-MPE-1104(1030),                -- 4-Port Multiservice Processing Engine
            type-SPEX-1204(1031),               -- 4-Port 10G Processing Engine
            type-SPC-GP44XP4LCX(1032),          -- 44-Port 100/1000BASE-X Ethernet Optical Interface Module(SFP,LC)+4-Port 10GBASE Ethernet Optical Interface Module(SFP+,LC)(C Type)
            type-SPC-GP44XP4LAX(1033),          -- 44-Port 100/1000BASE-X Ethernet Optical Interface Module(SFP,LC)+4-Port 10GBASE Ethernet Optical Interface Module(SFP+,LC)(A Type)
            type-SPC-XP24LCX(1034),             -- 24-Port 10GBASE Ethernet Optical Interface Module(SFP+,LC)(C Type)
            type-SPC-XP24LAX(1035),             -- 24-Port 10GBASE Ethernet Optical Interface Module(SFP+,LC)(A Type)
            type-SPC-XP12LCX(1036),             -- 12-Port 10GBASE Ethernet Optical Interface Module(SFP+,LC)(C Type)
            type-SPC-XP12LAX(1037),             -- 12-Port 10GBASE Ethernet Optical Interface Module(SFP+,LC)(A Type)
            type-SPC-XLP6LCX(1038),             -- 6-Port 40GBASE Ethernet Optical Interface Module(QSFP+,MPO)(C Type)
            type-SPC-XLP6LAX(1039),             -- 6-Port 40GBASE Ethernet Optical Interface Module(QSFP+,MPO)(A Type)
            type-SPC-CP1LCX(1040),              -- 1-Port 100GBASE Ethernet Optical Interface Module(CFP,LC)(C Type)
            type-SPC-CP1LAX(1041),              -- 1-Port 100GBASE Ethernet Optical Interface Module(CFP,LC)(A Type)
            type-SPC-CP2LB(1042),               -- 2-Port 100GBASE Ethernet Optical Interface Module(CFP,LC)(B Type)
            type-SPC-CP2LA(1043),               -- 2-Port 100GBASE Ethernet Optical Interface Module(CFP,LC)(A Type)
            type-SR05SRP1L1(1044),              -- Management and Route Process Unit(1L1)
            type-SR05SRP1L3(1045),              -- Management and Route Process Unit(1L3)
            type-SFC-04-4(1046),                -- Short-circuit Card Slot 4
            type-SFC-04-3(1047),                -- Short-circuit Card Slot 3
            type-SFC-04-2(1048),                -- Short-circuit Card Slot 2
            type-SFC-04-1(1049),                -- Short-circuit Card Slot 1
            type-LST1NSM2C1(1050),              -- NetStream Service Board
            type-CR-SPC-XP20RB(1051),           -- 20-Port 10GBASE-R Ethernet Optical Interface Module(RB),(SFP+,LC)
            type-SR07SRPUA1(1052),              -- Management and Route Process Unit(UA1)
            type-SR07SRPUB3(1053),              -- Management and Route Process Unit(UB1)
            type-SR07SRPUC3(1054),              -- Management and Route Process Unit
            type-SR07MPUA1(1055),               -- Management and Route Process Unit
            type-SR07SRPUB1(1056),              -- Management and Route Process Unit(UB1)
            type-SR07SRPUC1(1057),              -- Management and Route Process Unit
            type-MIC-MS4L(1058),                -- 4-Port Multi-Service Optical Interface Card,Domestic&Overseas Version
            type-SPC-GP44XP4LC(1059),           -- 44-Port 100/1000BASE-X Ethernet Optical Interface Board(SFP,LC)+4-Port 10GBASE Ethernet Optical Interface Board(SFP+,LC)(C Type)
            type-SPC-GP44XP4LA(1060),           -- 44-Port 100/1000BASE-X Ethernet Optical Interface Board(SFP,LC)+4-Port 10GBASE Ethernet Optical Interface Board(SFP+,LC)(A Type)
            type-SPC-XLP2XP4LC(1061),           -- 2-Port 40GBASE Ethernet Optical Interface Board(QSFP+,MPO)+4-Port 10GBASE Ethernet Optical Interface Board(SFP+,LC)(C Type)
            type-SPC-XP12LC(1062),              -- 12-Port 10GBASE Ethernet Optical Interface Board(SFP+,LC)(C Type)
            type-SPC-CP1LC(1063),               -- 1-Port 100GBASE Ethernet Optical Interface Module(CFP,LC)(C Type)
            type-SPC-XP24LC(1064),              -- 24-Port 10GBASE Ethernet Optical Interface Board(SFP+,LC)(C Type)
            type-SR07SRPUD3(1065),              -- Management and Route Process Unit(UD1)
            type-SR07MPUA3(1066),               -- Management and Route Process Unit(For 02 Chassis)
            type-MPEX-1304(1067),               -- 4-Port Multiservice Processing Engine
            type-MIC-GP10L1(1068),              -- 6-Port 1000BASE-X Optical Interface Card(SFP,LC)+4-Port 1000BASE-X/10GBASE Optical Interface Card(SFP+,LC)
            type-SR07SRPUB(1069),               -- Management and Route Processing Unit(UB3)
            type-CMPE-1104(1070),               -- 4-Port Multiservice Processing Engine
            type-CSFC-04-1(1071),               -- Fabric Card Slot 1
            type-CSFC-04-2(1072),               -- Fabric Card Slot 2
            type-CSFC-04-3(1073),               -- Fabric Card Slot 3
            type-CSFC-04-4(1074),               -- Fabric Card Slot 4
            type-CSFC-04B(1075),                -- Switch Fabric Card(B Type)
            type-CSFC-04D(1076),                -- Switch Fabric Card(D Type)
            type-CSFC-08B(1077),                -- Switch Fabric Card(B Type)
            type-CSFC-08D(1078),                -- Switch Fabric Card(D Type)
            type-CSFC-12B(1079),                -- Switch Fabric Card(B Type)
            type-CSFC-12D(1080),                -- Switch Fabric Card(D Type)
            type-CSPC-CP1LCX(1081),             -- 1-Port 100GBASE Ethernet Optical Interface Module(CFP,LC)(C Type)
            type-CSPC-CP2LB(1082),              -- 2-Port 100GBASE Ethernet Optical Interface Module(CFP,LC)(B Type)
            type-CSPC-GP24LA1(1083),            -- 16-Port 1000BASE-X Ethernet Optical Interface(SFP,LC)+8-Port Combo Interface Module(A Type)
            type-CSPC-GP24XP2LB(1084),          -- 16-Port 1000BASE-X Optical Interface(SFP,LC)+8-Port Combo Interface+2-Port 10GE Optical Interface Module(XFP,LC)(B Type)
            type-CSPC-GP44XP4LCX(1085),         -- 44-Port 1000BASE-X Ethernet Optical Interface Module(SFP,LC)+4-Port 10GBASE Ethernet Optical Interface Module(SFP+,LC)(C Type)
            type-CSPC-GP48LB(1086),             -- 48-Port Enhanced 1000BASE-X Ethernet Optical Interface Module(SFP,LC)(B Type)
            type-CSPC-GT48LA1(1087),            -- 48-Port 10/100/1000BASE-T Ethernet Interface Module(RJ45)(A Type)
            type-CSPC-XLP6LCX(1088),            -- 6-Port 40GBASE Ethernet Optical Interface Module(QSFP+,MPO)(C Type)
            type-CSPC-XP2LA1(1089),             -- 2-Port 10GBASE Ethernet Optical Interface Module(XFP,LC)(A Type)
            type-CSPC-XP4LB(1090),              -- 4-Port Enhanced 10GBASE Ethernet Optical Interface Module(XFP,LC)(B Type)
            type-CSPC-XP8LB(1091),              -- 8-Port Enhanced 10GBASE Ethernet Optical Interface Module(SFP+,LC)(B Type)
            type-CSPC-XP12LAX(1092),            -- 12-Port 10GBASE Ethernet Optical Interface Module(SFP+,LC)(A Type)
            type-CSPC-XP12LCX(1093),            -- 12-Port 10GBASE Ethernet Optical Interface Module(SFP+,LC)(C Type)
            type-CSPC-XP24LAX(1094),            -- 24-Port 10GBASE Ethernet Optical Interface Module(SFP+,LC)(A Type)
            type-CSPC-XP24LCX(1095),            -- 24-Port 10GBASE Ethernet Optical Interface Module(SFP+,LC)(C Type)
            type-CSPEX-1204(1096),              -- 4-Port 10G Processing Engine
            type-CSR05SRP1L1(1097),             -- Management and Route Process Unit(1L1)
            type-CSR05SRP1L3(1098),             -- Management and Route Process Unit(1L3)
            type-CSR07MPUA1(1099),              -- Management and Route Processing Unit
            type-CSR07SRPUA1(1100),             -- Management and Route Processing Unit(UA1)
            type-CSR07SRPUB1(1101),             -- Management and Route Processing Unit(UB1)
            type-CSR07SRPUC1(1102),             -- Management and Route Processing Unit
            type-LSXM1CGX8FX1(1103),            -- 8-Port 100GBASE Ethernet Optical Interface Module(CXP)(FX)
            type-LSXM1QGS24FX1(1104),           -- 24-Port 40GBASE Ethernet Optical Interface Module(QSFP+)(FX)
            type-LSXM1TGS48FX1(1105),           -- 48-Port 10GBASE Ethernet Optical Interface Module(SFP+,LC)(FX)
            type-LSXM1QGS12FX1(1106),           -- 12-Port 40GBASE Ethernet Optical Interface Module(QSFP+)(FX)
            type-LSXM1TGT48FX1(1107),           -- 48-Port 10GBASE-T Ethernet Electrical Interface Module(RJ45)(FX)
            type-LSU1IPSBEA0(1108),             -- Intrusion Prevention System Module
            type-PIC-GP10L(1109),               -- 10-Port 1000BASE-X Optical Interface Card,(SFP,LC)
            type-PIC-XP1L(1110),                -- 1-Port 10GBASE-R/W Ethernet Optical Interface Card,(XFP,LC)
            type-PIC-PUP1L(1111),               -- 1-Port 10G POS Optical Interface Card,(XFP,LC)
            type-PIC-PSP4L(1112),               -- 4-Port 2.5G POS Optical Interface Card(SFP,LC)
            type-PIC-PS2G4L(1113),              -- 2-Port 2.5G POS Optical Interface(SFP,LC)+4-Port 1000BASE-X Optical Interface Card(SFP,LC)
            type-PIC-PL2G6L(1114),              -- 2-Port 155M POS Optical Interface(SFP,LC)+6-Port 1000BASE-X Optical Interface Card(SFP,LC)
            type-PIC-TCP8L(1115),               -- 8-Port OC-3c/OC-12c POS/GE Optical Interface Card,(SFP,LC)
            type-PIC-CSP1L(1116),               -- 1-Port 2.5G CPOS Optical Interface Card(SFP,LC)
            type-PIC-PH2G6L(1117),              -- 2-Port 622M POS Optical Interface(SFP,LC)+6-Port 1000BASE-X Optical Interface Card(SFP,LC)
            type-LSXM1CGP12FX1(1118),           -- 12-Port 100GBASE Ethernet Optical Interface Module(CFP2)(FX)
            type-LSXM1CGP8FX1(1119),            -- 8-Port 100GBASE Ethernet Optical Interface Module(CFP2)(FX)
            type-LSXM1GT48FX1(1120),            -- 48-Port 1000Base-T Gigabit Ethernet Interface Board(RJ45)
            type-LSXM1GT48FX0(1121),            -- 48-Port 1000Base-T Gigabit Ethernet Interface Board(RJ45)
            type-LSXM1GP48FX1(1122),            -- 48-Port 1000BASE Ethernet SFP Optical Interface Board
            type-LSXM1GP48FX0(1123),            -- 48-Port 1000BASE Ethernet SFP Optical Interface Board
            type-LSXM1TGS24FX0(1124),           -- 24-Port 10GBASE Ethernet SFP+ Optical Interface Board
            type-LSXM1TGS24FX1(1125),           -- 24-Port 10GBASE Ethernet SFP+ Optical Interface Board
            type-MIC-SP8L(1126),                -- 8-Port OC-3c/STM-1c POS Optical Interface Card
            type-LSXM1TGS48FE1(1127),           -- 48-Port 10GBASE Ethernet SFP+ Optical Interface Board(FE)
            type-LSXM1QGS24FE1(1128),           -- 24-Port 40GBASE Ethernet Optical Interface Board(QSFP+)
            type-CSPEX-1504S(1129),             -- Multi-Service Processing Board
            type-CSPEX-1504X(1130),             -- Multi-Service Processing Board
            type-CSPEX-1404S(1131),             -- Multi-Service Processing Board
            type-CSPEX-1304S(1132),             -- Multi-Service Processing Board
            type-CSPEX-1404X(1133),             -- Multi-Service Processing Board
            type-CSPEX-1304X(1134),             -- Multi-Service Processing Board
            type-MIC-XP5L(1135),                -- 5-Port 10GBASE-R/W Ethernet Optical Interface Card,(SFP+,LC)
            type-MIC-XP2L(1136),                -- 2-Port 10GBASE-R/W Ethernet Optical Interface Card,(SFP+,LC)
            type-MIC-CP1L(1137),                -- 1-Port 100G Optical Interface Card,(CFP,LC)
            type-MIC-GP20L(1138),               -- 20-Port 1000BASE-X Ethernet Optical Interface Card,(SFP,LC),Monolithic
            type-MIC-GT20L(1139),               -- 20-Port 1000BASE-X Ethernet Electrical Interface Card,(RJ45,LC),Monolithic
            type-CEPC-XP48RX(1140),             -- 48-Port 10GBASE-R/W Interface Module,(SFP+,LC)
            type-CEPC-CP4RX(1141),              -- 4-Port 100GBASE Ethernet Optical Interface Board(CFP2)
            type-MIC-GP10L-V2(1142),            -- 10-Port 1000BASE-X Optical Interface Card,(SFP,LC)
            type-CSR07SPUD3(1143),              -- Management and Route Process Board(UD3)
            type-MIC-XP1L(1144),                -- 1-Port 10GBASE-R/W Ethernet Optical Interface Card,(SFP+,LC)
            type-CSFC-12E(1145),                -- Switch Fabric Board
            type-CEPC-XP24LX(1146),             -- 24-Port 10GBASE-R/W Interface Module,(SFP+,LC)
            type-IM-MSUX(1147),                 -- Multi-Service Processing Board,Monolithic
            type-CSFC-12F(1148),                -- Switch Fabric Board, Monolithic
            type-CSR05SRP1N3(1149),             -- Main Processing Unit(1N3)
            type-CSPEX-1602X(1150),             -- Service Processing Unit(1602X)
            type-MIC-XP20L(1151),               -- 20-port 10GBASE-R/W Ethernet Optical Interface Card(SFP+,LC)
            type-MIC-CP2L(1152),                -- 2-port 100G Ethernet Optical Interface Card(CFP2,LC)
            type-IM-NGFWX-IV(1153),             -- Next Generation Firewall Module
            type-SFC-12E(1154),                 -- Switch Fabric Board
            type-SPEX-1602X-E(1155),            -- Service Processing Unit(1602X)-E
            type-SPEX-1602X-L(1156),            -- Service Processing Unit(1602X)-L
            type-EPC-XP24LX-E(1157),            -- 24-Port 10GBASE-R/W Ethernet Optical Interface Line Processing Unit (SFP+,LC)-E
            type-EPC-XP24LX-L(1158),            -- 24-Port 10GBASE-R/W Ethernet Optical Interface Line Processing Unit (SFP+,LC)-L
            type-EPC-CP4RX-L(1159),             -- 4-Port 100GBASE Ethernet Optical Interface Line Processing Unit (CFP2)-L
            type-SPEX-1504X-E(1160),            -- Service Processing Unit(1504X)-E
            type-SPEX-1504X-L(1161),            -- Service Processing Unit(1504X)-L
            type-CSPEX-1602X-L(1162),           -- Service Processing Unit(1602X)-L
            type-CEPC-XP24LX-L(1163),           -- 24-Port 10GBASE-R/W Ethernet Optical Interface Line Processing Unit (SFP+,LC)-L
            type-CEPC-CP4RX-L(1164),            -- 4-port 100G Ethernet Optical Interface Line Processing Unit(QSFP28)
            type-MIC-CP1L-E(1165),              -- 1-port 100G Ethernet Optical Interface Card(CFP,LC)-E
            type-MIC-XP4L-E(1166),              -- 4-Port 10GBASE-R/W Ethernet Optical Interface Card,(SFP+,LC)-E
            type-MIC-XP16L-E(1167),             -- 16-port 10GBASE-R/W Ethernet Optical Interface Card(SFP+,LC)-E
            type-MIC-GP20L-E(1168),             -- 20-Port 1000BASE-X Ethernet Optical Interface Card,(SFP,LC)-E
            type-MIC-GP10L-V2-E(1169),          -- 10-Port 1000BASE-X Ethernet Optical Interface Card(SFP,LC)-E
            type-MIC-GT20L-E(1170),             -- 20-Port 1000BASE-X Ethernet Electrical Interface Card,(RJ45,LC)-E
            type-CSR05SRP1P3(1171),             -- Main Processing Unit(1P3)
            type-SR05SRP1P3(1172),              -- Main Processing Unit(1P3)
            type-CSFC-16E(1173),                -- Fabric Module(E Type)
            type-SFC-16E(1174),                 -- Fabric Module(E Type)
            type-CSFC-08E(1175),                -- Fabric Module(E Type)
            type-SFC-08E(1176),                 -- Fabric Module(E Type)
            type-IM-SMUX(1177),                 -- Security Monitor Unit (IM-SMUX)
            type-IM-IPSX-IV(1178),              -- Intrusion Prevention System Module
            type-IM-ACGX-IV(1179),              -- Application Control Gateway Module
            type-SFC-08E1(1180),                -- Fabric Module(E Type)
            type-CSFC-08E1(1181),               -- Fabric Module(E Type)
            type-IM-ACG1000X-IV(1182),          -- ACG1000-Blade-X Application Control Module
            type-MIC-QP1L(1183),                -- 1-port 40G Ethernet Optical Interface Card(QSFP+,LC)
            type-CSPEX-1804X(1184),             -- Service Processing Unit(1804X)
            type-MIC-CP2L-V2(1185),             -- 2-port 100G Ethernet Optical Interface Card(QSFP28)
            type-MIC-XP4L1(1186),               -- 4-port 10GBASE-R/W Ethernet Optical Interface Card 1(SFP+,LC)
            type-SFC-16T(1187),                 -- Fabric Module(T Type)
            type-CSFC-16T(1188),                -- Fabric Module(T Type)
            type-SFC-08T(1189),                 -- Fabric Module(T Type)
            type-CSFC-08T(1190),                -- Fabric Module(T Type)
            type-MIC-XP2L-LAN(1191),            -- 2-port 10GBASE-R Ethernet Optical Interface Card(SFP+,LC)-LAN
            type-MIC-XP5L1(1192),               -- 5-port 10GBASE-R/W Ethernet Optical Interface Card(SFP+,LC)
            type-MIC-CP1L-V2(1193),             -- 1-port 100G Ethernet Optical Interface Card(CFP2,LC)
            type-CEPC-XP40LX(1194),             -- 40-port 10GBASE-R/W Ethernet Optical Interface Line Processing Unit Module(SFP+,LC)
            type-CEPC-CQ4LX(1195),              -- 4-port 100G Ethernet Optical Interface Line Processing Unit Module(QSFP28,LC)
            type-CEPC-XP4LX(1196),              -- 4-port 10GBASE-R/W Ethernet Optical Interface Line Processing Unit Module(SFP+,LC)

--
-- 1200 to 1399 reserved for secondary switchs part II
--
            type-LSU1QGC4SF0(1201),             -- 4 Port 40G BASE Ethernet Optical Interface Board(CFP,SC)(SF)
            type-LSU1QGS8SF0(1202),             -- 8-Port 40G BASE Ethernet Optical Interface Board(QSFP,MPO)(SF)
            type-LSU1TGS48SF0(1203),            -- 48-Port 10GBASE Ethernet SFP+ Optical Interface Board
            type-LSU1QGS4SF0(1204),             -- 4-Port 40G BASE Ethernet Optical Interface Board(QSFP,MPO)(SF)
            type-LSU1TGS32SF0(1205),            -- 32-Port 10GBASE Ethernet SFP+ Optical Interface Board
            type-LSU1FAB08D0(1206),             -- Switching Fabric Module
            type-LSU1FAB04B0(1207),             -- Switching Fabric Module
            type-LSU1FAB08B0(1208),             -- Switching Fabric Module
            type-LSU1FAB12D0(1209),             -- Switching Fabric Module
            type-LSU1FAB12B0(1210),             -- Switching Fabric Module
            type-LSU1FAB04D0(1211),             -- Switching Fabric Module
            type-LSQ1CTGS16SC0(1212),           -- Supervisor Engine Board With 16-Port 10GBASE Ethernet SFP+ Optical Interfaces
            type-EWPX2CTGS16SC0(1213),          -- Supervisor Engine Board With 16-Port 10GBASE Ethernet SFP+ Optical Interfaces
            type-LSU3WCMD0(1214),               -- Access Controller Card
            type-EWPX3WCMD0(1215),              -- Access Controller Card
            type-LSQ1QGS4SC0(1216),             -- 4-Port 40G BASE Ethernet Optical Interface Board(QSFP+,MPO)(SC)
            type-LSQ1QGC4SC0(1217),             -- 4 Port 40GBASE Ethernet Optical Interface Board(CFP)(SC)
            type-LSU1TGT24SF0(1218),            -- 24-Port 10GBASE-T Ethernet Electrical Interface Board(RJ45)(SF)
            type-LSQ1QGS8SC3(1219),             -- 8-Port 40G BASE Ethernet Optical Interface Board(QSFP+,MPO)
            type-LSQ1TGS32SC3(1220),            -- 32-Port 10GBASE Ethernet SFP+ Optical Interface Board
            type-LSQ1QGS4SC3(1221),             -- 4-Port 40GBASE Ethernet Optical Interface Board(QSFP+,MPO)(SC)
            type-LSQ1TGS48SC3(1222),            -- 48-Port 10GBASE Ethernet SFP+ Optical Interface Board
            type-LSQ1QGC4SC3(1223),             -- 4-Port 40GBASE Ethernet Optical Interface Board(CFP)(SC)
            type-LSQ1FAB12D3(1224),             -- Switch Fabric Board
            type-LSQ1FAB08D3(1225),             -- Switching Fabric Module
            type-LSQ1FAB04D3(1226),             -- Switching Fabric Module
            type-LSQ1TGS8EB3(1227),             -- 8-Port 10GBASE Ethernet SFP+ Optical Interface Board
            type-LSQ1TGT24SC3(1228),            -- 24-Port 10GBASE-T Ethernet Electrical Interface Board(RJ45)(SC)
            type-LSQ1FAB08B0(1229),             -- Switching Fabric Module
            type-EWPX2CTGS16SC(1230),           -- Supervisor Engine Board With 16-Port 10GBASE Ethernet SFP+ Optical Interfaces
            type-LSU1SUPB0(1231),               -- Supervisor Engine Board
            type-LSQ1GP48SA0(1232),             -- 48-Port 1000BASE-X Ethernet Optical Interface Board(SFP,LC)
            type-LSQ1TGX2SA0(1233),             -- 2-Port 10GBASE Ethernet Optical Interface Board(XFP,LC)
            type-LSV1SRPUA1(1234),              -- Supervisor Engine Board
            type-LSV1QGS12SA1(1235),            -- 12-Port 40G BASE Ethernet Optical Interface Board(QSFP+)
            type-LSV1MPUA1(1236),               -- Supervisor Engine Board
            type-LSX1SUP10A0(1237),             -- Supervisor Engine Board
            type-LSX1SUP16A0(1238),             -- Supervisor Engine Board
            type-LSX1SUP10A1(1239),             -- Supervisor Engine Board
            type-LSX1SUP16A1(1240),             -- Supervisor Engine Board
            type-LSX1FAB10B0(1241),             -- Switch Fabric Board
            type-LSX1FAB16B0(1242),             -- Switch Fabric Board
            type-LSX1FAB10B1(1243),             -- Switch Fabric Board
            type-LSX1FAB16B1(1244),             -- Switch Fabric Board
            type-LSX1QGS16EA0(1245),            -- 16-Port 40G BASE Ethernet Optical Interface Board(QSFP+,MPO)
            type-LSX1TGS48EA0(1246),            -- 48-Port 10GBASE Ethernet SFP+ Optical Interface Board
            type-LSX1QGS16EA1(1247),            -- 16-Port 40G BASE Ethernet Optical Interface Board(QSFP+,MPO)
            type-LSX1TGS48EA1(1248),            -- 48-Port 10GBASE Ethernet SFP+ Optical Interface Board
            type-LSU1TGT24SF9(1249),            -- 24-Port 10GBASE-T Ethernet Electrical Interface Board(RJ45)(SF)
            type-LSU1QGS8SF9(1250),             -- 8-Port 40G BASE Ethernet Optical Interface Board(QSFP+,MPO)(SF)
            type-LSU1QGS4SF9(1251),             -- 4-Port 40GBASE Ethernet QSFP+ Optical Interface Board(QSFP+,MPO)(SF)
            type-LSU1TGS48SF9(1252),            -- 48-Port 10GBASE Ethernet SFP+ Optical Interface Board
            type-LSU1TGS32SF9(1253),            -- 32-Port 10GBASE Ethernet SFP+ Optical Interface Board
            type-LSU1FAB08D9(1254),             -- Switching Fabric Module
            type-LSU1SUPB9(1255),               -- Supervisor Engine Board
            type-LSQ3GV48SC0(1256),             -- 48-Port 1000Base-T Gigabit Ethernet Interface Board(RJ45), PoE Plus
            type-LSX1QGS12EC1(1257),            -- 12-Port 40GBASE Ethernet Optical Interface Board(QSFP+)
            type-LSX1QGS12EC0(1258),            -- 12-Port 40GBASE Ethernet Optical Interface Board(QSFP+)
            type-LSX1TGS48EC0(1259),            -- 48-Port 10GBASE Ethernet SFP+ Optical Interface Board
            type-LSX1TGS48EC1(1260),            -- 48-Port 10GBASE Ethernet SFP+ Optical Interface Board
            type-LSX1TGS24EC0(1261),            -- 24-Port 10GBASE Ethernet SFP+ Optical Interface Board(EC)
            type-LSX1TGS24EC1(1262),            -- 24-Port 10GBASE Ethernet SFP+ Optical Interface Board(EC)
            type-LSX1FAB10A0(1263),             -- Switch Fabric Board,For 10 Slots Chassis
            type-LSX1FAB16A1(1264),             -- Switch Fabric Board,For 16 Slots Chassis
            type-LSX1QGS12FB0(1265),            -- 12-Port 40GBASE Ethernet Optical Interface Board(QSFP+)
            type-LSX1TGS24FB0(1266),            -- 24-Port 10GBASE Ethernet SFP+ Optical Interface Board(FB)
            type-LSX1TGS48FB0(1267),            -- 48-Port 10GBASE Ethernet SFP+ Optical Interface Board(FB)
            type-LSX1QGS12EB1(1268),            -- 12-Port 40GBASE Ethernet Optical Interface Board(QSFP+)
            type-LSX1TGS24EB1(1269),            -- 24-Port 10GBASE Ethernet SFP+ Optical Interface Board(EB)
            type-LSX1FAB10A1(1270),             -- Switch Fabric Board,For 10 Slots Chassis
            type-LSX1TGS48EB1(1271),            -- 48-Port 10GBASE Ethernet SFP+ Optical Interface Board(EB)
            type-LSX1GP48EB1(1272),             -- 44-Port GE Optical Interface(SFP,LC)+4-Port 10GE Optical Interface Board(SFP+,LC)
            type-LSX1GP48FB0(1273),             -- 44-Port GE Optical Interface(SFP,LC)+4-Port 10GE Optical Interface Board(SFP+,LC)
            type-LSX1GT48FC0(1274),             -- 48-Port 1000Base-T Gigabit Ethernet Interface Module(RJ45)(FC)
            type-LSX1GT48FC1(1275),             -- 48-Port 1000Base-T Gigabit Ethernet Interface Module(RJ45)(FC)
            type-LSX1GP48FC0(1276),             -- 48-Port 1000BASE-X Gigabit Ethernet Optical Interface Module(SFP,LC)(FC)
            type-LSX1GP48FC1(1277),             -- 48-Port 1000BASE-X Gigabit Ethernet Optical Interface Module(SFP,LC)(FC)
            type-LSX1QGS12FC0(1278),            -- 12-Port 40GBASE Ethernet Optical Interface Module(QSFP+)(FC)
            type-LSX1QGS12FC1(1279),            -- 12-Port 40GBASE Ethernet Optical Interface Module(QSFP+)(FC)
            type-LSX2TGS48EA1(1280),            -- 48-Port 10GBASE Ethernet SFP+ Optical Interface Board(EA)
            type-LSX1CGC4EB1(1281),             -- 4-Port 100GBASE Ethernet Optical Interface Board(CFP),Monolithic
            type-LSX1CGC4EC0(1282),             -- 4-Port 100GBASE Ethernet Optical Interface Board(CFP),Monolithic
            type-LSX1GT48EB1(1283),             -- 48-Port 1000Base-T Gigabit Ethernet Interface Board(RJ45)
            type-LSX1GT48FB0(1284),             -- 48-Port 1000Base-T Gigabit Ethernet Interface Board(RJ45)
            type-LSX1FAB16S1(1285),             -- Switch Fabric Board,For 16 Slots Chassis
            type-LSQ1SUPB3(1286),               -- Supervisor Engine Board
            type-LSU1CGC2SE0(1287),             -- 2 Port 100GBASE Ethernet Optical Interface Board(CFP)(SE)
            type-LSU1TGS16SF0(1288),            -- 16-Port 10GBASE Ethernet SFP+ Optical Interface Board
            type-LSU1TGS8SF0(1289),             -- 8-Port 10GBASE Ethernet SFP+ Optical Interface Board
            type-LSQ1TGS4SC0(1290),             -- 4-Port 10GBASE Ethernet SFP+ Optical Interface Board
            type-LSU1GT48SE3(1291),             -- 48-Port 1000Base-T Gigabit Ethernet Interface Board(RJ45)
            type-LSU1GP48SE3(1292),             -- 48-Port 1000BASE Ethernet Optical Interface Board(SFP,LC)
            type-LSX1SUP10B0(1293),             -- Supervisor Engine Board
            type-LSX1SUP16B0(1294),             -- Supervisor Engine Board
            type-LSX1SUP10B1(1295),             -- Supervisor Engine Board
            type-LSX1SUP16B1(1296),             -- Supervisor Engine Board
            type-LSQ1CGV24PSC3(1297),           -- Switching and Routing Processing Unit with 24 10/100/1000BASE-T Electrical Ports(RJ45),including 4 Combo Ports,SFP Req,PoE,No Spell
            type-LSQ1SRPA8(1298),               -- Supervisor Engine Board
            type-LSQ1CGP24TSC8(1299),           -- Supervisor Engine Board
            type-LSQ1CGT24PSC8(1300),           -- Supervisor Engine Board
            type-LSQ1GT24PSA8(1301),            -- 24-Port 10/100/1000BASE-T Electrical(RJ45) Interface Board,including 4 Combo Ports,SFP Req,Upgradeable to PoE
            type-LSQ1GP24TSA8(1302),            -- 16-Port 1000BASE-X Gigabit Ethernet Optical(SFP,LC) And 8-Port 10/100/1000BASE-T RJ45/1000BASE-X SFP Combo Interface Board
            type-LSQ1GT48SA8(1303),             -- 48-Port 1000Base-T Gigabit Ethernet Interface Board(RJ45)
            type-LSQ1GP48SA8(1304),             -- 48-Port 1000BASE-X Ethernet Optical Interface Board(SFP,LC)
            type-LSQ1TGS4SC8(1305),             -- 4-Port 10GBASE Ethernet SFP+ Optical Interface Board
            type-LSQ1TGS8SC8(1306),             -- 8-Port 10GBASE Ethernet SFP+ Optical Interface Board
            type-LSU1GT24SE3(1307),             -- 24-Port 1000BASE-T Ethernet Interface Board (RJ45)
            type-LSU1GP12SE3(1308),             -- 12-Port 1000BASE-X Ethernet Optical Interface Board(SFP,LC)
            type-LSU1GP24SE3(1309),             -- 24 Port 1000BASE-X Ethernet Optical Interface Board(SFP,LC)
            type-LSU1T24XGSE3(1310),            -- 24-Port 1000BASE-T Gigabit Ethernet Interface(RJ45)+2-Port 10GBASE Ethernet Optical Interface Board(XFP,LC)
            type-LSU1P24XGSE3(1311),            -- 24-Port 1000BASE-X Gigabit Ethernet Optical Interface(SFP,LC)+2-Port 10GBASE Ethernet Optical Interface Board(XFP,LC)
            type-LSU1GP24TSE3(1312),            -- 16-Port 1000BASE-X Gigabit Ethernet Optical(SFP,LC) And 8-Port 10/100/1000BASE-T RJ45/1000BASE-X SFP Combo Interface Board
            type-LSU1GT40PSE3(1313),            -- 40-Port 10/100/1000BASE-T Electrical(RJ45) And 8-Port 1000BASE-X Optical Ethernet Interface Board(SFP,LC),PoE
            type-LSV1TGS24SA1(1314),            -- 24-Port 10G BASE Ethernet Optical Interface Board(SFP+)
            type-LSVM1SRPA1(1315),              -- Switching Fabric Module
            type-LSVM1SRPC1(1316),              -- Switching Fabric Module
            type-LSX1FAB16S0(1317),             -- Switch Fabric Board,For 16 Slots Chassis
            type-LSU1WCME0(1318),               -- Access Controller Service Board
            type-EWPX1WCME0(1319),              -- Access Controller Service Board
            type-LSUM1TGS48SG0(1320),           -- 48-Port 10GBASE-R Ethernet SFP+ Optical Interface Board(SG)
            type-LSUM1QGS12SG0(1321),           -- 12-Port 40GBASE-R Ethernet QSFP+ Optical Interface Board(SG)
            type-LSUM1GP44TSEC0(1322),          -- 44-Port 1000BASE-R Ethernet SFP Optical Interface Board(EC)+4-Port 10GBASE-R Ethernet SFP+ Optical Interface Board(EC)
            type-LSUM1TGS24EC0(1323),           -- 24-Port 10GBASE-R Ethernet SFP+ Optical Interface Board(EC)
            type-LSUM1QGS6EC0(1324),            -- 6-Port 40GBASE-R Ethernet QSFP+ Optical Interface Board(EC)
            type-LSUM1CGC2EC0(1325),            -- 2-Port 100GBASE-R Ethernet CFP Optical Interface Board(EC)
            type-LSU1CGC2SE9(1326),             -- 2 Port 100GBASE Ethernet Optical Interface Board(CFP)(SE)
            type-LSXM1QGS24EX1(1327),           -- 24 Ports 40G BASE Ethernet Optical Interface Board(QSFP+,MPO),No Spell
            type-LSXM1QGS24FB0(1328),           -- 24 Ports 40G BASE Ethernet Optical Interface Board(QSFP+,MPO),No Spell
            type-LSVM1QGS12FX1(1329),           -- 12-Port 40G BASE Ethernet Optical Interface Module(QSFP+,MPO/LC)
            type-LSVM1TGS24FX1(1330),           -- 24-Port 10G BASE Ethernet Optical Interface Module(SFP+,LC)
            type-LSVM1QGS6C2FX1(1331),          -- 2-Port 100GBASE Ethernet Optical Interface(CXP,MPO)+6-Port 40GBASE Ethernet Optical Interface(QSFP+,MPO/LC)+4-Port 10G BASE Ethernet Optical Interface Module(SFP+,LC)
            type-LSQM2GP44TSSC0(1332),          -- 44-Port GE Optical Interface(SFP,LC)+4-Port 10GE Optical Interface Board(SFP+,LC)(SC)
            type-LSQM2GP44TSSC3(1333),          -- 44-Port GE Optical Interface(SFP,LC)+4-Port 10GE Optical Interface Board(SFP+,LC)(SC)
            type-LSQM2GP24TSSC0(1334),          -- 24-Port GE Optical Interface(SFP,LC)+4-Port 10GE Optical Interface Board(SFP+,LC)(SC)
            type-LSQM2GP24TSSC3(1335),          -- 24-Port GE Optical Interface(SFP,LC)+4-Port 10GE Optical Interface Board(SFP+,LC)(SC)
            type-LSQM2GT24PTSSC0(1336),         -- 24-Port 1000Base-T Gigabit Ethernet Interface Board(RJ45)+20-Port GE Optical Interface(SFP,LC)+4-Port 10GE Optical Interface Board(SFP+,LC)(SC)
            type-LSQM2GT24PTSSC3(1337),         -- 24-Port 1000Base-T Gigabit Ethernet Interface Board(RJ45)+20-Port GE Optical Interface(SFP,LC)+4-Port 10GE Optical Interface Board(SFP+,LC)(SC)
            type-LSQM2GT24TSSC0(1338),          -- 24-Port 1000Base-T Gigabit Ethernet Interface Board(RJ45)+4-Port 10GE Optical Interface Board(SFP+,LC)(SC)
            type-LSQM2GT24TSSC3(1339),          -- 24-Port 1000Base-T Gigabit Ethernet Interface Board(RJ45)+4-Port 10GE Optical Interface Board(SFP+,LC)(SC)
            type-LSQM2GT48SC0(1340),            -- 48-Port 1000Base-T Gigabit Ethernet Interface Board(RJ45)(SC)
            type-LSQM2GT48SC3(1341),            -- 48-Port 1000Base-T Gigabit Ethernet Interface Board(RJ45)(SC)
            type-LSQM4GV48SC0(1342),            -- 48-Port 1000Base-T Gigabit Ethernet Interface Board(RJ45)(SC)-POE
            type-LSQM4GV48SC3(1343),            -- 48-Port 1000Base-T Gigabit Ethernet Interface Board(RJ45)(SC)-POE
            type-LSQM2TGS16SF0(1344),           -- 16-Port 10GE Optical Interface Board(SFP+,LC)(SF)
            type-LSQM2TGS16SF3(1345),           -- 16-Port 10GE Optical Interface Board(SFP+,LC)(SF)
            type-LSQM2MPUD0(1346),              -- Supervisor Engine Board
            type-LSQM2MPUD3(1347),              -- Supervisor Engine Board
            type-LSQM3MPUA0(1348),              -- Supervisor Engine Board
            type-LSQM3MPUA3(1349),              -- Supervisor Engine Board
            type-LSUM2GP44TSSE0(1350),          -- 44-Port GE Optical Interface(SFP,LC)+4-Port 10GE Optical Interface Board(SFP+,LC)(SE)
            type-LSUM2GP44TSSC3(1351),          -- 44-Port GE Optical Interface(SFP,LC)+4-Port 10GE Optical Interface Board(SFP+,LC)(SC)
            type-LSUM2GP24TSSE0(1352),          -- 24-Port GE Optical Interface(SFP,LC)+4-Port 10GE Optical Interface Board(SFP+,LC)(SE)
            type-LSUM2GP24TSSC3(1353),          -- 24-Port GE Optical Interface(SFP,LC)+4-Port 10GE Optical Interface Board(SFP+,LC)(SC)
            type-LSUM2GT24PTSSE0(1354),         -- 24-Port 1000Base-T Gigabit Ethernet Interface Board(RJ45)+20-Port GE Optical Interface(SFP,LC)+4-Port 10GE Optical Interface Board(SFP+,LC)(SE)
            type-LSUM2GT24PTSSC3(1355),         -- 24-Port 1000Base-T Gigabit Ethernet Interface Board(RJ45)+20-Port GE Optical Interface(SFP,LC)+4-Port 10GE Optical Interface Board(SFP+,LC)(SC)
            type-LSUM2GT24TSSE0(1356),          -- 24-Port 1000Base-T Gigabit Ethernet Interface Board(RJ45)+4-Port 10GE Optical Interface Board(SFP+,LC)(SE)
            type-LSUM2GT24TSSC3(1357),          -- 24-Port 1000Base-T Gigabit Ethernet Interface Board(RJ45)+4-Port 10GE Optical Interface Board(SFP+,LC)(SC)
            type-LSUM2GT48SE0(1358),            -- 48-Port 1000Base-T Gigabit Ethernet Interface Board(RJ45)(SE)
            type-LSUM2GT48SC3(1359),            -- 48-Port 1000Base-T Gigabit Ethernet Interface Board(RJ45)(SC)
            type-LSUM2GV48SE0(1360),            -- 48-Port 1000Base-T Gigabit Ethernet Interface Board(RJ45)(SE)-POE
            type-LSUM2GV48SC3(1361),            -- 48-Port 1000Base-T Gigabit Ethernet Interface Board(RJ45)(SC)-POE
            type-LSUM2TGS16SF0(1362),           -- 16-Port 10GE Optical Interface Board(SFP+,LC)(SF)
            type-LSUM2TGS16SF3(1363),           -- 16-Port 10GE Optical Interface Board(SFP+,LC)(SF)
            type-LSUM1MPU06B0(1364),            -- Supervisor Engine Board
            type-LSUM1MPU06B3(1365),            -- Supervisor Engine Board
            type-LSUM1MPU10C0(1366),            -- Supervisor Engine Board
            type-LSUM1MPU10C3(1367),            -- Supervisor Engine Board
            type-LSUM1FAB06C0(1368),            -- Switching Fabric Module
            type-LSUM1FAB06C3(1369),            -- Switching Fabric Module
            type-LSUM1FAB10C0(1370),            -- Switching Fabric Module
            type-LSUM1FAB10C3(1371),            -- Switching Fabric Module
            type-LSXM1SUPA1(1372),              -- Supervisor Engine Module
            type-LSXM1SFF16B1(1373),            -- Switch Fabric Board
            type-LSUM1SPMAEC0(1374),            -- 4-Port Multiservice Processing Engine
            type-LSXM1SUPB1(1375),              -- Supervisor Engine Module
            type-LSXM1SFF08B1(1376),            -- Switching Fabric Module,Type B(F1)
            type-LSXM1TGS4GPEB1(1377),          -- 44-Port GE Optical Interface(SFP,LC)+4-Port 10GE Optical Interface Module(SFP+,LC)(EB)
            type-LSXM1TGS16EA1(1378),           -- 16-Port 10GBASE Ethernet Optical Interface Module(SFP+,LC)(EA)
            type-LSXM1TGS8EA1(1379),            -- 8-Port 10GBASE Ethernet Optical Interface Module(SFP+,LC)(EA)
            type-LSXM1QGS36FX1(1380),           -- 36-Port 40GBASE Ethernet Optical Interface Module(QSFP+)(FX)
            type-LSXM1SFF16C1(1381),            -- Switching Fabric Module
            type-LSQM3MPUB0(1382),              -- Supervisor Engine Board
            type-LSQM3MPUB3(1383),              -- Supervisor Engine Board
            type-LSQM2MPUC0(1384),              -- Supervisor Engine Board
            type-LSQM2MPUC3(1385),              -- Supervisor Engine Board
            type-LST1FW3B1(1386),               -- Firewall Board
            type-LSX1NSCEA1(1387),              -- NetStream Service Board
            type-LSX1FWCEA1(1388),              -- Firewall Service Board
            type-LSXM1ADECEA1(1389),            -- Application Delivery Engine Module,Domestic&Overseas Version
            type-LSXM1SFF16A1(1390),            -- Switching Fabric Module
            type-LSV1MPUA0(1391),               -- Supervisor Engine Board
            type-LSVM1SRPA0(1392),              -- Switching Fabric Module
            type-LSVM1SRPC0(1393),              -- Switching Fabric Module
            type-LSV1QGS12SA0(1394),            -- 12-Port 40G BASE Ethernet Optical Interface Board(QSFP+)
            type-LSVM1QGS12FX0(1395),           -- 12-Port 40G BASE Ethernet Optical Interface Module(QSFP+,MPO/LC)
            type-LSVM1TGS24FX0(1396),           -- 24-Port 10G BASE Ethernet Optical Interface Module(SFP+,LC)
            type-LSVM1QGS6C2FX0(1397),          -- 2-Port 100GBASE Ethernet Optical Interface(CXP,MPO)+6-Port 40GBASE Ethernet Optical Interface(QSFP+,MPO/LC)+4-Port 10G BASE Ethernet Optical Interface Module(SFP+,LC)
            type-LSQ2FWBSC0(1398),              -- Gigabit Firewall Card, 4 Gigabit Port for Management
            type-LSQM1SRP8X2QE0(1399),          -- Supervisor Engine Board With 8-Port 10GBASE Ethernet SFP+ Optical Interfaces+2-Port 40GBASE-R Ethernet QSFP+ Optical Interfaces

--
-- 1400 to 1599 reserved for switche RPU logical modules
--
            type-PEX-Common(1400),              -- The general logical module type for PEX
            type-CSPEX-1812X(1401),             -- Service Processing Unit Module(1812X)
            type-CSPEX-1612X(1402),             -- Service Processing Unit Module(1612X)
            type-CSPEX-1512X(1403),             -- Service Processing Unit Module(1512X)
            type-NIC-XP20L(1404),               -- 20-port 10GBASE-R/W Ethernet Optical Interface Card Module(SFP+,LC)(NIC)
            type-NIC-XP10L(1405),               -- 10-port 10GBASE-R/W Ethernet Optical Interface Card Module(SFP+,LC)(NIC)
            type-NIC-CC2L(1406),                -- 2-port 100G Ethernet Optical Interface Card Module(CFP2,LC)(NIC)
            type-NIC-CC1L(1407),                -- 1-port 100G Ethernet Optical Interface Card Module(CFP2,LC)(NIC)
            type-NIC-XP5L(1408),                -- 5-port 10GBASE-R/W Ethernet Optical Interface Card Module(SFP+,LC)(NIC)
            type-NIC-GP20L(1409),               -- 20-port 1000BASE-X Ethernet Optical Interface Card Module(SFP,LC)(NIC)
            type-NIC-GT20L(1410),               -- 20-port 1000BASE-T Ethernet Copper Interface Card Module(RJ45)(NIC)
            type-MIC-CQ1L(1411),                -- 1-port 100G Ethernet Optical Interface Card Module(QSFP28,LC)
            type-MIC-XP10CQ1L(1412),            -- 10-port 10GBASE-R/W Ethernet Optical Interface(SFP+,LC)+1-port 100G Ethernet Optical Interface Card Module(QSFP28,LC)
            type-CSPEX-1502X(1413),             -- Service Processing Unit(1502X)
            type-EPC-CP4RX(1414),               -- 4-port 100GBASE Ethernet Optical Line Processing Unit(CFP2)
            type-EPC-CQ4LX(1415),               -- 4-port 100GBASE Ethernet Optical Line Processing Unit(QSFP28)
            type-MIC-XP4L1-E(1416),             -- 4-port 10GBASE-R/W Ethernet Optical Interface Card 1(SFP+,LC)
            type-MIC-CQ1L-E(1417),              -- 1-port 100G Ethernet Optical Interface Card 1(QSFP28)
            type-MIC-XP8L(1418),                -- 8-port 10GBASE-R/W Ethernet Optical Interface Card (SFP+,LC)
            type-IM-OAPX(1419),                 -- Universal Open Platform(IM-OAPX)
            type-MIC-GP20L1(1420),              -- 20-port 1000BASE-X Ethernet Optical Interface Card(SFP,LC)
            type-CSPEX-1802X(1421),             -- Service Processing Unit(1802X)
            type-MIC-CQ2L(1422),                -- 2-port 100G Ethernet Optical Interface Card(QSFP28,LC)
            type-IMMSUX(1423),                  -- Universal Line Processing Unit(IM-MSUX)(China Telecom)
            type-CSPEX-1104-E(1424),            -- Service Processing Unit(1104E)
            type-IMSMUX(1425),                  -- Security Monitor Unit(IM-SMUX)
            type-MIC-XP10L(1426),               -- 10-port 10GBASE-R/W Ethernet Optical Interface Card(SFP+,LC)
            type-RX-SRP1P3(1427),               -- Main Processing Unit(1P3)
            type-RX-SFC-08T(1428),              -- 1Tbps Fabric Module(08)
            type-RX-SFC-16T(1429),              -- 1Tbps Fabric Module(16)
            type-RX-SPE100(1430),               -- 100G Service Processing Unit(SPE100)
            type-RX-SPE200(1431),               -- 200G Service Processing Unit(SPE200)
            type-RX-SPE400(1432),               -- 400G Service Processing Unit(SPE400)
            type-RX-NIC-GP20L(1433),            -- 20-port 1000BASE-X Ethernet Optical Interface Card(SFP,LC)(RX-NIC,SPE100)
            type-RX-NIC-XP5L(1434),             -- 5-port 10GBASE-R/W Ethernet Optical Interface Card(SFP+,LC)(RX-NIC,SPE100)
            type-RX-NIC-XP10L(1435),            -- 10-port 10GBASE-R/W Ethernet Optical Interface Card(SFP+,LC)(RX-NIC,SPE200)
            type-RX-NIC-CC1L(1436),             -- 1-port 100G Ethernet Optical Interface Card(CFP2,LC)(RX-NIC,SPE200)
            type-RX-NIC-CC2L(1437),             -- 2-port 100G Ethernet Optical Interface Card(CFP2,LC)(RX-NIC,SPE400)
            type-RX-NIC-XP20L(1438),            -- 20-port 10GBASE-R/W Ethernet Optical Interface Card(SFP+,LC)(RX-NIC,SPE400)
            type-CSPC-GE24L-E(1439),            -- 24-port 1000BASE-X Ethernet Combo Interface Line Processing Unit(E Type)
            type-CSPC-GP24GE8XP2L-E(1440),      -- 24-port 1000BASE-X Ethernet Optical Interface(SFP,LC)+ 8-port 1000BASE-X Ethernet Combo Interface+2-port 10GBASE-R/W Ethernet Optical Interface Line Processing Unit(SFP+,LC)(E Type)
            type-CSPC-GE16XP4L-E(1441),         -- 16-port 1000BASE-X Ethernet Combo Interface+4-port 10GBASE-R/W Ethernet Optical Interface Line Processing Unit(SFP+,LC)(E Type)
            type-CSFC-04E(1442),                -- Fabric Module(E Type)
            type-SFC-04E(1443),                 -- Fabric Module(E Type)
            type-IM-MSUX-II(1444),              -- Universal Line Processing Unit(IM-MSUX-II)
            type-RX-NIC-YGS4L(1445),            -- 4-port 25G Ethernet Optical Interface Card(SFP28,LC)
            type-RX-NIC-CQ2LF(1446),            -- 2-port 100G Flexible Ethernet Optical Interface Card(QSFP28,LC)
            type-RX-SRP1Q3(1447),               -- Main Processing Unit(1Q3)
            type-RX-SFC-08E(1448),              -- 400Gbps Fabric Module(08)
            type-RX-SFC-16E(1449),              -- 400Gbps Fabric Module(16)
            type-RX-NIC-LGQ2L(1450),            -- 2-port 50G Ethernet Optical Interface Card(QSFP28,LC)(RX-NIC)

            type-RX-NIC-CQ1LF(1452),            -- 1-port 100G Flexible Ethernet Optical Interface Card(QSFP28,LC)(RX-NIC)
            type-IM-SFMX(1453),                 -- Network Data Encryption Service Processing Unit(IM-SFMX)
            type-MIC-SM(1454),                  -- Network Data Encryption Interface Card(MIC-SM)
            type-RX-NIC-CQ1L(1455),             -- 1-port 100G Ethernet Optical Interface Card(QSFP28,LC)(RX-NIC)
            type-RX-NIC-CQ2L(1456),             -- 2-port 100G Ethernet Optical Interface Card(QSFP28,LC)(RX-NIC)
            type-NIC-GP24L(1457),               -- 24-port 1000BASE-X Ethernet Optical Interface Card(SFP,LC)(NIC)
            type-NIC-CQ1L(1458),                -- 1-port 100G Ethernet Optical Interface Card(QSFP28,LC)(NIC)
            type-NIC-CQ2L(1459),                -- 2-port 100G Ethernet Optical Interface Card(QSFP28,LC)(NIC)

--
-- 1600 to 1999 reserved for secondary switches part III
--
            type-LSUM2GP44TSSE9(1600),          -- 44-Port GE Optical Interface(SFP,LC)+4-Port 10GE Optical Interface Board(SFP+,LC)(SE)
            type-LSUM2GP24TSSE9(1601),          -- 24-Port GE Optical Interface(SFP,LC)+4-Port 10GE Optical Interface Board(SFP+,LC)(SE)
            type-LSUM2GT24TSSE9(1602),          -- 24-Port 1000Base-T Gigabit Ethernet Interface Board(RJ45)+4-Port 10GE Optical Interface Board(SFP+,LC)(SE)
            type-LSUM2GT48SE9(1603),            -- 48-Port 1000Base-T Gigabit Ethernet Interface Board(RJ45)(SE)
            type-LSUM1SUPD0(1604),              -- Supervisor Engine Board
            type-LSUM1SUPD9(1605),              -- Supervisor Engine Board
            type-LSXM1TGT48FX0(1606),           -- 48-Port 10GBASE-T Ethernet Electrical Interface Module(RJ45)(FX)
            type-LSXM1TGS48FX0(1607),           -- 48-Port 10GBASE-T Ethernet Electrical Interface Module(RJ45)(FX)
            type-LSXM1TGS48FE0(1608),           -- 48-Port 10GBASE Ethernet Optical Interface Module(SFP+,LC)(FE)
            type-LSXM1QGS36FX0(1609),           -- 36-Port 40GBASE Ethernet Optical Interface Module(QSFP+)(FX)
            type-LSXM1QGS24FX0(1610),           -- 24-Port 40GBASE Ethernet Optical Interface Module(QSFP+)(FX)
            type-LSXM1QGS24FE0(1611),           -- 24-Port 40GBASE Ethernet Optical Interface Module(QSFP+)(FE)
            type-LSXM1CGX8FX0(1612),            -- 8-Port 100GBASE Ethernet Optical Interface Module(CXP)(FX)
            type-LSXM1CGP12FX0(1613),           -- 12-Port 100GBASE Ethernet Optical Interface Module(CFP2)(FX)
            type-LSXM1SUPB0(1614),              -- Supervisor Engine Module
            type-LSXM1SFF16C0(1615),            -- Switching Fabric Module,Type F(Class C)
            type-LSXM1SFF16A0(1616),            -- Switching Fabric Module,Type F(Class A)
            type-LSXM1SFF08B0(1617),            -- Switching Fabric Module,Type F(Class B)
            type-LSQM6GV48SC0(1618),            -- 48-Port 10/100/1000BASE-T Ethernet Interface Module(RJ45),Upgradeable to PoE
            type-LSXM1SUP04B1(1619),            -- Supervisor Engine Module
            type-LSXM1SFF04B1(1620),            -- Switching Fabric Module,Type F(Class B)
            type-LSXM1SUP04B0(1621),            -- Supervisor Engine Module
            type-LSXM1SFF04B0(1622),            -- Switching Fabric Module,Type F(Class B)
            type-LSU1ADECEA0(1623),             -- Application Delivery Engine Module,Domestic&Overseas Version
            type-LSU1NSCEA0(1624),              -- NetStream Service Board
            type-LSU3FWCEA0(1625),              -- Firewall Service Board
            type-LSXM1MPU06B3(1626),            -- Supervisor Engine Board
            type-LSXM1MPU10C3(1627),            -- Supervisor Engine Board
            type-LSXM1SUPD3(1628),              -- Supervisor Engine Board
            type-LSXM1FAB06C3(1629),            -- Switching Fabric Module
            type-LSXM1FAB10C3(1630),            -- Switching Fabric Module
            type-LSXM1FAB12D3(1631),            -- Switching Fabric Module
            type-LSXM1FAB04D3(1632),            -- Switching Fabric Module
            type-LSXM1FAB08D3(1633),            -- Switching Fabric Module
            type-LSXM1GP44TSSE3(1634),          -- 44-Port GE Optical Interface(SFP,LC)+4-Port 10GE Optical Interface Board(SFP+,LC)(SE)
            type-LSXM1GP24TSSE3(1635),          -- 24-Port GE Optical Interface(SFP,LC)+4-Port 10GE Optical Interface Board(SFP+,LC)(SE)
            type-LSXM1GT24PTSSE3(1636),         -- 24-Port 1000Base-T Gigabit Ethernet Interface Board(RJ45)+20-Port GE Optical Interface(SFP,LC)+4-Port 10GE Optical Interface Board(SFP+,LC)(SE)
            type-LSXM1GT48SE3(1637),            -- 48-Port 1000Base-T Gigabit Ethernet Interface Board(RJ45)(SE)
            type-LSXM1TGS24EC3(1638),           -- 24-Port 10GBASE-R Ethernet SFP+ Optical Interface Board(EC)
            type-LSXM1CGC2EC3(1639),            -- 2-Port 100GBASE-R Ethernet CFP Optical Interface Board(EC)
            type-LSXM1TGT24SF3(1640),           -- 24-Port 10GBASE-T Ethernet Electrical Interface Board(RJ45)(SF)
            type-LSXM1TGS16SF3(1641),           -- 16-Port 10GE Optical Interface Board(SFP+,LC)(SF)
            type-LSXM1QGS12SG3(1642),           -- 12-Port 40GBASE-R Ethernet QSFP+ Optical Interface Board(SG)
            type-LSXM1TGS48SG3(1643),           -- 48-Port 10GBASE-R Ethernet SFP+ Optical Interface Board(SG)
            type-LSQM1FAB04B3(1644),            -- Switching Fabric Module
            type-LSQM1FAB08B3(1645),            -- Switching Fabric Module
            type-LSQM1FAB12B3(1646),            -- Switching Fabric Module
            type-LSXM1SFF08A0(1647),            -- Switching Fabric Board
            type-LSXM1SFF08A1(1648),            -- Switching Fabric Board
            type-LSXM1FWDF1(1649),              -- FW IV Next Generation Firewall Module
            type-LSQM1PT8TSSC0(1650),           -- 8-Port 1G EPON OLT Optical Interface(SFP,SC)+2-Port 10GE Optical Interface Board(SFP+,LC)(SC)
            type-LSQM1PT24TSSC0(1651),          -- 24-Port 1G EPON OLT Optical Interface(SFP,SC)+2-Port 10GE Optical Interface Board(SFP+,LC)(SC)
            type-LSQM1TGS12EC0(1652),           -- 12-Port 10GBASE-R Ethernet SFP+ Optical Interface Board(EC)
            type-LSXM1CGQ32TB1(1653),           -- 32-Port 100GBASE Ethernet Optical Interface Board(QSFP28),Monolithic,LF
            type-LSXM1CGQ48TB1(1654),           -- 48-Port 100GBASE Ethernet Optical Interface Board(QSFP28),Monolithic
            type-LSXM1QGS48TB1(1655),           -- 48-Port 40GBASE Ethernet Optical Interface Board(QSFP+),Monolithic
            type-LSXM1SRT08E1(1656),            -- Switch Fabric Board
            type-LSXM1SRT16E1(1657),            -- Switch Fabric Board
            type-LSXM1SRT02E1(1658),            -- Switch Fabric Board
            type-LSXM1SUP02B1(1659),            -- Supervisor Engine Module
            type-LSUM1SUPC0(1660),              -- Supervisor Engine Board
            type-LSUM1SUPC3(1661),              -- Supervisor Engine Board
            type-LSXM1SUPC3(1662),              -- Supervisor Engine Board
            type-LSQM1GP44TSSE0(1663),          -- 44-Port GE Optical Interface(SFP,LC)+4-Port 10GE Optical Interface Board(SFP+,LC)(SC)
            type-LSQM1GP24TSSE0(1664),          -- 24-Port GE Optical Interface(SFP,LC)+4-Port 10GE Optical Interface Board(SFP+,LC)(SC)
            type-LSQM1GT48SE0(1665),            -- 48-Port 1000Base-T Gigabit Ethernet Interface Board(RJ45)(SC)
            type-LSQM1GV48SE0(1666),            -- 48-Port 1000Base-T Gigabit Ethernet Interface Board(RJ45)(SC)-POE
            type-LSXM1QGS12FX0(1667),           -- 12-Port 40GBASE Ethernet Optical Interface Module(QSFP+)(FX)
            type-LSXM3QGS24FE1(1668),           -- 24-Port 40GBASE Ethernet Optical Interface Module(QSFP+)(FE)
            type-LSXM3QGS24FX1(1669),           -- 24-Port 40GBASE Ethernet Optical Interface Module(QSFP+)(FX)
            type-LSXM3QGS36FX1(1670),           -- 36-Port 40GBASE Ethernet Optical Interface Module(QSFP+)(FX)
            type-LSXM3TGS48FE1(1671),           -- 48-Port 10GBASE Ethernet Optical Interface Module(SFP+,LC)(FX)
            type-LSXM3TGS48FX1(1672),           -- 48-Port 10GBASE Ethernet Optical Interface Module(SFP+,LC)(FX)
            type-LSXM2TGS48FX1(1673),           -- 48-Port 10GBASE Ethernet Optical Interface Module(SFP+,LC)(FX)
            type-LSQM1MPU06B0(1674),            -- Supervisor Engine Board
            type-LSQM1MPU10C0(1675),            -- Supervisor Engine Board
            type-LSQM1FAB06C0(1676),            -- Switching Fabric Module
            type-LSQM1FAB10C0(1677),            -- Switching Fabric Module
            type-LSQM1QGS12SG0(1678),           -- 12-Port 40GBASE-R Ethernet QSFP+ Optical Interface Board(SG)
            type-LSQM1TGS48SG0(1679),           -- 48-Port 10GBASE-R Ethernet SFP+ Optical Interface Board(SG)
            type-LSQM1TGT24SF0(1680),           -- 24-Port 10GBASE-T Ethernet Electrical Interface Board(RJ45)(SF)
            type-LSQM1QGS8A0(1681),             -- 8-Port QSFP+ Module
            type-LSQM1TGS24QSM0(1682),          -- 24-Port SFP+ and 2-Port QSFP+ Module
            type-LSQM1TGT24QSM0(1683),          -- 24-Port 10G BASE-T and 2-Port QSFP+ Module
            type-LSQM1TGS24QSA0(1684),          -- 24-Port SFP+ and 2-Port QSFP+ Module
            type-LSUM1FWCEAB0(1685),            -- Firewall Board
            type-LSQM2GP24TSSA0(1686),          -- 24-Port GE Optical Interface(SFP,LC)+4-Port 10GE Optical Interface Board(SFP+,LC)(SA)
            type-LSQM2GT48SA0(1687),            -- 48-Port 1000Base-T Gigabit Ethernet Interface Board(RJ45)(SA)
            type-LSQM2GP48SA0(1688),            -- 48-Port 1000BASE-X Ethernet Optical Interface Board(SFP,LC)(SA)
            type-LSQM2GP24TSSA3(1689),          -- 24-Port GE Optical Interface(SFP,LC)+4-Port 10GE Optical Interface Board(SFP+,LC)(SA)
            type-LSQM2GT48SA3(1690),            -- 48-Port 1000Base-T Gigabit Ethernet Interface Board(RJ45)(SA)
            type-LSQM2GP48SA3(1691),            -- 48-Port 1000BASE-X Ethernet Optical Interface Board(SFP,LC)(SA)
            type-LSUM2GP24TSSA0(1692),          -- 24-Port GE Optical Interface(SFP,LC)+4-Port 10GE Optical Interface Board(SFP+,LC)(SA)
            type-LSUM2GT48SA0(1693),            -- 48-Port 1000Base-T Gigabit Ethernet Interface Board(RJ45)(SA)
            type-LSUM2GP48SA0(1694),            -- 48-Port 1000BASE-X Ethernet Optical Interface Board(SFP,LC)(SA)
            type-LSXM1SUPT1(1695),              -- Supervisor Engine Module
            type-LSXM1SUP02T1(1696),            -- Supervisor Engine Module
            type-LSXM1SFF16B0(1697),            -- Switch Fabric Board
            type-LSXM4TGS48FX1(1698),           -- 48-Port 10GBASE Ethernet Optical Interface Module(SFP+,LC)(FX)
            type-LSXM4QGS24FX1(1699),           -- 24-Port 40GBASE Ethernet Optical Interface Module(QSFP+)(FX)
            type-LSXM1TGS48FD1(1700),           -- 48-Port 10GBASE Ethernet Optical Interface Module(SFP+,LC)(FD)
            type-LSXM1QGS24FD1(1701),           -- 24-Port 40GBASE Ethernet Optical Interface Module(QSFP+)(FD)
            type-LSXM2QGS24FX1(1702),           -- 24-Port 40GBASE Ethernet Optical Interface Module(QSFP+)(FX)
            type-LSXM1TGS48FD0(1703),           -- 48-Port 10GBASE Ethernet Optical Interface Module(SFP+,LC)
            type-LSXM1QGS24FD0(1704),           -- 24-Port 40GBASE Ethernet Optical Interface Module(QSFP+)(FD)
            type-LSXM2TGS48FX0(1705),           -- 48-Port 10GBASE Ethernet Optical Interface Module(SFP+,LC)(FX)
            type-LSXM2QGS24FX0(1706),           -- 24-Port 40GBASE Ethernet Optical Interface Module(QSFP+)(FX)
            type-LSXM4TGS48FX0(1707),           -- 48-Port 10GBASE Ethernet Optical Interface Module(SFP+,LC)(FX)
            type-LSXM4QGS24FX0(1708),           -- 24-Port 40GBASE Ethernet Optical Interface Module(QSFP+)(FX)
            type-LSXM1TGW48FX1(1709),           -- 48-Port 10GBASE Ethernet WAN Optical Interface Module(SFP+,LC)(FX)
            type-LSUM1MPU10A0(1710),            -- Supervisor Engine Board
            type-LSUM1FAB10A0(1711),            -- Switching Fabric Module
            type-LSUM2TGS32QSSG0(1712),         -- 32-Port 10GBASE-R Ethernet Optical Interface(SFP+,LC)+4-Port 40GBASE-R Ethernet Optical Interface Board(QSFP+,LC)(SG)
            type-LSUM2QGS12SG0(1713),           -- 12-Port 40GBASE-R Ethernet QSFP+ Optical Interface Board(SG)
            type-LSUM2TGS48SG0(1714),           -- 48-Port 10GBASE-R Ethernet SFP+ Optical Interface Board(SG)
            type-LSXM2QGS12SG3(1715),           -- 12-Port 40GBASE-R Ethernet QSFP+ Optical Interface Board(SG)
            type-LSXM2TGS48SG3(1716),           -- 48-Port 10GBASE-R Ethernet SFP+ Optical Interface Board(SG)
            type-LSUM1FWDEC0(1717),             -- Firewall Service Board
            type-LSQM1FWDSC0(1718),             -- Firewall Service Board
            type-LSQM1TGS48RSG0(1719),          -- 48-Port 10GBASE-R Ethernet SFP+ Optical Interface Board(SG)
            type-LSQM2TGS48XSG0(1720),          -- 48-Port 10GBASE-R Ethernet SFP+ Optical Interface Board(SG)
            type-LSQM2QGS12XSG0(1721),          -- 12-Port 40GBASE-R Ethernet QSFP+ Optical Interface Board(SG)
            type-LSQM3GP44TSSC0(1722),          -- 44-Port GE Optical Interface(SFP,LC)+4-Port 10GE Optical Interface Board(SFP+,LC)(SC)
            type-LSXM1CGQ36HB1(1723),           -- 36-Port 100GBASE Ethernet Optical Interface Module(QSFP28)(HB)
            type-LSXM1CGQ36HC1(1724),           -- 36-Port 100GBASE Ethernet Optical Interface Module(QSFP28)(HC)
            type-LSXM1CGQ18QGHB1(1725),         -- 18-Port 100GBASE (QSFP28) + 18-Port 40GBASE Ethernet Optical Interface Module (QSFP+)(HB)
            type-LSXM1CGQ18QGHC1(1726),         -- 18-Port 100GBASE (QSFP28) + 18-Port 40GBASE Ethernet Optical Interface Module (QSFP+)(HC)
            type-LSXM1QGS48HB1(1727),           -- 48-Port 40GBASE Ethernet Optical Interface Module(QSFP+)(HB)
            type-LSXM1QGS48HC1(1728),           -- 48-Port 40GBASE Ethernet Optical Interface Module(QSFP+)(HC)
            type-LSXM1TGS48C2HB1(1729),         -- 48-Port 10G BASE Ethernet Optical Interface(SFP+,LC)+2-Port 100GBASE Ethernet Optical Interface Module(QSFP28)(HB)
            type-LSXM1SFH04D1(1730),            -- Switch Fabric Board,Type H(Class D)
            type-LSXM1SFH08D1(1731),            -- Switch Fabric Board For Type D(F2)
            type-LSXM1SFH12D1(1732),            -- Fabric Module,Type H(Class D)
            type-LSXM1SFH16C1(1733),            -- Switch Fabric Board,Type H(Class C)
            type-LSXM1GP48FD0(1737),            -- 48-Port 1000BASE-X Gigabit Ethernet Optical Interface Module(SFP,LC)(FD)
            type-LSXM1GP48FD1(1738),            -- 48-Port 1000BASE-X Gigabit Ethernet Optical Interface Module(SFP,LC)(FD)
            type-LSXM1GT48FD0(1739),            -- 48-Port 1000Base-T Gigabit Ethernet Interface Module(RJ45)(FD)
            type-LSXM1GT48FD1(1740),            -- 48-Port 1000Base-T Gigabit Ethernet Interface Module(RJ45)(FD)
            type-LSXM1FAB10B0(1741),            -- Switching Fabric Module
            type-LSUM1MPU10A3(1742),            -- Supervisor Engine Board
            type-LSUM1FAB10A3(1743),            -- Switching Fabric Module
            type-LSQM1MPU10A0(1744),            -- Supervisor Engine Board
            type-LSQM1FAB10A0(1745),            -- Switching Fabric Module
            type-LSQM2TGS32QSXSG0(1746),        -- 32-Port 10GBASE-R Ethernet Optical Interface(SFP+,LC)+4-Port 40GBASE-R Ethernet Optical Interface Board(QSFP+,LC)(SG)
            type-LSQM1TGS48RSG3(1747),          -- 48-Port 10GBASE-R Ethernet SFP+ Optical Interface Board(SG)
            type-LSXM2TGS32QSSG3(1748),         -- 32-Port 10GBASE-R Ethernet Optical Interface(SFP+,LC)+4-Port 40GBASE-R Ethernet Optical Interface Board(QSFP+,LC)(SG)
            type-LSUM1NSDEC0(1749),             -- NetStream Service Board
            type-LSQM1NSDSC0(1750),             -- NetStream Service Board
            type-LSQM1QGS4SC0(1751),            -- 4-Port 40G BASE Ethernet Optical Interface Board(QSFP+,MPO)(SC)
            typ-eLSQM2MPUD3(1752),              -- Supervisor Engine Board
            typ-eLSQM3MPUB3(1753),              -- Supervisor Engine Board
            type-LSQM3MPUB4(1754),              -- Supervisor Engine Board
            type-LSQM2MPUDS0(1755),             -- Supervisor Engine Board
            type-LSQM4GV48SA0(1756),            -- 48-Port 1000Base-T Gigabit Ethernet Interface Board(RJ45)(SA)-POE
            type-LSQM1WCMX20(1757),             -- Access Controller Service Board
            type-LSQM1WCMX40(1758),             -- Access Controller Service Board
            type-LSUM1WCMX20RT(1759),           -- Access Controller Service Board
            type-LSUM1WCMX40RT(1760),           -- Access Controller Service Board
            type-LSXM1CGQ18QGHB0(1761),         -- 18-PORT 100GBASE Ethernet Optical Interface (QSFP28)/36-PORT 40GBASE Ethernet Optical Interface Module(QSFP+)(HB)
            type-LSXM1SFH08C0(1762),            -- Fabric Module,Type H(Class C)
            type-LSXM1SFH08C1(1763),            -- Fabric Module,Type H(Class C)
            type-LSXM2SFH16C0(1764),            -- Fabric Module,Type H(Class C)
            type-LSXM2SFH16C1(1765),            -- Fabric Module,Type H(Class C)
            type-LSXM1NSDF1(1766),              -- NetStream Module
            type-LSUM2TGS48SG3(1767),           -- 48-Port 10GBASE-R Ethernet SFP+ Optical Interface Board(SG)
            type-DS-3E7602-MPU(1768),           -- Supervisor Engine Board
            type-DS-3E7606-MPU(1769),           -- Supervisor Engine Board
            type-DS-3E7600-24T4X-SC(1770),      -- 24-Port 1000Base-T Gigabit Ethernet Interface Board(RJ45)+4-Port 10GE Optical Interface Board(SFP+,LC)(SC)
            type-DS-3E7600-24F4X-SA(1771),      -- 24-Port GE Optical Interface(SFP,LC)+4-Port 10GE Optical Interface Board(SFP+,LC)(SA)
            type-DS-3E7600-48T-SA(1772),        -- 48-Port 1000Base-T Gigabit Ethernet Interface Board(RJ45)(SA)
            type-DS-3E7600-48F-SA(1773),        -- 48-Port 1000BASE-X Ethernet Optical Interface Board(SFP,LC)(SA)
            type-DS-3E7600-24F4X-SC(1774),      -- 24-Port GE Optical Interface(SFP,LC)+4-Port 10GE Optical Interface Board(SFP+,LC)(SC)
            type-DS-3E7600-44F4X-SC(1775),      -- 44-Port GE Optical Interface(SFP,LC)+4-Port 10GE Optical Interface Board(SFP+,LC)(SC)
            type-DS-3E7600-48T-SC(1776),        -- 48-Port 1000Base-T Gigabit Ethernet Interface Board(RJ45)(SC)
            type-DS-3E7600-16X-SC(1777),        -- 16-Port 10GE Optical Interface Board(SFP+,LC)(SF)
            type-S7602-MPU(1778),               -- Supervisor Engine Board
            type-S7606-MPU(1779),               -- Supervisor Engine Board
            type-S76-24GT4XFSC(1780),           -- 24-Port 1000Base-T Gigabit Ethernet Interface Board(RJ45)+4-Port 10GE Optical Interface Board(SFP+,LC)(SC)
            type-S76-24GF4XFSA(1781),           -- 24-Port GE Optical Interface(SFP,LC)+4-Port 10GE Optical Interface Board(SFP+,LC)(SA)
            type-S76-48GTSA(1782),              -- 48-Port 1000Base-T Gigabit Ethernet Interface Board(RJ45)(SA)
            type-S76-48GFSA(1783),              -- 48-Port 1000BASE-X Ethernet Optical Interface Board(SFP,LC)(SA)
            type-S76-24GT20GF4XFSC(1784),       -- 24-Port 1000Base-T Gigabit Ethernet Interface Board(RJ45)+20-Port GE Optical Interface(SFP,LC)+4-Port 10GE Optical Interface Board(SFP+,LC)(SC)
            type-LSXM1TGS48C2HB0(1785),         -- 48-PORT 10GBASE Ethernet Optical Interface (SFP+,LC)+2-PORT 100GBASE Ethernet Optical Interface Module(QSFP28)(HB)
            type-LSXM1CGQ18QGHC0(1786),         -- 18-PORT 100GBASE Ethernet Optical Interface (QSFP28)/36-PORT 40GBASE Ethernet Optical Interface Module(QSFP+)(HC)
            type-LSXM1TGS48HB1(1787),           -- 48-Port 10G BASE Ethernet Optical Interface Module(SFP+,LC)(HB)
            type-LSXM1TGS48HB0(1788),           -- 48-Port 10G BASE Ethernet Optical Interface Module(SFP+,LC)(HB)
            type-LSQM1CGP24TSSC0(1789),         -- Supervisor Engine Board With 24-Port 1000BASE-X Ethernet SFP Optical Interface+4-Port 10GBASE-R Ethernet SFP+ Optical Interfaces
            type-LSQM1CGP24TSSA0(1790),         -- Supervisor Engine Board With 24-Port 1000BASE-X Ethernet SFP Optical Interface+4-Port 10GBASE-R Ethernet SFP+ Optical Interfaces
            type-LSQM1CGT24TSSC0(1791),         -- Supervisor Engine Board With 24-Port 10/100/1000BASE-T Ethernet Interface+4-Port 10GBASE-R Ethernet SFP+ Optical Interfaces
            type-LSQM1CGT24TSSA0(1792),         -- Supervisor Engine Board With 24-Port 10/100/1000BASE-T Ethernet Interface+4-Port 10GBASE-R Ethernet SFP+ Optical Interfaces
            type-LSQM2GP24SA0(1793),            -- 24-Port GE Optical Interface(SFP,LC)(SA)
            type-LSX1SUPH1(1794),               -- Supervisor Engine Board
            type-LSX1SUPH0(1795),               -- Supervisor Engine Board
            type-LSX1SUP04H1(1796),             -- Supervisor Engine Board
            type-LSX1SUP04H0(1797),             -- Supervisor Engine Board
            type-LSXM1SFH08D0(1798),            -- Fabric Module,Type H(Class D)
            type-LSXM1SFH04D0(1799),            -- Fabric Module,Type H(Class D)

--
-- 1800 for united assignment
--
            type-LSXM1SFH16C0(1800),            -- Fabric Module,Type H(Class C+)
            type-LSXM1SFH12D0(1801),            -- Fabric Module,Type H(Class D)
            type-LSXM1QGS48HB0(1802),           -- 48-Port 40GBASE Ethernet Optical Interface Module(QSFP+)(HB)
            type-LSXM1QGS48HC0(1803),           -- 36-Port 100GBASE Ethernet Optical Interface Module(QSFP28)(HB)
            type-LSXM1CGQ36HB0(1804),           -- 36-Port 100GBASE Ethernet Optical Interface Module(QSFP28)(HB)
            type-LSXM1TGS48C2HC0(1805),         -- 48-PORT 10GBASE Ethernet Optical Interface (SFP+,LC)+2-PORT 100GBASE Ethernet Optical Interface Module(QSFP28)(HC)
            type-LSQM2GP44TSSE0(1806),          -- 44-Port GE Optical Interface(SFP,LC)+4-Port 10GE Optical Interface Board(SFP+,LC)(SE)
            type-LSQM2GP24TSSA8(1807),          -- 24-Port GE Optical Interface(SFP,LC)+4-Port 10GE Optical Interface Board(SFP+,LC)(SA)
            type-LSQM2GT48SA8(1808),            -- 48-Port 1000Base-T Gigabit Ethernet Interface Board(RJ45)(SA)
            type-LSQM2GP48SA8(1809),            -- 48-Port 1000BASE-X Ethernet Optical Interface Board(SFP,LC)(SA)
            type-EWPXM1CGP24TSSC0(1810),        -- Supervisor Engine Board With 24-Port 1000BASE-X Ethernet SFP Optical Interface+4-Port 10GBASE-R Ethernet SFP+ Optical Interfaces
            type-EWPXM3MPUB0(1811),             -- Supervisor Engine Board
            type-EWPXM2MPUDS0(1812),            -- Supervisor Engine Board
            type-EWPXM2TGS16SF0(1813),          -- 16-Port 10GE Optical Interface Board(SFP+,LC)(SF)
            type-EWPXM2GP44TSSC0(1814),         -- 44-Port GE Optical Interface(SFP,LC)+4-Port 10GE Optical Interface Board(SFP+,LC)(SC)
            type-EWPXM2GP24TSSC0(1815),         -- 24-Port GE Optical Interface(SFP,LC)+4-Port 10GE Optical Interface Board(SFP+,LC)(SC)
            type-EWPXM1MAC0F(1816),             -- Access Controller Service Board
            type-LSQM1CGP24TSSA8(1817),         -- Supervisor Engine Board With 24-Port 1000BASE-X Ethernet SFP Optical Interface+4-Port 10GBASE-R Ethernet SFP+ Optical Interfaces
            type-LSQM1CGT24TSSA8(1818),         -- Supervisor Engine Board With 24-Port 10/100/1000BASE-T Ethernet Interface+4-Port 10GBASE-R Ethernet SFP+ Optical Interfaces
            type-LSWM1FWD0(1819),               -- Firewall Service Board
            type-LSUM2MPU10C0(1820),            -- Supervisor Engine Board
            type-LSQM2MPU10C0(1821),            -- Supervisor Engine Board
            type-LSUM2MPU10C3(1822),            -- Supervisor Engine Board
            type-LSUM2FAB10C0(1823),            -- Switching Fabric Module
            type-LSQM2FAB10C0(1824),            -- Switching Fabric Module
            type-LSUM2FAB10C3(1825),            -- Switching Fabric Module
            type-LSUM2CQGS12SG0(1826),          -- 12-Port 40GBASE-R QSFP+ or 4-Port 100GBASE-R QSFP28 Optical Interface Board(SG)
            type-LSXM2CQGS12SG3(1827),          -- 12-Port 40GBASE-R QSFP+ or 4-Port 100GBASE-R QSFP28 Optical Interface Board(SG)
            type-LSQM2CQGS12XSG0(1828),         -- 12-Port 40GBASE-R QSFP+ or 4-Port 100GBASE-R QSFP28 Optical Interface Board(SG)
            type-LSQM1CQGS12SG0(1829),          -- 12-Port 40GBASE-R QSFP+ or 4-Port 100GBASE-R QSFP28 Optical Interface Board(SG)
            type-LSXM1CGQ6QGHB0(1830),          -- 6-Port 100GBASE Ethernet Optical Interface(QSFP28)/12-Port 40GBASE Ethernet Optical Interface Module(QSFP+)(HB)
            type-LSXM1CGQ6QGHB1(1831),          -- 6-Port 100GBASE Ethernet Optical Interface(QSFP28)/12-Port 40GBASE Ethernet Optical Interface Module(QSFP+)(HB)
            type-LSXM1CGQ6QGHC0(1832),          -- 6-Port 100GBASE Ethernet Optical Interface(QSFP28)/12-Port 40GBASE Ethernet Optical Interface Module(QSFP+)(HC)
            type-LSXM1QGS36HB0(1833),           -- 36-Port 40GBASE Ethernet Optical Interface Module(QSFP+)(HB)
            type-LSXM1QGS36HB1(1834),           -- 36-Port 40GBASE Ethernet Optical Interface Module(QSFP+)(HB)
            type-LSXM1QGS36HC0(1835),           -- 36-Port 40GBASE Ethernet Optical Interface Module(QSFP+)(HC)
            type-LSXM1SUPC0(1836),              -- Supervisor Engine Unit
            type-LSXM1SUPC1(1837),              -- Supervisor Engine Unit
            type-LSXM1SUP04H0(1838),            -- Supervisor Engine Unit
            type-LSXM1SUP04H1(1839),            -- Supervisor Engine Unit
            type-LSXM1SUPH0(1840),              -- Supervisor Engine Unit
            type-LSXM1SUPH1(1841),              -- Supervisor Engine Unit
            type-EWPXM2WCMD0F(1842),            -- 20G Access Controller Module
            type-LSUM2QGS24RSG0(1843),          -- 24-Port 40GBASE-R Ethernet QSFP+ Optical Interface Board(SG)
            type-LSQM1QGS24RSG0(1844),          -- 24-Port 40GBASE-R Ethernet QSFP+ Optical Interface Board(SG)
            type-LSXM2QGS24RSG3(1845),          -- 24-Port 40GBASE-R Ethernet QSFP+ Optical Interface Board(SG)
            type-LSQM2QGS24RXSG0(1846),         -- 24-Port 40GBASE-R Ethernet QSFP+ Optical Interface Board(SG)
            type-LSQM2TGS48RSG0(1847),          -- 48-Port 10GBASE-R Ethernet SFP+ Optical Interface Board(SG)
            type-LSXM1X86SUPE0(1848),           -- Cloud Supervisor Engine Unit
            type-LSXM1X86SUPE1(1849),           -- Cloud Supervisor Engine Unit
            type-LSQM1CGS2QSA0(1850),           -- 2-Port 100G Ethernet Optical Interface(QSFP28)+2-Port 40G Ethernet Optical Interface Module(QSFP+)
            type-LSUM1ACGDEC0(1851),            -- Application Control Module
            type-LSQM1ACGDSC0(1852),            -- Application Control Module
            type-LSXM1CGQ36HF1(1853),           -- 36-Port 100GBASE Ethernet Optical Interface Module(QSFP28)(HF)
            type-LSXM1QGS48HF1(1854),           -- 48-Port 40GBASE Ethernet Optical Interface Module(QSFP+)(HF)
            type-LSXM1CGQ18QGHF1(1855),         -- 18-PORT 100GBASE Ethernet Optical Interface(QSFP28)/36-Port 40GBASE Ethernet Optical Interface Module(QSFP+)(HF)
            type-LSXM1QGS36HF1(1856),           -- 36-Port 40GBASE Ethernet Optical Interface Module(QSFP+)(HF)
            type-LSXM1CGQ6QGHF1(1857),          -- 6-Port 100GBASE Ethernet Optical Interface(QSFP28)/12-Port 40GBASE Ethernet Optical Interface Module(QSFP+)(HF)
            type-LSXM1QGS48HF0(1858),           -- 48-Port 40GBASE Ethernet Optical Interface Module(QSFP+)(HF)
            type-LSXM1CGQ18QGHF0(1859),         -- 18-PORT 100GBASE Ethernet Optical Interface(QSFP28)/36-Port 40GBASE Ethernet Optical Interface Module(QSFP+)(HF)
            type-LSXM1CGQ6QGHF0(1860),          -- 6-Port 100GBASE Ethernet Optical Interface(QSFP28)/12-Port 40GBASE Ethernet Optical Interface Module(QSFP+)(HF)
            type-LSXM1TGS48HF0(1861),           -- 48-Port 10GBASE Ethernet Optical Interface Module(SFP+,LC)(HF)
            type-LSXM1TGS48HF1(1862),           -- 48-Port 10GBASE Ethernet Optical Interface Module(SFP+,LC)(HF)
            type-LSQM1GP24FC3(1863),            -- 24-Port 1000BASE-X Optical Interface Board(SFP,LC)
            type-LSQM1GP24FD3(1864),            -- 24-Port 1000BASE-X Optical Interface Board(SFP,LC)
            type-LSQM1GP24TSFC3(1865),          -- 24-Port 1000BASE-X Optical Interface(SFP,LC)+4-Port 10GBASE-R Ethernet Optical Interface Board(SFP+,LC)
            type-LSQM1GP24TSFD3(1866),          -- 24-Port 1000BASE-X Optical Interface(SFP,LC)+4-Port 10GBASE-R Ethernet Optical Interface Board(SFP+,LC)
            type-LSQM1GP40TS8FD0(1867),         -- 40-Port 1000BASE-X Optical Interface(SFP,LC)+8-Port 10GBASE-R Ethernet Optical Interface Board(SFP+,LC)
            type-LSQM1GP48FC3(1868),            -- 48-Port 1000BASE-X Optical Interface Board(SFP,LC)
            type-LSQM1GP48FD0(1869),            -- 48-Port 1000BASE-X Optical Interface Board(SFP,LC)
            type-LSQM1GP48FD3(1870),            -- 48-Port 1000BASE-X Optical Interface Board(SFP,LC)
            type-LSQM1GT48FC3(1871),            -- 48-Port 10/100/1000BASE-T Electrical Interface Board(RJ45)
            type-LSQM1GT48FD0(1872),            -- 48-Port 10/100/1000BASE-T Electrical Interface Board(RJ45)
            type-LSQM1GT48FD3(1873),            -- 48-Port 10/100/1000BASE-T Electrical Interface Board(RJ45)
            type-LSQM1TGS24FC3(1874),           -- 24-Port 10GBASE-R Ethernet Optical Interface Board(SFP+,LC)
            type-LSQM1TGS24FD0(1875),           -- 24-Port 10GBASE-R Ethernet Optical Interface Board(SFP+,LC)
            type-LSQM1TGS24FD3(1876),           -- 24-Port 10GBASE-R Ethernet Optical Interface Board(SFP+,LC)
            type-LSQM1TGS24XFD0(1877),          -- 24-Port 10GBASE-R Ethernet Optical Interface Board(SFP+,LC)
            type-LSQM1TGS48RFE0(1878),          -- 48-Port 10GBASE-R Ethernet Optical Interface Board(SFP+,LC)
            type-LSQM1TGS8FC3(1879),            -- 8-Port 10GBASE-R Ethernet Optical Interface Board(SFP+,LC)
            type-LSQM1TGS8FD3(1880),            -- 8-Port 10GBASE-R Ethernet Optical Interface Board(SFP+,LC)
            type-LSUM1GP40TS8FD0(1881),         -- 40-Port 1000BASE-X Optical Interface(SFP,LC)+8-Port 10GBASE-R Ethernet Optical Interface Board(SFP+,LC)
            type-LSUM1GP48FD0(1882),            -- 48-Port 1000BASE-X Optical Interface Board(SFP,LC)
            type-LSUM1GP48FD3(1883),            -- 48-Port 1000BASE-X Optical Interface Board(SFP,LC)
            type-LSUM1GT48FD0(1884),            -- 48-Port 10/100/1000BASE-T Electrical Interface Board(RJ45)
            type-LSUM1GT48FD3(1885),            -- 48-Port 10/100/1000BASE-T Electrical Interface Board(RJ45)
            type-LSUM1TGS24FD0(1886),           -- 24-Port 10GBASE-R Ethernet Optical Interface Board(SFP+,LC)
            type-LSUM1TGS24FD3(1887),           -- 24-Port 10GBASE-R Ethernet Optical Interface Board(SFP+,LC)
            type-LSXM1GP40TS8FD0(1888),         -- 40-Port 1000BASE-X Optical Interface(SFP,LC)+8-Port 10GBASE-R Ethernet Optical Interface Board(SFP+,LC)
            type-LSXM1GT48FD3(1889),            -- 48-Port 10/100/1000BASE-T Electrical Interface Board(RJ45)
            type-LSXM1TGS24FD3(1890),           -- 24-Port 10GBASE-R Ethernet Optical Interface Board(SFP+,LC)
            type-LSQM1MPUS10C3(1891),           -- Supervisor Engine Board
            type-LSQM1MPUSA3(1892),             -- Supervisor Engine Board
            type-LSQM2SUPA3(1893),              -- Supervisor Engine Board
            type-LSXM1SFH16E1(1894),            -- Fabric Module,Type H(Class E)
            type-LSXM1SFH16E0(1895),            -- Fabric Module,Type H(Class E)
            type-LSXM1GP40TS8FD3(1896),         -- 40-Port 1000BASE-X Optical Interface(SFP,LC)+8-Port 10GBASE-R Ethernet Optical Interface Board(SFP+,LC)
            type-LSQM1MPUS10C0(1897),           -- Supervisor Engine Board
            type-LSQM1MPUSA0(1898),             -- Supervisor Engine Board
            type-LSQM2SUPA0(1899),              -- Supervisor Engine Board
            type-LSQM1TGS16FC3(1900),           -- 16-Port 10GBASE-R Ethernet SFP+ Optical Interface Board(FC)
            type-LSQM1TGS16FD0(1901),           -- 16-Port 10GBASE-R Ethernet SFP+ Optical Interface Board(FD)
            type-LSQM1TGS16FD3(1902),           -- 16-Port 10GBASE-R Ethernet SFP+ Optical Interface Board(FD)
            type-LSQM2TGS48SG0(1903),           -- 48-Port 10GBASE-R Ethernet SFP+ Optical Interface Board(SG)
            type-LSQM2TGS48SG3(1904),           -- 48-Port 10GBASE-R Ethernet SFP+ Optical Interface Board(SG)
            type-LSXM1CGQ48HB1(1905),           -- 48-Port 100GBASE Ethernet Optical Interface Module(QSFP+)(HB)
            type-LSQM1MPUS06A8(1906),           -- Supervisor Engine Board
            type-LSQM1TGS16FD8(1907),           -- 16-Port 10GBASE-R Ethernet SFP+ Optical Interface Board(FD)
            type-LSXM1SFH08E1(1908),            -- Fabric Module,Type H(Class E)
            type-LSXM1SFH08CC0(1909),           -- Fabric Module,Type H(Class C)
            type-LSXM1SUP08C0(1910),            -- Supervisor Engine Unit
            type-LSUM2FAB04D0(1911),            -- Switching Fabric Module
            type-LSUM2FAB04D3(1912),            -- Switching Fabric Module
            type-LSXM2FAB04D3(1913),            -- Switching Fabric Module
            type-LSUM2FAB04B0(1914),            -- Switching Fabric Module
            type-LSUM2FAB04B3(1915),            -- Switching Fabric Module
            type-LSUM2FAB08D0(1916),            -- Switching Fabric Module
            type-LSUM2FAB08D3(1917),            -- Switching Fabric Module
            type-LSXM2FAB08D3(1918),            -- Switching Fabric Module
            type-LSUM2FAB08B0(1919),            -- Switching Fabric Module
            type-LSUM2FAB08B3(1920),            -- Switching Fabric Module
            type-LSUM2FAB12D0(1921),            -- Switching Fabric Module
            type-LSUM2FAB12D3(1922),            -- Switching Fabric Module
            type-LSXM2FAB12D3(1923),            -- Switching Fabric Module
            type-LSUM2FAB12B0(1924),            -- Switching Fabric Module
            type-LSUM2FAB12B3(1925),            -- Switching Fabric Module
            type-LSQM1CGS2FE0(1926),            -- 2-Port 100GBASE-R Ethernet QSFP28 Optical Interface Board(FE)
            type-LSQM1CGS2FE3(1927),            -- 2-Port 100GBASE-R Ethernet QSFP28 Optical Interface Board(FE)
            type-LSQM1CGS2XFE0(1928),           -- 2-Port 100GBASE-R Ethernet QSFP28 Optical Interface Board(FE)
            type-LSUM1CGS2FE0(1929),            -- 2-Port 100GBASE-R Ethernet QSFP28 Optical Interface Board(FE)
            type-LSUM1CGS2FE3(1930),            -- 2-Port 100GBASE-R Ethernet QSFP28 Optical Interface Board(FE)
            type-LSXM1CGS2FE3(1931),            -- 2-Port 100GBASE-R Ethernet QSFP28 Optical Interface Board(FE)
            type-LSUM1TGS16FD0(1932),           -- 16-Port 10GBASE-R Ethernet SFP+ Optical Interface Board(FD)
            type-LSUM1TGS16FD3(1933),           -- 16-Port 10GBASE-R Ethernet SFP+ Optical Interface Board(FD)
            type-LSQM1TGS16XFD0(1934),          -- 16-Port 10GBASE-R Ethernet SFP+ Optical Interface Board(FD)
            type-LSQM1GP40TS8FC3(1935),         -- 40-Port 1000BASE-X Optical Interface(SFP,LC)+8-Port 10GBASE-R Ethernet Optical Interface Board(SFP+,LC)
            type-S76-16XFSF(1936),              -- 16-Port 10GE Optical Interface Board(SFP+,LC)(SF)
            type-S76-24EP2XFSC-OLT(1937),       -- 24-Port 1G EPON OLT Optical Interface(SFP,SC)+2-Port 10GE Optical Interface Board(SFP+,LC)(SC)
            type-DS-3E7600-24T20F4X-SC(1938),   -- 24-Port 1000Base-T Gigabit Ethernet Interface Board(RJ45)+20-Port GE Optical Interface(SFP,LC)+4-Port 10GE Optical Interface Board(SFP+,LC)(SC)
            type-LSUM1FAB04E0(1939),            -- Switching Fabric Module
            type-LSUM1FAB08E0(1940),            -- Switching Fabric Module
            type-LSUM1FAB12E0(1941),            -- Switching Fabric Module
            type-LSXM1CGQ8FX1(1942),            -- 8-Port 100GBASE Ethernet Optical Interface Module(QSFP28)(FX)
            type-LSQM1IPSDSC0(1943),            -- Intrusion Prevention System Module
            type-LSQM2ACGDSC0(1944),            -- Application Control Module
            type-LSQM1ADEDSC0(1945),            -- Load Balancing Module
            type-LSWM1ADED0(1946),              -- Load Balancing Card
            type-LSWM1IPSD0(1947),              -- Intrusion Prevention System Card
            type-LSQM1GP40TS8FD3(1948),         -- 40-Port 1000BASE-X Optical Interface(SFP,LC)+8-Port 10GBASE-R Ethernet Optical Interface Board(SFP+,LC)
            type-LSUM1SUPXD0(1949),             -- Supervisor Engine Board
            type-LSUM1CQGS32SF0(1950),          -- 32-Port 40GBASE-R QSFP+ or 16-Port 100GBASE-R QSFP28 Optical Interface Board(SF)
            type-LSUM1TGS48XSG0(1951),          -- 48-Port 10GBASE-R Ethernet SFP+ Optical Interface Board(SG)
            type-LSUM1FAB08XE0(1952),           -- Switching Fabric Module
            type-LSUM1FAB16XD0(1953),           -- Switching Fabric Module
            type-LSXM1SFH02E0(1954),            -- Switching Fabric Module
            type-LSXM1SFH02E1(1955),            -- Switching Fabric Module
            type-LSXM1SFH12C0(1956),            -- Fabric Module,Type H(Class C)
            type-LSXM1SFH12C1(1957),            -- Fabric Module,Type H(Class C)
            type-LSUM1CQGS12XSG0(1958),         -- 12-Port 40GBASE-R QSFP+ or 4-Port 100GBASE-R QSFP28 Optical Interface Board(SG)
            type-LSQM1CTGS24QSFD0(1959),        -- Supervisor Engine Board With 24-Port 10GBASE-R SFP+ Optical Interface+2-Port 40GBASE-R QSFP+ Optical Interfaces or 1-Port 100GBASE-R QSFP28 Optical Interfaces
            type-LSQM1TGS24QSFD0(1960),         -- 24-Port 10GBASE-R Optical Interface(SFP+,LC)+2-Port 40GBASE-R Optical Interface Board(QSFP+) or 1-Port 100GBASE-R Optical Interface Board(QSFP28)
            type-LSUM1WBCZ720RT(1961),          -- Access Controller Service Board
            type-LSQM1WBCZ720(1962),            -- Access Controller Service Board
            type-DS-3E7610X-MPU(1963),          -- Supervisor Engine Board
            type-DS-3E7610X-CLOS(1964),         -- Switching Fabric Module
            type-DS-3E7610X-32X4QX-SF(1965),    -- 32-Port 10GBASE-R Ethernet Optical Interface(SFP+,LC)+4-Port 40GBASE-R Ethernet Optical Interface Board(QSFP+,LC)(SF)
            type-DS-3E7610X-16X-SF(1966),       -- 16-Port 10GBASE-R Ethernet SFP+ Optical
            type-DS-3E7610X-44F4X-SE(1967),     -- 44-Port GE Optical Interface(SFP,LC)+4-Port 10GE Optical Interface Board(SFP+,LC)(SE)
            type-DS-3E7610X-48T-SE(1968),       -- 48-Port 1000Base-T Gigabit Ethernet Interface Board(RJ45)(SE)
            type-LSQM2GT24PTSSC8(1969),         -- 24-Port 1000Base-T Gigabit Ethernet Interface Board(RJ45)+20-Port GE Optical Interface(SFP,LC)+4-Port 10GE Optical Interface Board(SFP+,LC)(SC)
            type-LSQM1CGP24TSSC8(1970),         -- Supervisor Engine Board With 24-Port 1000BASE-X Ethernet SFP Optical Interface+4-Port 10GBASE-R Ethernet SFP+ Optical Interfaces
            type-LSQM1CGT24TSSC8(1971),         -- Supervisor Engine Board With 24-Port 10/100/1000BASE-T Ethernet Interface+4-Port 10GBASE-R Ethernet SFP+ Optical Interfaces
            type-LSQM1MPUS06B8(1972),           -- Supervisor Engine Board
            type-LSVM1MPUB1(1973),              -- Supervisor Engine Unit
            type-LSXM1TGS24QGMODHB0(1974),      -- 24-Port 10GBASE Ethernet Optical Interface(SFP+,LC)+4-Port 40GBASE Ethernet Optical Interface Module(QSFP+)(HB),With 1 Expansion Slot
            type-LSXM1TGS24QGMODHB1(1975),      -- 24-Port 10GBASE Ethernet Optical Interface(SFP+,LC)+4-Port 40GBASE Ethernet Optical Interface Module(QSFP+)(HB),With 1 Expansion Slot
            type-LSXM1TGS48QGHA0(1976),         -- 48-Port 10GBASE Ethernet Optical Interface(SFP+,LC)+4-Port 40GBASE Ethernet Optical Interface Module(QSFP+)(HA)
            type-LSXM1TGS48QGHA1(1977),         -- 48-Port 10GBASE Ethernet Optical Interface(SFP+,LC)+4-Port 40GBASE Ethernet Optical Interface Module(QSFP+)(HA)
            type-LSXM1CGC2A0(1978),             -- 2-Ports 100G CFP Ethernet Optical Interface Module(CFP)
            type-LSXM1CGC2A1(1979),             -- 2-Ports 100G CFP Ethernet Optical Interface Module(CFP)
            type-LSQM2FWDSC0(1980),             -- Firewall Service Board
            type-LSQM1XPT12TSFD0(1981),         -- 12-Port 10/1GBASE EPON OLT Optical Interface(XFP,LC)+8-Port 10GBASE-R Ethernet Optical Interface Board(SFP+,LC)
            type-LSXM1QGS24HB0(1982),           -- 24-Port 40GBASE Ethernet Optical Interface Module(QSFP+)(HB)
            type-LSXM1QGS24HB1(1983),           -- 24-Port 40GBASE Ethernet Optical Interface Module(QSFP+)(HB)
            type-LSXM1QGS24HC0(1984),           -- 24-Port 40GBASE Ethernet Optical Interface Module(QSFP+)(HC)
            type-LSXM1SUP01B1(1985),            -- Supervisor Engine Board
            type-LSCM1SUP03A0(1986),            -- Supervisor Engine Board
            type-LSCM1SUP03A0-Z(1987),          -- Supervisor Engine Board
            type-LSCM1MPUS06A0(1988),           -- Supervisor Engine Board
            type-LSCM1MPUS06A0-Z(1989),         -- Supervisor Engine Board
            type-LSCM1GT48SC0(1990),            -- 48-Port 10/100/1000BASE-T Electrical Interface Board(RJ45)(SC)
            type-LSCM1GT48SC0-Z(1991),          -- 48-Port 10/100/1000BASE-T Electrical Interface Board(RJ45)(SC)
            type-LSCM1TGS48SE0(1992),           -- 48-Port 10GBASE-R Ethernet SFP+ Optical Interface Board(SE)
            type-LSCM1TGS48SE0-Z(1993),         -- 48-Port 10GBASE-R Ethernet SFP+ Optical Interface Board(SE)
            type-LSCM1QGS8CSSE0(1994),          -- 8-Port 40GBASE-R QSFP+ + 4-Port 100GBASE-R QSFP28 Optical Interface Board(SE)
            type-LSCM1QGS8CSSE0-Z(1995),        -- 8-Port 40GBASE-R QSFP+ + 4-Port 100GBASE-R QSFP28 Optical Interface Board(SE)
            type-LSWM2SP4P(1996),               -- 4-Port 10GBASE-R Ethernet SFP+ Optical Interface Module
            type-LSWM2SP4P-Z(1997),             -- 4-Port 10GBASE-R Ethernet SFP+ Optical Interface Module
            type-LSQM1MPUS10B0(1998),           -- Supervisor Engine Board
            type-LSQM1MPUS10B3(1999),           -- Supervisor Engine Board
            type-LSQM1MPUSC0(2000),             -- Supervisor Engine Board
            type-LSQM1MPUSC3(2001),             -- Supervisor Engine Board
            type-LSQM2GP24TSSC8(2002),          -- 24-Port 1000BASE-X Optical Interface(SFP,LC)+4-Port 10GBASE-R Ethernet Optical Interface Board(SFP+,LC)(SC)
            type-LSQM2GT24TSSC8(2003),          -- 24-Port 10/100/1000BASE-T Electrical Interface(RJ45)+4-Port 10GBASE-R Ethernet Optical Interface Board(SFP+,LC)(SC)
            type-LSXM1TGS24CGMODHD0(2004),      -- 24-Port 10GBASE Ethernet Optical Interface(SFP+,LC)+4-Port 100GBASE Ethernet Optical Interface Module(QSFP28)(HD),With 1 Expansion Slot
            type-LSXM1TGS24CGMODHD1(2005),      -- 24-Port 10GBASE Ethernet Optical Interface(SFP+,LC)+4-Port 100GBASE Ethernet Optical Interface Module(QSFP28)(HD),With 1 Expansion Slot
            type-LSQM1TGS16GPSA0(2006),         -- 24-Port 1000BASE-R Ethernet Optical Interface(SFP,LC)+16-Port 10GBASE-R Ethernet Optical Interface Board(SFP+,LC)
            type-EWPXM2TGS48SG0(2007),          -- 48-Port 10GBASE-R Ethernet SFP+ Optical Interface Board(SG)
            type-EWPXM1TGS16FD0(2008),          -- 16-Port 10GBASE-R Ethernet SFP+ Optical Interface Board(FD)
            type-LSXM1CGQ36HF0(2009),           -- 36-Port 100GBASE Ethernet Optical Interface Module(QSFP28)(HF)
            type-LSXM2SUPT0(2010),              -- Supervisor Engine Board
            type-LSXM2SUPT1(2011),              -- Supervisor Engine Board
            type-LSXM1SFT16E0(2012),            -- Switch Fabric Board
            type-LSXM1SFT16E1(2013),            -- Switch Fabric Board
            type-lsxM1CGQ36TD0(2014),           -- 36-Port 100GBASE Ethernet Optical Interface Board(QSFP28)
            type-lsxM1CGQ36TD1(2015),           -- 36-Port 100GBASE Ethernet Optical Interface Board(QSFP28)
            type-LSQM1TGT24FD0(2016),           -- 24-Port 10GBASE-T Ethernet Copper Interface Module(RJ45)(FD)
            type-LSUM1TGT24FD0(2017),           -- 24-Port 10GBASE-T Ethernet Copper Interface Module(RJ45)(FD)
            type-LSXM2SFT08E0(2018),            -- Fabric Module,Type T(Class E)
            type-LSXM2SFT08E1(2019),            -- Fabric Module,Type T(Class E)
            type-LSXM1CCP8HF0(2020),            -- 8-Port 200GBASE Ethernet Optical Interface Module(CFP2)(HF)
            type-LSXM1CCP8HF1(2021),            -- 8-Port 200GBASE Ethernet Optical Interface Module(CFP2)(HF)

            type-LSUM1TFGS24CSSH0(2026),        -- 24-Port 25G Ethernet Optical Interface(SFP28)+4-Port 100G Ethernet Optical Interface Module(QSFP28)(SH)

            type-S8610-MPU(2028),               -- Supervisor Engine Board
            type-S8610-NET(2029),               -- Switching Fabric Module
            type-S86-44GF4XFSE(2030),           -- 44-Port GE Optical Interface(SFP,LC)+4-Port 10GE Optical Interface Board(SFP+,LC)(SE)
            type-S86-48GTSE(2031),              -- 48-Port 1000Base-T Gigabit Ethernet Interface Board(RJ45)(SE)
            type-S86-12QFSG(2032),              -- 12-Port 40GBASE-R Ethernet QSFP+ Optical Interface Board(SG)
            type-S86-48XFSG(2033),              -- 48-Port 10GBASE-R Ethernet SFP+ Optical Interface Board(SG)
            type-LSUM1MPUS06XEC0(2034),         -- Supervisor Engine Board
            type-LSUM1MPUS10XE0(2035),          -- Supervisor Engine Board
            type-LSUM1MPUS10XEB0(2036),         -- Supervisor Engine Board
            type-LSUM1FAB06XEC0(2037),          -- Switch Fabric Board
            type-LSUM1FAB10XE0(2038),           -- Switch Fabric Board
            type-LSUM1FAB10XEB0(2039),          -- Switch Fabric Board
            type-LSUM1FAB08XEB0(2040),          -- Switch Fabric Board
            type-LSUM1TGS48SH0(2041),           -- 48-Port 10G Ethernet Optical Interface Module(SFP+,LC)(SH)
            type-LSUM1CGS8SH0(2042),            -- 8-Port 100G Ethernet Optical Interface Module(QSFP28)(SH)
            type-LSUM1YGS24CSSH0(2043),         -- 24-Port 25G Ethernet Optical Interface(SFP28,LC)+4-Port 100G Ethernet Optical Interface Module(QSFP28)(SH)
            type-LSUM1CGS20XSH0(2044),          -- 20-Port 100G Ethernet Optical Interface Module(QSFP28)(SH)
            type-LSUM1CGS32XSH0(2045),          -- 32-Port 100G Ethernet Optical Interface Module(QSFP28)(SH)
            type-LSUM1CGS8QSSH0(2046),          -- 8-Port 100G Ethernet Optical Interface Module(QSFP28) +8-port 40G/4-Port 100G Ethernet Optical Interface Module(QSFP28)(SH)
            type-LSUM1YGS48XSH0(2047),          -- 48-Port 25G Ethernet Optical Interface(SFP28,LC)(SH)
            type-LSXM3SUPT1(2048),              -- Type-H Supervisor Engine Unit
            type-LSXM4SUPT1(2049),              -- Type-T Supervisor Engine Unit
            type-LSQM2GP24TSSA0-Z(2050),        -- 24-Port GE Optical Interface(SFP,LC)+4-Port 10GE Optical Interface Board(SFP+,LC)(SA)
            type-LSQM2GT48SA0-Z(2051),          -- 48-Port 1000Base-T Gigabit Ethernet Interface Board(RJ45)(SA)
            type-LSQM2GP48SA0-Z(2052),          -- 48-Port 1000BASE-X Ethernet Optical Interface Board(SFP,LC)(SA)
            type-LSUM2TGS48SG0-Z(2053),         -- 48-Port 10GBASE-R Ethernet SFP+ Optical Interface Board(SG)
            type-LSUM2QGS12SG0-Z(2054),         -- 12-Port 40GBASE-R Ethernet QSFP+ Optical Interface Board(SG)
            type-LSUM2TGS32QSSG0-Z(2055),       -- 32-Port 10GBASE-R Ethernet Optical Interface(SFP+,LC)+4-Port 40GBASE-R Ethernet Optical Interface Board(QSFP+,LC)(SG)
            type-LSUM1TGS48RSH0(2056),          -- 48-Port 10GBASE-R Ethernet Optical Interface Module(SFP+,LC)(SH)
            type-LSUM1MPUS06XEB0(2057),         -- Supervisor Engine Board
            type-LSUM1MPUS10XEA0(2058),         -- Supervisor Engine Board
            type-LSUM1FAB06XEB0(2059),          -- Switch Fabric Board
            type-LSUM1FAB10XEA0(2060),          -- Switch Fabric Board

            type-LSXM1CGQ8TD1(2064),            -- 8-Port 100GBASE  Ethernet Optical Interface Board(QSFP28)
            type-LSXM1CGQ12TD1(2065),           -- 12-Port 100GBASE  Ethernet Optical Interface Board(QSFP28)
            type-LSXM1CGQ18TD1(2066),           -- 18-Port 100GBASE  Ethernet Optical Interface Board(QSFP28)
            type-LSXM1QGS24C6TD1(2067),         -- 24-Port 40GBASE Ethernet Optical Interface Module (QSFP+) + 6-Port 100GBASE (QSFP28)
            type-LSXM1QGS36TD1(2068),           -- 36-Port 40GBASE Ethernet Optical Interface Module(QSFP+)
            type-LSXM1QGS48TD1(2069),           -- 48-Port 40GBASE Ethernet Optical Interface Module(QSFP+)
            type-LSXM1TGS48C4TD1(2070),         -- 48-Port 10GBASE Ethernet Optical Interface(SFP+,LC)+4-Port 100GBASE Ethernet Optical Interface Module(QSFP28)
            type-LSXM1GP48TD1(2071),            -- 48-Port GE BASE Ethernet Optical Interface Module(SFP,LC))
            type-LSXM1TGS48TD1(2072),           -- 48-Port 10G BASE Ethernet Optical Interface Module(SFP+,LC))

            type-LSQM2FWDSC8(2077),             -- Firewall Service Board
            type-IM-MSEX-B(2080),               -- Service Processing Unit(IM-MSEX-B)
            type-IM-MSEX-B-IM-SP-B(2081),       -- Service Processing Unit + Universal Line Processing Interface Card(IM-MSEX-B-IM-SP-B)
            type-LSUM1MPUS06XEC0-Z(2082),       -- Supervisor Engine Board
            type-LSUM1CGS8SH0-Z(2083),          -- 8-Port 100G Ethernet Optical Interface Module(QSFP28)(SH)
            type-LSUM1SUPXD0-Z(2084),           -- Supervisor Engine Board
            type-LSUM1FAB08XE0-Z(2085),         -- Switching Fabric Module
            type-LSUM1CGS20XSH0-Z(2086),        -- 20-Port 100G Ethernet Optical Interface Module(QSFP28)(SH)
            type-LSUM1FAB06XEC0-Z(2087),        -- Switch Fabric Board
            type-LSUM1CQGS32SF0-Z(2088),        -- 32-Port 40GBASE-R QSFP+ or 16-Port 100GBASE-R QSFP28 Optical Interface Board(SF)
            type-LSXM1FAB10XE3(2089),           -- Switch Fabric Board
            type-LSXM1FAB08XE3(2090),           -- Switching Fabric Module
            type-LSXM1YGS48XSH3(2091),          -- 48-Port 25G Ethernet Optical Interface(SFP28,LC)(SH)
            type-LSXM1YGS24CSSH3(2092),         -- 24-Port 25G Ethernet Optical Interface(SFP28,LC)+4-Port 100G Ethernet Optical Interface Module(QSFP28)(SH)
            type-LSXM1CGS8QSSH3(2093),          -- 8-Port 100G Ethernet Optical Interface Module(QSFP28) +8-port 40G/4-Port 100G Ethernet Optical Interface Module(QSFP28)(SH)
            type-LSXM1TGS48SH3(2094),           -- 48-Port 10G Ethernet Optical Interface Module(SFP+,LC)(SH)
            type-LSXM1MPUS10XE3(2095),          -- Supervisor Engine Board
            type-LSXM1FAB06XEC3(2096),          -- Switch Fabric Board
            type-LSXM1MPUS06XEC3(2097),         -- Supervisor Engine Board
            type-LSXM1CGS8SH3(2098),            -- 8-Port 100G Ethernet Optical Interface Module(QSFP28)(SH)
            type-LSXM1SUPXD3(2099),             -- Supervisor Engine Board
            type-LSXM1CGS20XSH3(2100),          -- 20-Port 100G Ethernet Optical Interface Module(QSFP28)(SH)
            type-LSUM1GP48FD0-Z(2101),          -- 48-Port 1000BASE-X Optical Interface Board(SFP,LC)
            type-LSQM1TGS48RFE0-Z(2102),        -- 48-Port 10GBASE-R Ethernet Optical Interface Board(SFP+,LC)
            type-LSXM1CGS32XSH3(2103),          -- 32-Port 100G Ethernet Optical Interface Module(QSFP28)(SH)
            type-LSQM2GP40TS8FD0(2104),         -- 40-Port 1000BASE-X Optical Interface(SFP,LC)+8-Port 10GBASE-R Ethernet Optical Interface Board(SFP+,LC)
            type-LSUM1SUPXES0(2105),            -- Supervisor Engine Board
            type-LSQM2SUPB0(2106),              -- Supervisor Engine Board
            type-LSUM2GP40TS8FD0(2107),         -- 40-Port 1000BASE-X Optical Interface(SFP,LC)+8-Port 10GBASE-R Ethernet Optical Interface Board(SFP+,LC)



            type-LSXM2SFT08E2(2109),               -- Fabric Module,Type T(Class E)
            type-LSXM1TGS48TD2(2110),              -- 48-port 10G BASE Ethernet Optical Interface Board(SFP+,LC)
            type-LSXM1CGQ36TD2(2111),              -- 36-Port 100GBASE Ethernet Optical Interface Board(QSFP28)
            type-RX-NIC-LGQ4L(2112),               -- 4-port 50G Ethernet Optical Interface Card(QSFP28,LC)(RX-NIC)
            type-LSXM1CDQ24KB1(2113),              -- 24-Port 400GBASE Ethernet Optical Interface Module(QSFP-DD)(KB)
            type-LSXM1SUP02L1(2114),               -- Supervisor Engine Unit
            type-LSXM1CGQ48KB1(2115),              -- 48-Port 100GBASE Ethernet Optical Interface Module(QSFP28)(KB)
            type-LSXM1SFK08F1(2116),               -- Switch Fabric Board,Type K(Class F)
            type-MIC-CQ1L1(2118),                  -- 1-port 100G Ethernet Optical Interface Card(QSFP28)
            type-DS-3E7600-16X-SC-B(2119),         -- 16-Port 10GBASE-R Ethernet SFP+ Optical Interface Board(FD)
            type-DS-3E12508-MPU(2120),             -- Supervisor Engine Board
            type-DS-3E12500-7610-48T-SE(2121),     -- 48-Port 1000Base-T Gigabit Ethernet Interface Board(RJ45)(SE)
            type-DS-3E7603-MPU(2122),              -- Supervisor Engine Board
            type-DS-3E12500-7610-16X-SF(2123),     -- 16-Port 10GBASE-R Ethernet SFP+ Optical Interface Board(FD)
            type-DS-3E12500-24T20F4X-SE(2124),     -- 24-Port 1000Base-T Gigabit Ethernet Interface Board(RJ45)+20-Port GE Optical Interface(SFP,LC)+4-Port 10GE Optical Interface Board(SFP+,LC)(SE)
            type-DS-3E12500-12Q-SG(2125),          -- 12-Port 40GBASE-R Ethernet QSFP+ Optical Interface Board(SG)
            type-DS-3E12500-48X-SG(2126),          -- 48-Port 10GBASE-R Ethernet SFP+ Optical Interface Board(SG)
            type-DS-3E12500-7610-32X4QX-SF(2127),  -- 32-Port 10GBASE-R Ethernet Optical Interface(SFP+,LC)+4-Port 40GBASE-R Ethernet Optical Interface Board(QSFP+,LC)(SG)
            type-DS-3E12500-7610-44F4X-SE(2128),   -- 44-Port GE Optical Interface(SFP,LC)+4-Port 10GE Optical Interface Board(SFP+,LC)(SE)
            type-DS-3E12508-CLOS(2129),            -- Switching Fabric Module
            type-LSXM2SUPT2(2130),                 -- Supervisor Engine Board
            type-CSR05SRP1P3A(2131),               -- Main Processing Unit(1P3A)
            type-CSFC-08E1A(2132),                 -- Fabric Module(E Type)
            type-CSFC-16EA(2133),                  -- Fabric Module(E Type)
            type-CSPEX-1602XA(2134),               -- Service Processing Unit(1602XA)
            type-CEPC-CP4RXA(2135),                -- 4-port 100GBASE Ethernet Optical Interface Line Processing Unit A(CFP2)
            type-CSPEX-1504XA(2136),               -- Service Processing Unit(1504XA)
            type-CSPEX-1804XA(2137),               -- Service Processing Unit(1804XA)
            type-MIC-GP10LA(2138),                 -- 10-port 1000BASE-X Ethernet Optical Interface Card A(SFP,LC)
            type-MIC-GT20LA(2139),                 -- 20-port 1000BASE-X Ethernet Copper Interface Card A(RJ45)
            type-MIC-XP20LA(2140),                 -- 20-port 10GBASE-R/W Ethernet Optical Interface Card A(SFP+,LC)









            type-LSDM1QGS12SE0-Z(2142),            -- 12-Port 40GBASE-R Ethernet QSFP+ Optical Interface Board(SE)
            type-LSDM1TGS48SE0-Z(2143),            -- 48-Port 10GBASE-R Ethernet SFP+ Optical Interface Board(SE)
            type-LSDM1SUPA0-Z(2144),               -- Supervisor Engine Board
            type-LSDM1FAB08D0-Z(2145),             -- Switch Fabric Board
            type-LSDM1GT24GPSE0-Z(2146),           -- 24-Port 10/100/1000BASE-T Electrical Interface(RJ45)+24-Port 1000BASE-X Ethernet Optical Interface Board(SFP,LC)(SE)

            type-LSXM1CGQ18TD2(2147),              -- 18-Port 100GBASE Ethernet Optical Interface Board(QSFP28)
            type-LSXM1QGS36TD2(2148),              -- 36-Port 40GBASE Ethernet Optical Interface Board(QSFP+)

            type-RP-S-G(2149),                     -- Main Processing Unit,Domestic Version
            type-MOD20-G(2150),                    -- Service Processing Unit(MOD20-G),Domestic&Overseas Version
            type-MPA-PSP4L-G(2151),                -- 4-port OC-48c/STM-16c POS Optical Interface Card(SFP,LC),Domestic&Overseas Version
            type-MPA-TCP8L-G(2152),                -- 8-port OC-3c/OC-12c POS/GE Optical Interface Card(SFP,LC),Domestic&Overseas Version
            type-MPA-ET16L-G(2153),                -- 16-port E1 Copper Interface Card(HM96 Male Connector),Domestic&Overseas Version
            type-MPA-GP10L-G(2154),                -- 10-port 1000BASE-X Optical Interface Card(SFP,LC),Domestic&Overseas Version
            type-MPA-XP4L-G(2155),                 -- 4-port 10GBASE-R/W Ethernet Optical Interface Card(SFP+,LC),Domestic&Overseas Version
            type-LSXM1SFH04DR1(2156),              -- Switch Fabric Board,Type H(Class D)
            type-LSXM1SFH08CR1(2157),              -- Fabric Module,Type H(Class C)
            type-LSXM1SFH08DR1(2158),              -- Switch Fabric Board For Type D(F2)
            type-LSXM1SFH16CR1(2159),              -- Fabric Module,Type H(Class C)
            type-LSXM1SFH16ER1(2160),              -- Fabric Module,Type H(Class E)
            type-LSXM1TGS48HFR1(2161),             -- 48-Port 10GBASE Ethernet Optical Interface Module(SFP+,LC)(HF)
            type-LSXM1CGQ18QGHFR1(2162),           -- 18-PORT 100GBASE Ethernet Optical Interface(QSFP28)/36-Port 40GBASE Ethernet Optical Interface Module(QSFP+)(HF)




            type-LSXM1SUP04TR1(2163),              -- Supervisor Engine Unit
            type-LSXM1CGQ36HBR1(2164),             -- 36-Port 100GBASE Ethernet Optical Interface Module(QSFP28)(HB)
            type-LSXM1CGQ36HFR1(2165),             -- 36-Port 100GBASE Ethernet Optical Interface Module(QSFP28)(HF)
            type-LSXM1CGQ6QGHFR1(2166),            -- 6-Port 100GBASE Ethernet Optical Interface(QSFP28)/12-Port 40GBASE Ethernet Optical Interface Module(QSFP+)(HF)
            type-LSXM1TGS48HBR1(2167),             -- 48-Port 10G BASE Ethernet Optical Interface Module(SFP+,LC)(HB)
            type-LSXM1CGQ18QGHBR1(2168),           -- 18-PORT 100GBASE Ethernet Optical Interface(QSFP28)/36-Port 40GBASE Ethernet Optical Interface Module(QSFP+)(HF)
            type-LSXM1SUPER1(2169),                -- Supervisor Engine Module

            type-LSQM1SDNB0(2170),                 -- SDN-engine Blade
            type-LSUM1SDNB0(2171),                 -- SDN-engine Blade
            type-LSQM1EPSB0(2172),                 -- EPS-engine Blade
            type-LSUM1EPSB0(2173),                 -- EPS-engine Blade

            type-LSXM2TGS48HB2(2174),              -- 48-Port 10GBASE Ethernet Optical Interface Module(SFP+,LC)(HB)
            type-LSXM2CGQ18QGHB2(2175),            -- 18-Port 100GBASE Ethernet Optical Interface(QSFP28)/36-Port 40GBASE Eth
            type-LSUM1CGS8SH3(2176),               -- 8-Port 100G Ethernet Optical Interface Module(QSFP28)(SH)
            type-LSUM1GT48FC3(2177),               -- 48-Port 1000BASE-X Optical Interface Board(SFP,LC)
            type-LSUM1FAB10XEA3(2178),             -- Switch Fabric Board
            type-LSUM1TGS48SH3(2179),              -- 48-Port 10/100/1000BASE-T Electrical Interface Board(RJ45)
            type-LSUM1MPUS10XE3(2180),             -- Supervisor Engine Board
            type-LSUM1GP48FC3(2181),               -- 48-Port 10G Ethernet Optical Interface Module(SFP+,LC)(SH)
            type-LSQM1TGS16FD0-Z(2182),            -- 16-Port 10GBASE-R Ethernet SFP+ Optical Interface Board(FD)
            type-LSQM2SUPA0-Z(2183),               -- Supervisor Engine Board
            type-LSUM1TGS16FD0-Z(2184),            -- 16-Port 10GBASE-R Ethernet SFP+ Optical Interface Board(FD)
            type-LSWM2FPGAB(2185),                 -- NetStream
            type-LSWM2EC(2186),                    -- EScaner
            type-LSWM2FPGA(2187),                  -- NetStream + 4*SFP Plus
            type-LSWM2ZSP4P(2188),                 -- 4-Port SFP28 Module
            type-LSXM1CGQ8TD2(2189),               -- 8-Port 10GBASE-R Ethernet QSFP28 Optical Interface Board
            type-LSXM1TGS48C4TD2(2190),            -- 48-Port 10GBASE-R Ethernet Optical Interface(SFP+,LC)+4-Port 100GBASE-R Ethernet Optical Interface Board(QSFP28,LC)
            type-LSXM1QGS24C6TD2(2191),            -- 24-Port 40GBASE-R Ethernet Optical Interface(QSFP+,LC)+6-Port 100GBASE-R Ethernet Optical Interface Board(QSFP28,LC)
            type-LSCM1MPUS06A8(2192),              -- Supervisor Engine Board
            type-LSCM1TGS48SC8(2193),              -- 48-Port 10GBASE-R Ethernet SFP+ Optical Interface Board(SC)
            type-LSQM1MPUS06S0(2194),              -- Supervisor Engine Board
            type-LSQM1SRP4Y06A0(2195),             -- Supervisor Engine Board With 4-Port 25GBASE-R Ethernet SFP28 Optical Interfaces
            type-S76-16XFSF-E(2196),               -- 16-Port 10GBASE-R Ethernet SFP+ Optical Interface Board(FD)
            type-S7603-MPU(2197),                  -- Supervisor Engine Board
            type-LSCM2MPUS06AS8(2198),             -- Supervisor Engine Board
            type-LSCM2CGT24TSSC8(2199),            -- Supervisor Engine Board With 24-Port 10/100/1000BASE-T Ethernet Interface+4-Port 10GBASE-R Ethernet SFP+ Optical Interfaces
            type-LSCM2CGP24TSSC8(2200),            -- Supervisor Engine Board With 24-Port 1000BASE-X Ethernet SFP Optical Interface+4-Port 10GBASE-R Ethernet SFP+ Optical Interfaces
            type-LSCM2CTGS12GTSC8(2201),           -- Supervisor Engine Board With 16-Port 10/100/1000BASE-T Ethernet Interface+12-Port 10GBASE-R Ethernet SFP+ Optical Interfaces
            type-LSCM2CTGS12GPSC8(2202),           -- Supervisor Engine Board With 16-Port 1000BASE-X Ethernet SFP Optical Interface+12-Port 10GBASE-R Ethernet SFP+ Optical Interfaces
            type-LSCM2GT24GPTSSC8(2203),           -- 24-Port 10/100/1000BASE-T Ethernet Interface Board(RJ45)+20-Port 1000BASE-X Ethernet SFP Optical Interface(SFP,LC)+4-Port 10GBASE-R Optical Interface Board(SFP+,LC)(SC)
            type-LSCM2GT24GPSC8(2204),             -- 24-Port 10/100/1000BASE-T Ethernet Interface Board(RJ45)+8-Port 1000BASE-X Ethernet SFP Optical Interface(SFP,LC)(SC)
            type-LSCM2GP24GTSC8(2205),             -- 8-Port 10/100/1000BASE-T Ethernet Interface Board(RJ45)+24-Port 1000BASE-X Ethernet SFP Optical Interface(SFP,LC)(SC)
            type-LSCM2GT48SC8(2206),               -- 48-Port 10/100/1000BASE-T Ethernet Interface Board(RJ45)(SC)
            type-LSCM2GP48SC8(2207),               -- 48-Port 1000BASE-X Ethernet Optical Interface Board(SFP,LC)(SC)
            type-LSCM2TGS16GPSC8(2208),            -- 24-Port 1000BASE-R Ethernet Optical Interface(SFP,LC)+16-Port 10GBASE-R Ethernet Optical Interface Board(SFP+,LC)(SC)
            type-LSXM2SFH16CR1(2209),              -- Fabric Module,Type H(Class C)
            type-LSXM1SFK08FR1(2213),              -- Switch Fabric Board,Type K(Class F)
            type-LSXM1CDQ24KBR1(2214),             -- 24-Port 400GBASE Ethernet Optical Interface Module(QSFP-DD)(KB)
            type-LSXM1SUP02LR1(2215),              -- Supervisor Engine Unit
            type-LSXM1CGQ48KBR1(2216),             -- 48-Port 100GBASE Ethernet Optical Interface Module(QSFP28)(KB)
            type-LSXM1CGQ36HC0(2217),              -- 36-Port 100GBASE Ethernet Optical Interface Module(QSFP28)(HC)
            type-LSXM1TGS48TE2(2218),              -- 48-Port 10G BASE Ethernet Optical Interface Module(SFP+,LC)
            type-LSXM1CGQ36TE2(2219),              -- 36-Port 100GBASE Ethernet Optical Interface Board(QSFP28)
            type-LSXM1SFT16F1(2220),               -- Switch Fabric Board
            type-LSXM1CGQ18TE2(2221),              -- 18-Port 100GBASE Ethernet Optical Interface Board(QSFP28)
            type-LSXM1CGQ8TE2(2222),               -- 8-Port 100GBASE Ethernet Optical Interface Board(QSFP28)
            type-LSWM116H(2223),                   -- 16-Port QSFP28 Ethernet Optical Interface Module
            type-LSWM1M4CD(2224),                  -- 4-Port 400GBASE Ethernet Optical Interface Module(QSFP-DD)
            type-LSXM1QGS36TE2(2225),              -- 36-Port 40GBASE Ethernet Optical Interface Module(QSFP+)
            type-LSXM1SFT16F2(2226),               -- Switch Fabric Board
            type-CSPEX-1812X-E(2227),              -- Service Processing Unit(1812X-E)
            type-MOD20-A3(2228),                   -- SR0MZLF1DQM1,Service Processing Unit(MOD20-G),Domestic&Overseas Version
            type-RP-S-G-A3(2229),                  -- SR0MZSRP1A4,Main Processing Unit,Domestic Version
            type-LSXM1SFT16EA1(2230),              -- Switch Fabric Board
            type-RP1-S-G(2231),                    -- SR0MZSRP1A3A,Main Processing Unit(S Type),Domestic&Overseas Version
            type-MOD21-G(2232),                    -- SR0MZLF1DQM1,Service Processing Unit(MOD21-G),Domestic&Overseas Version
            type-LSXM1SUPKR1(2233),                -- Supervisor Engine Module
            type-LSXM1CDQ36KBR1(2234),             -- 36-Port 400GBASE Ethernet Optical Interface Module(QSFP-DD)(KB)
            type-LSXM1CMUR1(2235),                 -- Board Monitor Unit
            type-LSXM1SFK16GR1(2236),              -- Switch Fabric Board,Type K(Class G)
            type-CSR05SRP1R3(2237),                -- CSR05SRP1R3,Main Processing Unit(1R3)
            type-MIC-TCP8L(2238),                  -- SR0MDTCP8LA1,8-port OC-3c/OC-12c POS Optical Interface Card(SFP,LC),Domestic&Overseas Version
            type-MIC-PSP4L(2239),                  -- SR0MDPSP4LA1,4-port OC-48c/STM-16c POS Optical Interface Card(SFP,LC),Domestic&Overseas Version
            type-LSUM1MPU06B8(2240),               -- Supervisor Engine Board
            type-LSUM1MPU10C8(2241),               -- Supervisor Engine Board
            type-LSUM1FAB06C8(2242),               -- Switching Fabric Module
            type-LSUM1FAB10C8(2243),               -- Switching Fabric Module
            type-LSUM1MPU10A8(2244),               -- Supervisor Engine Board
            type-LSUM1FAB10A8(2245),               -- Switching Fabric Module
            type-LSUM1TGS16FD8(2246),              -- 16-Port 10GBASE-R Ethernet SFP+ Optical Interface Board(FD)
            type-LSUM1GP48FD8(2247),               -- 48-Port 1000BASE-X Optical Interface Board(SFP,LC)
            type-LSUM1GT48FD8(2248),               -- 48-Port 10/100/1000BASE-T Electrical Interface Board(RJ45)
            type-LSUM1GP40TS8FD8(2249),            -- 40-Port 1000BASE-X Optical Interface(SFP,LC)+8-Port 10GBASE-R Ethernet Optical Interface Board(SFP+,LC)
            type-LSUM1TGS48RSH8(2250),             -- 48-Port 10GBASE-R Ethernet Optical Interface Module(SFP+,LC)(SH)
            type-LSDM1GP48SE0-Z(2251),             -- 48-Port 1000BASE-X Ethernet Optical Interface Board(SFP,LC)
            type-LSDM1GT48SE0-Z(2252),             -- 48-Port 10/100/1000BASE-T Ethernet Interface Board(RJ45)(SE)
            type-LSDM1CGS8SE0-Z(2253),             -- 8-Port 100GBASE-R Ethernet Optical Interface Board(QSFP28,LC)
            type-LSXM1SUP04T2(2254),               -- Supervisor Engine Board
            type-LSXM1SFT04F2(2255),               -- Switch Fabric Board
            type-LSXM1SFT08F2(2256),               -- Switch Fabric Board
            type-RX-NIC-CQ2LF-E(2257),             -- 2-port 100G Flexible Ethernet Optical Interface Card(QSFP28,LC)(RX-NIC)
            type-LSUM1TGS24FD8(2258),              -- 24-Port 10GBASE-R Ethernet Optical Interface Board(SFP+,LC)
            type-RX-SPE400-E(2259),                -- Service Processing Unit(SPE400-E)
            type-LSXM1SFK08GR1(2260),              -- Switch Fabric Board,Type K(Class G)
            type-RX-SFC-16T1(2261),                -- 1Tbps Fabric Module(16)
            type-LSCM3SUP03A0-Z(2262),             -- Supervisor Engine Board
            type-LSCM3MPUS06A0-Z(2263),            -- Supervisor Engine Board
            type-LSCM3GT48SC0-Z(2264),             -- 48-Port 10/100/1000BASE-T Electrical Interface Board(RJ45)(SC)
            type-LSCM3TGS48SE0-Z(2265),            -- 48-Port 10GBASE-R Ethernet SFP+ Optical Interface Board(SE)
            type-LSCM3QGS8CSSE0-Z(2266),           -- 8-Port 40GBASE-R QSFP+ + 4-Port 100GBASE-R QSFP28 Optical Interface Board(SE)
            type-LSDM3QGS12SE0-Z(2267),            -- 12-Port 40GBASE-R Ethernet QSFP+ Optical Interface Board(SE)
            type-LSDM3TGS48SE0-Z(2268),            -- 48-Port 10GBASE-R Ethernet SFP+ Optical Interface Board(SE)
            type-LSDM3SUPA0-Z(2269),               -- Supervisor Engine Board
            type-LSDM3FAB08D0-Z(2270),             -- Switch Fabric Board
            type-LSDM3GT24GPSE0-Z(2271),           -- 24-Port 10/100/1000BASE-T Electrical Interface(RJ45)+24-Port 1000BASE-X Ethernet Optical Interface Board(SFP,LC)(SE)
            type-LSDM3GP48SE0-Z(2272),             -- 48-Port 1000BASE-X Ethernet Optical Interface Board(SFP,LC)
            type-LSDM3GT48SE0-Z(2273),             -- 48-Port 10/100/1000BASE-T Ethernet Interface Board(RJ45)(SE)
            type-LSDM3CGS8SE0-Z(2274),             -- 8-Port 100GBASE-R Ethernet Optical Interface Board(QSFP28,LC)
            type-RX-CEPC-CQ8LF(2275),              -- 8-port 100G Flexible Ethernet Optical Interface Line Processing Unit(QSFP28,LC)
            type-RX-SPE200-E(2276),                -- Service Processing Unit(SPE200-E)
            type-DSH7503-MP(2277),                 -- Supervisor Engine Board
            type-DSH7506-MP(2278),                 -- Supervisor Engine Board
            type-DSH7510-MP(2279),                 -- Supervisor Engine Board
            type-DSH7500-48T-P(2280),              -- 48-Port 1000Base-T Gigabit Ethernet Interface Board(RJ45)-POE
            type-DSH7500-16X(2281),                -- 16-Port 10GBASE-R Ethernet SFP+ Optical Interface Board
            type-DSH7500-48F(2282),                -- 48-Port 1000BASE-X Optical Interface Board(SFP,LC)
            type-DSH7500-12QX4Q28(2283),           -- 12-Port 40GBASE-R QSFP+ or 4-Port 100GBASE-R QSFP28 Optical Interface Board
            type-DSH7500-24F4X(2284),              -- 24-Port GE Optical Interface(SFP,LC)+4-Port 10GE Optical Interface Board(SFP+,LC)
            type-DSH7500-24QX(2285),               -- 24-Port 40GBASE-R Ethernet QSFP+ Optical Interface Board
            type-DSH7500-24T4X(2286),              -- 24-Port 1000Base-T Gigabit Ethernet Interface Board(RJ45)+4-Port 10GE Optical Interface Board(SFP+,LC)
            type-DSH7500-24X2QX1Q28(2287),         -- 24-Port 10GBASE-R Optical Interface(SFP+,LC)+2-Port 40GBASE-R Optical Interface Board(QSFP+) or 1-Port 100GBASE-R Optical Interface Board(QSFP28)
            type-DSH7500-2Q28(2288),               -- 2-Port 100GBASE-R Ethernet QSFP28 Optical Interface Board
            type-DSH7500-44F4X(2289),              -- 44-Port GE Optical Interface(SFP,LC)+4-Port 10GE Optical Interface Board(SFP+,LC)
            type-DSH7500-48T(2290),                -- 48-Port 10/100/1000BASE-T Electrical Interface Board(RJ45)
            type-DSH7500-48X(2291),                -- 48-Port 10GBASE-R Ethernet SFP+ Optical Interface Board
            type-LSWM2-iMC(2292),                  -- Intelligent Network Management Module
            type-LSWM2ZQP2P-Z(2293),               -- 2-Port QSFP28 Interface Module
            type-LSWM2ZSP4P-Z(2294),               -- 4-Port SFP28 Interface Module
            type-LSWM2ZSP8P-Z(2295),               -- 8-Port SFP28 Interface Module
            type-LSDM3SUP04A0-Z(2296),             -- Supervisor Engine Board
            type-LSDM3FAB04E0-Z(2297),             -- Switching Fabric Module
            type-LSDM3FAB08E0-Z(2298),             -- Switching Fabric Module
            type-LSDM3QGS36SE0-Z(2299),            -- 36-Port 40GBASE-R Ethernet QSFP+ Optical Interface Board
            type-LSDM3CGS12SE0-Z(2300),            -- 12-Port 100GBASE-R Ethernet QSFP28 Optical Interface Board
            type-LSQM2XPT12TSFD0(2301),            -- 12-Port 10/1GBASE-PR/PRX Ethernet Optical(SFP+,LC) and 8-Port 10GBASE-R SFP+ Optical Interface Board
            type-CSPEX-1702X(2302),                -- Service Processing Unit(1702X)
            type-CSR05SRP1P1(2303),                -- CSR05SRP1P1 Main Processing Unit(1P1)
            type-NIC-GP24L1(2304),                 -- 24-port 1000BASE-X Ethernet Optical Interface Card(SFP,LC)(NIC)
            type-NIC-GP24LA(2305),                 -- 24-port 1000BASE-X Ethernet Optical Interface Card A(SFP,LC)(NIC)
            type-NIC-XP20L1(2306),                 -- 20-port 10GBASE-R/W Ethernet Optical Interface Card(SFP+,LC)(NIC)
            type-NIC-XP20LA(2307),                 -- 20-port 10GBASE-R/W Ethernet Optical Interface Card A(SFP+,LC)(NIC)
            type-RX-NIC-LGQ4LF(2308),              -- 4-port 50G Flexible Ethernet Optical Interface Card(QSFP28,LC)(RX-NIC)
            type-CSR05SRP1R3A(2309),               -- Main Processing Unit(1R3A)
            type-CEPC-CQ8L(2310),                  -- 8-port 100G Ethernet Optical Interface Line Processing Unit(QSFP28,LC)
            type-CEPC-CQ8LA(2311),                 -- 8-port 100G Ethernet Optical Interface Line Processing Unit A(QSFP28,LC)
            type-CSPEX-1802XA(2312),               -- Service Processing Unit(1802XA)
            type-CSPEX-1802XB(2313),               -- Service Processing Unit(1802XB)
            type-CSPEX-1502XA(2314),               -- Service Processing Unit(1502XA)
            type-CSPEX-1512XB(2315),               -- Service Processing Unit(1512XB)

            type-NIC-XP20L1A(2317),                -- 20-port 10GBASE-R/W Ethernet Optical Interface Card A(SFP+,LC)(NIC)
            type-NIC-XP20L1B(2318),                -- 20-port 10GBASE-R/W Ethernet Optical Interface Card B(SFP+,LC)(NIC)

            type-NIC-GP24L1A(2320),                -- 24-port 1000BASE-X Ethernet Optical Interface Card A(SFP,LC)(NIC)
            type-NIC-GP24L1B(2321),                -- 24-port 1000BASE-X Ethernet Optical Interface Card B(SFP,LC)(NIC)
            type-NIC-CQ2LA(2322),                  -- 2-port 100G Ethernet Optical Interface Card A(QSFP28)(NIC)
            type-NIC-CQ2LB(2323),                  -- 2-port 100G Ethernet Optical Interface Card B(QSFP28)(NIC)
            type-NIC-XP5LA(2324),                  -- 5-port 10GBASE-R/W Ethernet Optical Interface Card A(SFP+,LC)(NIC)
            type-NIC-XP5LB(2325),                  -- 5-port 10GBASE-R/W Ethernet Optical Interface Card B(SFP+,LC)(NIC)
            type-CSFC-16T1(2326),                  -- Fabric Module(T Type)
            type-LSUM1MPUS10XEC0(2327),            -- Supervisor Engine Board
            type-LSUM1MPUS10XEC3(2328),            -- Supervisor Engine Board
            type-LSUM1MPUS06XEC3(2329),            -- Supervisor Engine Board
            type-LSUM1FAB10XEC0(2330),             -- Switching Fabric Module
            type-LSCM2MPUS06AS0-Z(2331),           -- Supervisor Engine Board
            type-LSCM2CGT24TSSC0-Z(2332),          -- Supervisor Engine Board With 24-Port 10/100/1000BASE-T Ethernet Interface+4-Port 10GBASE-R Ethernet SFP+ Optical Interfaces
            type-LSCM2CGP24TSSC0-Z(2333),          -- Supervisor Engine Board With 24-Port 1000BASE-X Ethernet SFP Optical Interface+4-Port 10GBASE-R Ethernet SFP+ Optical Interfaces
            type-LSCM2CTGS12GTSC0-Z(2334),         -- Supervisor Engine Board With 16-Port 10/100/1000BASE-T Ethernet Interface+12-Port 10GBASE-R Ethernet SFP+ Optical Interfaces
            type-LSCM2CTGS12GPSC0-Z(2335),         -- Supervisor Engine Board With 16-Port 1000BASE-X Ethernet SFP Optical Interface+12-Port 10GBASE-R Ethernet SFP+ Optical Interfaces
            type-LSCM2GT24GPTSSC0-Z(2336),         -- 24-Port 10/100/1000BASE-T Ethernet Interface Board(RJ45)+20-Port 1000BASE-X Ethernet SFP Optical Interface(SFP,LC)+4-Port 10GBASE-R Optical Interface Board(SFP+,LC)(SC)
            type-LSCM2GT24GPSC0-Z(2337),           -- 24-Port 10/100/1000BASE-T Ethernet Interface Board(RJ45)+8-Port 1000BASE-X Ethernet SFP Optical Interface(SFP,LC)(SC)
            type-LSCM2GP24GTSC0-Z(2338),           -- 8-Port 10/100/1000BASE-T Ethernet Interface Board(RJ45)+24-Port 1000BASE-X Ethernet SFP Optical Interface(SFP,LC)(SC)
            type-LSCM2GT48SC0-Z(2339),             -- 48-Port 10/100/1000BASE-T Ethernet Interface Board(RJ45)(SC)
            type-LSCM2GP48SC0-Z(2340),             -- 48-Port 1000BASE-X Ethernet Optical Interface Board(SFP,LC)(SC)
            type-LSCM2TGS16GPSC0-Z(2341),          -- 24-Port 1000BASE-R Ethernet Optical Interface(SFP,LC)+16-Port 10GBASE-R Ethernet Optical Interface Board(SFP+,LC)(SC)
            type-LSWM2SP2PM-Z(2342),               -- 2-Port SFP+ Interface Module with MACsec
            type-LSWM2QP2P-Z(2343),                -- 2-Port QSFP+ Interface Module
            type-LSWM2SP8P-Z(2344),                -- 8-Port SFP+ Interface Module
            type-LSCM2MPUS06AS0(2345),             -- Supervisor Engine Board
            type-LSCM2CGT24TSSC0(2346),            -- Supervisor Engine Board With 24-Port 10/100/1000BASE-T Ethernet Interface+4-Port 10GBASE-R Ethernet SFP+ Optical Interfaces
            type-LSCM2CGP24TSSC0(2347),            -- Supervisor Engine Board With 24-Port 1000BASE-X Ethernet SFP Optical Interface+4-Port 10GBASE-R Ethernet SFP+ Optical Interfaces
            type-LSCM2CTGS12GTSC0(2348),           -- Supervisor Engine Board With 16-Port 10/100/1000BASE-T Ethernet Interface+12-Port 10GBASE-R Ethernet SFP+ Optical Interfaces
            type-LSCM2CTGS12GPSC0(2349),           -- Supervisor Engine Board With 16-Port 1000BASE-X Ethernet SFP Optical Interface+12-Port 10GBASE-R Ethernet SFP+ Optical Interfaces
            type-LSCM2GT24GPTSSC0(2350),           -- 24-Port 10/100/1000BASE-T Ethernet Interface Board(RJ45)+20-Port 1000BASE-X Ethernet SFP Optical Interface(SFP,LC)+4-Port 10GBASE-R Optical Interface Board(SFP+,LC)(SC)
            type-LSCM2GT24GPSC0(2351),             -- 24-Port 10/100/1000BASE-T Ethernet Interface Board(RJ45)+8-Port 1000BASE-X Ethernet SFP Optical Interface(SFP,LC)(SC)
            type-LSCM2GP24GTSC0(2352),             -- 8-Port 10/100/1000BASE-T Ethernet Interface Board(RJ45)+24-Port 1000BASE-X Ethernet SFP Optical Interface(SFP,LC)(SC)
            type-LSCM2GT48SC0(2353),               -- 48-Port 10/100/1000BASE-T Ethernet Interface Board(RJ45)(SC)
            type-LSCM2GP48SC0(2354),               -- 48-Port 1000BASE-X Ethernet Optical Interface Board(SFP,LC)(SC)
            type-LSCM2TGS16GPSC0(2355),            -- 24-Port 1000BASE-R Ethernet Optical Interface(SFP,LC)+16-Port 10GBASE-R Ethernet Optical Interface Board(SFP+,LC)(SC)
            type-LSXM1SFK04FR1(2356),              -- Fabric Module
            type-LSXM1SFK08ER1(2357),              -- Fabric Module
            type-LSXM1SFK16ER1(2358),              -- Fabric Module
            type-LSXM1CCQ48KBR1(2359),             -- 48-Port 200GBASE Ethernet Optical Interface Module (QSFP56)(KB)
            type-LSQM3SUPA0(2360),                 -- Supervisor Engine Board
            type-LSQM3SUPA3(2361),                 -- Supervisor Engine Board
            type-LSXM1YGS24CGMODTE2(2362),         -- 24-Port 25G Ethernet Optical Interface(SFP28)+4-Port 100G Ethernet Optical Interface Module (QSFP28),With 1 Expansion Slot
            type-LSXM1SUPE1(2363),                 -- Supervisor Engine Unit
            type-LSUM2TGS48SH0(2364),              -- 48-Port 10G Ethernet Optical Interface Module(SFP+,LC)(SH)
            type-LSCM3SUP03A0(2365),               -- Supervisor Engine Board
            type-LSCM3MPUS06A0(2366),              -- Supervisor Engine Board
            type-LSCM3TGS48SE0(2367),              -- 48-Port 10GBASE-R Ethernet SFP+ Optical Interface Board(SE)
            type-LSCM3QGS8CSSE0(2368),             -- 8-Port 40GBASE-R QSFP+ + 4-Port 100GBASE-R QSFP28 Optical Interface Board(SE)
            type-LSCM3SUP03A0-ZE(2369),            -- Supervisor Engine Board
            type-LSCM3GT48SC0-ZE(2370),            -- 48-Port 10/100/1000BASE-T Electrical Interface Board(RJ45)(SC)
            type-LSCM3TGS48SE0-ZE(2371),           -- 48-Port 10GBASE-R Ethernet SFP+ Optical Interface Board(SE)
            type-LSCM3QGS8CSSE0-ZE(2372),          -- 8-Port 40GBASE-R QSFP+ + 4-Port 100GBASE-R QSFP28 Optical Interface Board(SE)
            type-LSDM3FAB04G0-Z(2373),             -- Switch Fabric Board
            type-LSDM3FAB08G0-Z(2374),             -- Switch Fabric Board
            type-LSDM3FAB16G0-Z(2375),             -- Switch Fabric Board
            type-LSDM3CGS36SF0-Z(2376),            -- 36-Port 100GBASE-R Ethernet Optical Interface Board(QSFP28,LC)
            type-LSDM3YGS48SF0-Z(2377),            -- 48-Port 25GBASE-R Ethernet Optical Interface Board(SFP28,LC)
            type-LSCM3MPUS10B0(2378),              -- Supervisor Engine Unit
            type-LSCM3MPUS10B0-Z(2379),            -- Supervisor Engine Unit
            type-LSUM1CGS8QSSH8(2380),             -- 8-Port 100G Ethernet Optical Interface Module(QSFP28) +8-port 40G/4-Port 100G Ethernet Optical Interface Module(QSFP28)(SH)
            type-LSDM3TGS48SF0-Z(2381),            -- 48-Port 10GBASE-R Ethernet SFP+ Optical Interface Board(SF)
            type-LSDM1SUPA0(2382),                 -- Supervisor Engine Board
            type-LSDM1FAB08D0(2383),               -- Switch Fabric Board
            type-LSDM1TGS48SE0(2384),              -- 48-Port 10GBASE-R Ethernet SFP+ Optical Interface Board(SE)
            type-LSDM1GT24GPSE0(2385),             -- 24-Port 10/100/1000BASE-T Electrical Interface(RJ45)+24-Port 1000BASE-X Ethernet Optical Interface Board(SFP,LC)(SE)
            type-LSDM1GT48SE0(2386),               -- 48-Port 10/100/1000BASE-T Ethernet Interface Board(RJ45)(SE)
            type-LSDM1GP48SE0(2387),               -- 48-Port 1000BASE-X Ethernet Optical Interface Board(SFP,LC)
            type-LSDM3SUPA0(2388),                 -- Supervisor Engine Board
            type-LSDM3FAB08D0(2389),               -- Switch Fabric Board
            type-LSDM3TGS48SE0(2390),              -- 48-Port 10GBASE-R Ethernet SFP+ Optical Interface Board(SE)
            type-LSDM3GT24GPSE0(2391),             -- 24-Port 10/100/1000BASE-T Electrical Interface(RJ45)+24-Port 1000BASE-X Ethernet Optical Interface Board(SFP,LC)(SE)
            type-LSDM3GT48SE0(2392),               -- 48-Port 10/100/1000BASE-T Ethernet Interface Board(RJ45)(SE)
            type-LSDM3GP48SE0(2393),               -- 48-Port 1000BASE-X Ethernet Optical Interface Board(SFP,LC)
            type-SR07MPUA3-M(2394),                -- Management and Route Process Board(UA3-M)
            type-SFE-A(2395),                      -- Network Processing Unit(A)
            type-MIC-CQ1L-M(2396),                 -- 1-Port 100G Ethernet Optical Interface Card(QSFP28,LC)
            type-MIC-CQ2L-M(2397),                 -- 2-Port 100G Ethernet Optical Interface Card(QSFP28,LC)
            type-LSXM1CGQ18C1(2398),               -- 18-Port 100GBASE Ethernet Optical Interface Module (QSFP28)
            type-LSXM1CGQMS18B1(2399),             -- 18-Port 100GBASE MACsec Ethernet Optical Interface Module(QSFP28)
            type-LSXM1MOD48KBR1(2400),             -- 48KBR Flexible Line Processing Platform Module
            type-LSXM1CDQ36KB1(2401),              -- 36-Port 400GBASE Ethernet Optical Interface Module(QSFP-DD)(KB)
            type-LSXM1SUP02TR1(2402),              -- Supervisor Engine Unit
            type-LSCM2SUP03B0(2407),               -- Supervisor Engine Board
            type-LSCM2SUP03B0-Z(2408),             -- Supervisor Engine Board
            type-LSWM2QP4P(2409),                  -- 4-Port QSFP+ Interface Module
            type-LSXM1SUPS2(2410),                 -- Supervisor Engine Board
            type-LSXM1SFS08D2(2411),               -- Switch Fabric Board
            type-LSXM1TGS48SE2(2412),              -- 48-Port 10GBASE-R Ethernet SFP+ Optical Interface Board(SE)
            type-LSXM1GT24GPSE2(2413),             -- 24-Port 10/100/1000BASE-T Electrical Interface(RJ45)+24-Port 1000BASE-X Ethernet Optical Interface Board(SFP,LC)(SE)
            type-LSXM1GT48SE2(2414),               -- 48-Port 10/100/1000BASE-T Ethernet Interface Board(RJ45)(SE)
            type-LSXM1GP48SE2(2415),               -- 48-Port 1000BASE-X Ethernet Optical Interface Board(SFP,LC)
            type-LSXM3SUPS2(2416),                 -- Supervisor Engine Board
            type-LSXM3SFS08D2(2417),               -- Switch Fabric Board
            type-LSXM3TGS48SE2(2418),              -- 48-Port 10GBASE-R Ethernet SFP+ Optical Interface Board(SE)
            type-LSXM3GT24GPSE2(2419),             -- 24-Port 10/100/1000BASE-T Electrical Interface(RJ45)+24-Port 1000BASE-X Ethernet Optical Interface Board(SFP,LC)(SE)
            type-LSXM3GT48SE2(2420),               -- 48-Port 10/100/1000BASE-T Ethernet Interface Board(RJ45)(SE)
            type-LSXM3GP48SE2(2421),               -- 48-Port 1000BASE-X Ethernet Optical Interface Board(SFP,LC)
            type-LSXM3SUP04S2(2422),               -- Supervisor Engine Board
            type-LSXM3SFS04G2(2423),               -- Switch Fabric Board
            type-LSXM3SFS08G2(2424),               -- Switch Fabric Board
            type-LSXM3SFS16G2(2425),               -- Switch Fabric Board
            type-LSXM3CGQ36SF2(2426),              -- 36-Port 100GBASE-R Ethernet Optical Interface Board(QSFP28,LC)
            type-LSXM3YGS48SF2(2427),              -- 48-Port 25GBASE-R Ethernet Optical Interface Board(SFP28,LC)
            type-LSXM3TGS48SF2(2428),              -- 48-Port 10GBASE-R Ethernet SFP+ Optical Interface Board(SF)
            type-MIC-GP12L-M(2429),                -- 12-port 1000BASE-X Optical Interface Card(SFP,LC)
            type-MIC-CQ1LF-M(2430),                -- 1-port 100G Flexible Ethernet Optical Interface Card(QSFP28,LC)
            type-MIC-XP10L-M(2431),                -- 10-port 10GBASE-R/W Ethernet Optical Interface Card Module(SFP+,LC)
            type-MIC-CLP4L-M(2432),                -- 4-port OC-3/STM-1 Channelized POS Optical Interface Card(SFP,LC)
            type-MIC-ET16L-M(2433),                -- 16-port E1 Copper Interface Card(HM96 Male Connector)
            type-MIC-PSP4L-M(2434),                -- 4-Port OC-48c/STM-16c POS Optical Interface Card,(SFP,LC)
            type-MIC-TCP8L-M(2435),                -- 8-Port OC-3c/OC-12c POS Optical Interface Card,(SFP,LC)
            type-MIC-SP4L-M(2436),                 -- 4-port OC-3c/STM-1c POS/ATM or 1-port OC-12c/STM-4c POS/ATM Fiber Interface Card(SFP,LC)
            type-LSCM2GV48SC0(2437),               -- 48-Port 10/100/1000BASE-T Ethernet Interface Board(RJ45)(SC)-POE
            type-LSQM1FAB06XEB0(2438),             -- Switch Fabric Board
            type-LSQM1FAB10XEA0(2439),             -- Switch Fabric Board
            type-LSQM1MPUS06XEB0(2440),            -- Supervisor Engine Board
            type-LSQM1MPUS10XEA0(2441),            -- Supervisor Engine Board
            type-LSQM2TGS48XSH0(2442),             -- 48-Port 10G Ethernet Optical Interface Module(SFP+,LC)(SH)
            type-LSQM1TGS48RXSH0(2443),            -- 48-Port 10GBASE-R Ethernet Optical Interface Module(SFP+,LC)(SH)
            type-LSQM1CGS8XSH0(2444),              -- 8-Port 100G Ethernet Optical Interface Module(QSFP28)(SH)
            type-LSQM1YGS24CSXSH0(2445),           -- 24-Port 25G Ethernet Optical Interface(SFP28,LC)+4-Port 100G Ethernet Optical Interface Module(QSFP28)(SH)
            type-LSQM1CGS8QSXSH0(2446),            -- 8-Port 100G Ethernet Optical Interface Module(QSFP28) +8-port 40G/4-Port 100G Ethernet Optical Interface Module(QSFP28)(SH)
            type-LSQM2GP24TSXSA0(2447),            -- 24-Port GE Optical Interface(SFP,LC)+4-Port 10GE Optical Interface Board(SFP+,LC)(SA)
            type-LSQM2GT48XSA0(2448),              -- 48-Port 1000Base-T Gigabit Ethernet Interface Board(RJ45)(SA)
            type-LSQM2GP48XSA0(2449),              -- 48-Port 1000BASE-X Ethernet Optical Interface Board(SFP,LC)(SA)
            type-LSQM2GP44TSXSE0(2450),            -- 44-Port GE Optical Interface(SFP,LC)+4-Port 10GE Optical Interface Board(SFP+,LC)(SE)
            type-LSQM2GT24PTSXSE0(2451),           -- 24-Port 1000Base-T Gigabit Ethernet Interface Board(RJ45)+20-Port GE Optical Interface(SFP,LC)+4-Port 10GE Optical Interface Board(SFP+,LC)(SE)
            type-LSQM2GT24TSXSE0(2452),            -- 24-Port 1000Base-T Gigabit Ethernet Interface Board(RJ45)+4-Port 10GE Optical Interface Board(SFP+,LC)(SE)
            type-LSQM1GT48XFD0(2453),              -- 48-Port 1000BASE-X Optical Interface Board(SFP,LC)
            type-LSQM2GP40TS8XFD0(2454),           -- 40-Port 1000BASE-X Optical Interface(SFP,LC)+8-Port 10GBASE-R Ethernet Optical Interface Board(SFP+,LC)
            type-LSQM1TGT24XFD0(2455),             -- 24-Port 10GBASE-T Ethernet Copper Interface Module(RJ45)(FD)
            type-LSEM1SUPA0(2456),                 -- Supervisor Engine Board
            type-LSEM1SF06D0(2457),                -- Switch Fabric Board
            type-LSEM1GT48TSSD0(2458),             -- 48-Port 10/100/1000BASE-T Electrical Interface(RJ45)+4-Port 10GBASE-R Ethernet Optical Interface Board(SFP+,LC)(SD)
            type-LSEM1TGS24SD0(2459),              -- 24-Port 10GBASE-R Ethernet SFP+ Optical Interface Board(SD)
            type-LSEM1TGS48SD0(2460),              -- 48-Port 10GBASE-R Ethernet SFP+ Optical Interface Board(SD)
            type-LSDM3FAB08F0-Z(2461),             -- Switching Fabric Module
            type-LSDM3FAB16F0-Z(2462),             -- Switching Fabric Module
            type-LSDM3QGS36SF0-Z(2463),            -- 36-Port 40G Ethernet Optical Interface Module (QSFP+)
            type-LSDM3CGS18SF0-Z(2464),            -- 18-Port 100G Ethernet Optical Interface Module (QSFP28)
            type-LSDM3CDQ16SF0-Z(2465),            -- 16-Port 400G Ethernet Optical Interface Module (QSFP-DD)
            type-LSDM3CDQ8SF0-Z(2466),             -- 8-Port 400G Ethernet Optical Interface Module (QSFP-DD)
            type-LSXM3SFS08F2(2467),               -- Switching Fabric Module
            type-LSXM3SFS16F2(2468),               -- Switching Fabric Module
            type-LSXM3QGS36SF2(2469),              -- 36-Port 40G Ethernet Optical Interface Module (QSFP+)
            type-LSXM3CGQ18SF2(2470),              -- 18-Port 100G Ethernet Optical Interface Module (QSFP28)
            type-LSXM3CDQ16SF2(2471),              -- 16-Port 400G Ethernet Optical Interface Module (QSFP-DD)
            type-LSXM3CDQ8SF2(2472),               -- 8-Port 400G Ethernet Optical Interface Module (QSFP-DD)
            type-MIC-XP4L-M(2473),                 -- 4-Port 10GBASE-R/W Ethernet Optical Interface Card (SFP+,LC)
            type-LSDM3SUP04A0(2474),               -- Supervisor Engine Board
            type-LSDM3FAB04E0(2475),               -- Switching Fabric Module
            type-LSDM3QGS36SE0(2476),              -- 36-Port 40GBASE-R Ethernet QSFP+ Optical Interface Board
            type-CSR05SRP1P3-G(2477),              -- Management and Route Process Board(1P3-G)
            type-CSPEX-2304X-G(2478),              -- Network Processing Unit(2304X-G)
            type-CSFC-08T-G(2479),                 -- Fabric Module(T Type-G)
            type-S66-8VGT(2480),                   -- 8-Port SmartGE (5/2.5/1G) Interface Module
            type-LSXM1MOD24KBR1(2481),             -- 24KBR Flexible Line Processing Platform Module
            type-LSXM1TGS24C1(2482),               -- 24-Port 10GBASE Ethernet Optical Interface Module (SFP+,LC)
            type-LSXM1CGQ8C1(2483),                -- 8-Port 100GBASE Ethernet Optical Interface Module (QSFP28)
            type-LSXM1CGQ72KCR1(2484),             -- 36-Port 200GBASE Ethernet Optical Interface (QSFP56)/72-Port 100GBASE Ethernet Optical Interface Module (QSFP28)(KC)
            type-CSR05SRP1P3-GZ(2485),             -- Management and Route Process Board(1P3-GZ)
            type-CSPEX-2304X-GZ(2486),             -- Network Processing Unit(2304X-GZ)
            type-CSFC-08T-GZ(2487),                -- Fabric Module(T Type-GZ)
            type-MIC-CQ1L2(2488),                  -- 1-port 100G  Ethernet Optical Interface Card A(QSFP28)
            type-MIC-GT12L-M(2489),                -- 12-Port 1000BASE-X Ethernet Copper Interface Card (RJ45)
            type-MIC-GP24L-M(2490),                -- 24-Port 1000BASE-X Ethernet Optical Interface Card (SFP,LC)
            type-LSQM1MPUS06S8(2491),              -- Supervisor Engine Board
            type-LSQM3SUPA8(2492),                 -- Supervisor Engine Board
            type-LSQM1PT24TSSC8(2493),             -- 24-Port 1G EPON OLT Optical Interface(SFP,SC)+2-Port 10GE Optical Interface Board(SFP+,LC)(SC)
            type-LSQM2XPT12TSFD8(2494),            -- 12-Port 10/1GBASE-PR/PRX Ethernet Optical(SFP+,LC) and 8-Port 10GBASE-R SFP+ Optical Interface Board
            type-LSQM2GP24SA8(2495),               -- 24-Port GE Optical Interface(SFP,LC)(SA)
            type-LSQM1TGS16GPSA8(2496),            -- 24-Port 1000BASE-R Ethernet Optical Interface(SFP,LC)+16-Port 10GBASE-R Ethernet Optical Interface Board(SFP+,LC)
            type-LSEM1SUPB0(2500),                 -- Supervisor Engine Board
            type-LSEM1SF12B0(2501),                -- Switching Fabric Module
            type-LSEM1YGS48CQSF0(2502),            -- 48-Port 25G Ethernet Optical Interface(SFP28,LC)+4-Port 100G Ethernet Optical Interface Module(QSFP28)
            type-LSEM1CGQ16SF0(2503),              -- 16-Port 100G Ethernet Optical Interface Module(QSFP28)
            type-LSXM1SUPF1(2504),                 -- Supervisor Engine Unit
            type-LSXM1SUPFA1(2505),                -- AI Supervisor Engine Unit
            type-LSXM1SFP16F1(2506),               -- Fabric Module,Type P(Class F)
            type-LSXM1TGS48PB1(2507),              -- 48-Port 10GBASE Ethernet Optical Interface Module(SFP+,LC)(PB)
            type-LSXM1CGQ36PB1(2508),              -- 36-Port 100GBASE Ethernet Optical Interface Module(QSFP28)(PB)
            type-SR07MPUA3-M-Z(2509),              -- Management and Route Process Board(UA3-M)

            type-SFE-A-Z(2510),                    -- Network Processing Unit(A)
            type-MIC-CQ1L-M-Z(2511),               -- 1-Port 100G Ethernet Optical Interface Card(QSFP28,LC)
            type-MIC-CQ2L-M-Z(2512),               -- 2-Port 100G Ethernet Optical Interface Card(QSFP28,LC)
            type-MIC-XP4L-M-Z(2513),               -- 4-Port 10GBASE-R/W Ethernet Optical Interface Card (SFP+,LC)
            type-MIC-GP12L-M-Z(2514),              -- 12-port 1000BASE-X Optical Interface Card(SFP,LC)
            type-MIC-XP10L-M-Z(2515),              -- 10-port 10GBASE-R/W Ethernet Optical Interface Card Module(SFP+,LC)
            type-MIC-CLP4L-M-Z(2516),              -- 4-port OC-3/STM-1 Channelized POS Optical Interface Card(SFP,LC)
            type-MIC-ET16L-M-Z(2517),              -- 16-port E1 Copper Interface Card(HM96 Male Connector)
            type-MIC-PSP4L-M-Z(2518),              -- 4-Port OC-48c/STM-16c POS Optical Interface Card,(SFP,LC)
            type-MIC-TCP8L-M-Z(2519),              -- 8-Port OC-3c/OC-12c POS Optical Interface Card,(SFP,LC)
            type-MIC-SP4L-M-Z(2520),               -- 4-port OC-3c/STM-1c POS/ATM or 1-port OC-12c/STM-4c POS/ATM Fiber Interface Card(SFP,LC)
            type-MIC-GT12L-M-Z(2521),              -- 12-Port 1000BASE-X Ethernet Copper Interface Card (RJ45)
            type-MIC-GP24L-M-Z(2522),              -- 24-Port 1000BASE-X Ethernet Optical Interface Card (SFP,LC)
            type-DS-3E7803-MPU(2523),              -- Supervisor Engine Board
            type-DS-3E7800-16X24F-SC(2524),        -- 24-Port 1000BASE-R Ethernet Optical Interface(SFP,LC)+16-Port 10GBASE-R Ethernet Optical Interface Board(SFP+,LC)
            type-DS-3E7800-48F-SC(2525),           -- 48-Port 1000BASE-X Ethernet Optical Interface Board(SFP,LC)
            type-DS-3E7800-24F8T-SC(2526),         -- 8-Port 10/100/1000BASE-T Ethernet Interface Board(RJ45)+24-Port 1000BASE-X Ethernet SFP Optical Interface(SFP,LC)(SC)
            type-DS-3E7806-MPU(2527),              -- Supervisor Engine Board
            type-DS-3E7800-24T20F4X-SC(2528),      -- 24-Port 10/100/1000BASE-T Ethernet Interface Board(RJ45)+20-Port 1000BASE-X Ethernet SFP Optical Interface(SFP,LC)+4-Port 10GBASE-R Optical Interface Board(SFP+,LC)(SC)
            type-DS-3E7800-24T8F-SC(2529),         -- 24-Port 10/100/1000BASE-T Ethernet Interface Board(RJ45)+8-Port 1000BASE-X Ethernet SFP Optical Interface(SFP,LC)(SC)
            type-DS-3E7800-48T-SC(2530),           -- 48-Port 10/100/1000BASE-T Ethernet Interface Board(RJ45)(SC)
            type-RX-SRP1R3(2531),                  -- RX-SRP1R3,Main Processing Unit(1R3)
            type-CSFC-16T-G(2532),                 -- Fabric Module(T Type-G)
            type-NIC-XP20L-E(2533),                -- 20-port 10GBASE-R/W Ethernet Optical Interface Card A(SFP+,LC)(NIC)
            typeS7803-MPU(2534),                   -- Supervisor Engine Board
            typeS7806-MPU(2535),                   -- Supervisor Engine Board
            typeS78-16XF24GF(2536),                -- 24-Port 1000BASE-R Ethernet Optical Interface(SFP,LC)+16-Port 10GBASE-R Ethernet Optical Interface Board(SFP+,LC)
            typeS78-24GF8GT(2537),                 -- 8-Port 10/100/1000BASE-T Ethernet Interface Board(RJ45)+24-Port 1000BASE-X Ethernet SFP Optical Interface(SFP,LC)
            typeS78-24GT20GF4XF(2538),             -- 24-Port 10/100/1000BASE-T Ethernet Interface Board(RJ45)+20-Port 1000BASE-X Ethernet SFP Optical Interface(SFP,LC)+4-Port 10GBASE-R Optical Interface Board(SFP+,LC)
            typeS78-24GT8GF(2539),                 -- 24-Port 10/100/1000BASE-T Ethernet Interface Board(RJ45)+8-Port 1000BASE-X Ethernet SFP Optical Interface(SFP,LC)
            typeS78-48GF(2540),                    -- 48-Port 1000BASE-X Ethernet Optical Interface Board(SFP,LC)
            typeS78-48GT(2541),                    -- 48-Port 10/100/1000BASE-T Ethernet Interface Board(RJ45)
            type-LSWM124SFPP(2542),                -- 24-Port SFP+ Interface Module
            type-LSWM124MUPWR(2543),               -- 24-Port 10G PoE++ multi-speed Interface Module
            type-LSWM2XMGT2PM(2544),               -- 2*1G/2.5G/5G/10G BASE-T Ethernet Interface Board(RJ45)
            type-LSCM2GV48SC0-Z(2545),             -- 48-Port 10/100/1000BASE-T Ethernet Interface Board(RJ45)(SC)-POE
            type-LSCM2GT24GPTSSD0(2546),           -- 24-Port 10/100/1000BASE-T Ethernet Interface Board(RJ45)+20-Port 1000BASE-X Ethernet SFP Optical Interface(SFP,LC)+4-Port 10GBASE-R Optical Interface Board(SFP+,LC)(SD)
            type-LSCM2GT24GPSD0(2547),             -- 24-Port 10/100/1000BASE-T Ethernet Interface Board(RJ45)+8-Port 1000BASE-X Ethernet SFP Optical Interface(SFP,LC)(SD)
            type-LSCM2GP24GTSD0(2548),             -- 8-Port 10/100/1000BASE-T Ethernet Interface Board(RJ45)+24-Port 1000BASE-X Ethernet SFP Optical Interface(SFP,LC)(SD)
            type-LSCM2GT48SD0(2549),               -- 48-Port 10/100/1000BASE-T Ethernet Interface Board(RJ45)(SD)
            type-LSCM2GP48SD0(2550),               -- 48-Port 1000BASE-X Ethernet Optical Interface Board(SFP,LC)
            type-LSCM2TGS16GPSD0(2551),            -- 24-Port 1000BASE-R Ethernet Optical Interface(SFP,LC)+16-Port 10GBASE-R Ethernet Optical Interface Board(SFP+,LC)
            type-LSCM2GV48SD0(2552),               -- 48-Port 10/100/1000BASE-T Ethernet Interface Board(RJ45)(SD)-POE
            type-LSCM2GT24GPTSSD0-Z(2553),         -- 24-Port 10/100/1000BASE-T Ethernet Interface Board(RJ45)+20-Port 1000BASE-X Ethernet SFP Optical Interface(SFP,LC)+4-Port 10GBASE-R Optical Interface Board(SFP+,LC)(SD)
            type-LSCM2GT24GPSD0-Z(2554),           -- 24-Port 10/100/1000BASE-T Ethernet Interface Board(RJ45)+8-Port 1000BASE-X Ethernet SFP Optical Interface(SFP,LC)(SD)
            type-LSCM2GP24GTSD0-Z(2555),           -- 8-Port 10/100/1000BASE-T Ethernet Interface Board(RJ45)+24-Port 1000BASE-X Ethernet SFP Optical Interface(SFP,LC)(SD)
            type-LSCM2GT48SD0-Z(2556),             -- 48-Port 10/100/1000BASE-T Ethernet Interface Board(RJ45)(SD)
            type-LSCM2GP48SD0-Z(2557),             -- 48-Port 1000BASE-X Ethernet Optical Interface Board(SFP,LC)
            type-LSCM2TGS16GPSD0-Z(2558),          -- 24-Port 1000BASE-R Ethernet Optical Interface(SFP,LC)+16-Port 10GBASE-R Ethernet Optical Interface Board(SFP+,LC)
            type-LSCM2GV48SD0-Z(2559),             -- 48-Port 10/100/1000BASE-T Ethernet Interface Board(RJ45)(SD)-POE
            type-LSUM1TGT24FD0-Z(2560),            -- 24-Port 10GBASE-T Ethernet Copper Interface Module(RJ45)(FD)
            type-LSXM1TGS24XT24C4Q2TE2(2561),      -- 24-Port 10G Ethernet Optical Interface(SFP+)+4-Port 100G Ethernet Optical Interface(QSFP28)+24-Port 10G/1000BASE-T Ethernet Copper Interface(RJ45)+2-Port 40G Ethernet Optical Interface Module(QSFP+)
            type-CSFC-16T-GZ(2562),                -- Fabric Module(T Type-GZ)
            type-CSPEX-2612X(2563),                -- Service Processing Unit(2612X)
            type-CSPEX-2612XA(2564),               -- Service Processing Unit(2612XA)
            type-CEPC-CQ8L1A(2565),                -- 8-port 100G Ethernet Optical Interface Line Processing Unit A(QSFP28,LC)
            type-CEPC-CQ8L1(2566),                 -- 8-port 100G Ethernet Optical Interface Line Processing Unit(QSFP28,LC)
            type-CEPC-CQ12L(2567),                 -- 12-port 100G Ethernet Optical Interface Line Processing Unit(QSFP28,LC)
            type-CEPC-CQ16L(2568),                 -- 16-port 100G Ethernet Optical Interface Line Processing Unit(QSFP28,LC)
            type-CEPC-CQ16L1(2569),                -- 16-port 100G Ethernet Optical Interface Line Processing Unit(QSFP28,LC)
            type-ZD-S7803M-MPU-24T4X(2570),        -- Supervisor Engine Board With 24-Port 10/100/1000BASE-T Ethernet Interface+4-Port 10GBASE-R Ethernet SFP+ Optical Interfaces
            type-ZD-S7803M-MPU-24F4X(2571),        -- Supervisor Engine Board With 24-Port 1000BASE-X Ethernet SFP Optical Interface+4-Port 10GBASE-R Ethernet SFP+ Optical Interfaces
            type-ZD-S7800-24T8F-SC(2572),          -- 24-Port 10/100/1000BASE-T Ethernet Interface Board(RJ45)+8-Port 1000BASE-X Ethernet SFP Optical Interface(SFP,LC)(SC)
            type-ZD-S7800-48T-SC(2573),            -- 48-Port 10/100/1000BASE-T Ethernet Interface Board(RJ45)(SC)
            type-ZD-S7800-48F-SC(2574),            -- 48-Port 1000BASE-X Ethernet Optical Interface Board(SFP,LC)
            type-DS-3E7803M-MPU-24T4X(2575),       -- Supervisor Engine Board With 24-Port 10/100/1000BASE-T Ethernet Interface+4-Port 10GBASE-R Ethernet SFP+ Optical Interfaces
            type-DS-3E7803M-MPU-24F4X(2576),       -- Supervisor Engine Board With 24-Port 1000BASE-X Ethernet SFP Optical Interface+4-Port 10GBASE-R Ethernet SFP+ Optical Interfaces
            type-LSXM1SEERBA2(2582),               -- High Performance Compute Engine Module
            type-LSEM1SF08C0(2583),                -- Switch Fabric Board
            type-LSEM1TGS48QSSF0(2584),            -- 48-Port 10G Ethernet Optical Interface(SFP+)+4-Port 40G Ethernet Optical Interface Module (QSFP+)(SF)
            type-LSEM1QGS16SF0(2585),              -- 16-Port 40G Ethernet Optical Interface Ethernet Optical Interface Module (QSFP+)(SF)
            type-LSEM1TGS16GP32SD0(2586),          -- 16-Port 10G Ethernet Optical Interface (SFP+)+32-Port 1000BASE Ethernet Optical Interface Module (SFP)(SD)
            type-LSEM1SF08C0-Z(2587),              -- Switch Fabric Board
            type-LSEM1TGS48QSSF0-Z(2588),          -- 48-Port 10G Ethernet Optical Interface(SFP+)+4-Port 40G Ethernet Optical Interface Module (QSFP+)(SF)
            type-LSEM1QGS16SF0-Z(2589),            -- 16-Port 40G Ethernet Optical Interface Ethernet Optical Interface Module (QSFP+)(SF)
            type-LSEM1TGS16GP32SD0-Z(2590),        -- 16-Port 10G Ethernet Optical Interface (SFP+)+32-Port 1000BASE Ethernet Optical Interface Module (SFP)(SD)
            type-LSEM1SUPA0-Z(2591),               -- Supervisor Engine Board
            type-LSEM1SF06D0-Z(2592),              -- Switch Fabric Board
            type-LSEM1GT48TSSD0-Z(2593),           -- 48-Port 10/100/1000BASE-T Electrical Interface(RJ45)+4-Port 10GBASE-R Ethernet Optical Interface Board(SFP+,LC)(SD)
            type-LSEM1TGS24SD0-Z(2594),            -- 24-Port 10GBASE-R Ethernet SFP+ Optical Interface Board(SD)
            type-LSEM1TGS48SD0-Z(2595),            -- 48-Port 10GBASE-R Ethernet SFP+ Optical Interface Board(SD)
            type-LSEM1SUPB0-Z(2596),               -- Supervisor Engine Board
            type-LSEM1SF12B0-Z(2597),              -- Switching Fabric Module
            type-LSEM1YGS48CQSF0-Z(2598),          -- 48-Port 25G Ethernet Optical Interface(SFP28,LC)+4-Port 100G Ethernet Optical Interface Module(QSFP28)
            type-LSEM1CGQ16SF0-Z(2599),            -- 16-Port 100G Ethernet Optical Interface Module(QSFP28)
            type-LSEM1RCGQ2TSSF0(2600),            -- 2-Port 100G RPR Optical Interface(QSFP28)+16-Port 10G Ethernet Optical Interface Module(SFP+)(SF)
            type-LSEM1RCGQ2TSSF0-Z(2601),          -- 2-Port 100G RPR Optical Interface(QSFP28)+16-Port 10G Ethernet Optical Interface Module(SFP+)(SF)
            type-LSEM3RCGQ2TSSF0(2602),            -- 2-Port 100G RPR Optical Interface(QSFP28)+16-Port 10G Ethernet Optical Interface Module(SFP+)(SF)
            type-LSEM3SF08C0(2603),                -- Switch Fabric Board
            type-LSEM3TGS48QSSF0(2604),            -- 48-Port 10G Ethernet Optical Interface(SFP+)+4-Port 40G Ethernet Optical Interface Module (QSFP+)(SF)
            type-LSEM3QGS16SF0(2605),              -- 16-Port 40G Ethernet Optical Interface Ethernet Optical Interface Module (QSFP+)(SF)
            type-LSEM3TGS16GP32SD0(2606),          -- 16-Port 10G Ethernet Optical Interface (SFP+)+32-Port 1000BASE Ethernet Optical Interface Module (SFP)(SD)
            type-LSEM3SUPA0(2607),                 -- Supervisor Engine Board
            type-LSEM3SF06D0(2608),                -- Switch Fabric Board
            type-LSEM3GT48TSSD0(2609),             -- 48-Port 10/100/1000BASE-T Electrical Interface(RJ45)+4-Port 10GBASE-R Ethernet Optical Interface Board(SFP+,LC)(SD)
            type-LSEM3TGS24SD0(2610),              -- 24-Port 10GBASE-R Ethernet SFP+ Optical Interface Board(SD)
            type-LSEM3TGS48SD0(2611),              -- 48-Port 10GBASE-R Ethernet SFP+ Optical Interface Board(SD)
            type-LSEM3SUPB0(2612),                 -- Supervisor Engine Board
            type-LSEM3SF12B0(2613),                -- Switching Fabric Module
            type-LSEM3YGS48CQSF0(2614),            -- 48-Port 25G Ethernet Optical Interface(SFP28,LC)+4-Port 100G Ethernet Optical Interface Module(QSFP28)
            type-LSEM3CGQ16SF0(2615),              -- 16-Port 100G Ethernet Optical Interface Module(QSFP28)
            type-MIC-CQ1L2-Z(2616),                -- 1-port 100G  Ethernet Optical Interface Card A(QSFP28)
            type-MIC-GP10L2(2617),                 -- 10-Port 1000BASE-X Optical Interface Card,(SFP,LC)
            type-LSCM1FWDSD0(2618),                -- Next Generation Firewall
            type-LSCM2FWDSD0(2619),                -- Next Generation Firewall
            type-LSCM2CGS8QS8SF0(2620),            -- 8-Port 40G Ethernet Optical Interface(QSFP+)+8-Port 100G Ethernet Optical Interface Module(QSFP28)(SF)
            type-LSCM2TGS16GP32SD0(2621),          -- 32-Port 1000BASE Ethernet Optical Interface(SFP)+16-Port 10G Ethernet Optical Interface Module(SFP+)(SD)
            type-LSCM2TGS48SF0(2622),              -- 48-Port 10G Ethernet Optical Interface Module(SFP+)(SF)
            type-LSCM2YGS16TS8SF0(2623),           -- 16-Port 25G Ethernet Optical Interface(SFP28)+8-Port 10G Ethernet Optical Interface Module(SFP+)(SF)
            type-LSCM2YGS32TS16SF0(2624),          -- 32-Port 25G Ethernet Optical Interface(SFP28)+16-Port 10G Ethernet Optical Interface Module(SFP+)(SF)
            type-LSCM2SRP6C4Y06A0(2625),           -- Main Processing Unit with Switching and Routing With 4-Port 25G Ethernet Optical Interface(SFP28)+6-Port 100G Ethernet Optical Interfaces(QSFP28)
            type-LSXM1SUPRS2(2626),                -- Supervisor Engine Unit
            type-LSXM1CMURS2(2627),                -- Switch Environment Management Module
            type-LSCM1FWDSD0-Z(2628),              -- Next Generation Firewall
            type-LSCM2FWDSD0-Z(2629),              -- Next Generation Firewall
            type-LSCM2CGS8QS8SF0-Z(2630),          -- 8-Port 40G Ethernet Optical Interface(QSFP+)+8-Port 100G Ethernet Optical Interface Module(QSFP28)(SF)
            type-LSCM2TGS16GP32SD0-Z(2631),        -- 32-Port 1000BASE Ethernet Optical Interface(SFP)+16-Port 10G Ethernet Optical Interface Module(SFP+)(SD)
            type-LSCM2TGS48SF0-Z(2632),            -- 48-Port 10G Ethernet Optical Interface Module(SFP+)(SF)
            type-LSCM2YGS16TS8SF0-Z(2633),         -- 16-Port 25G Ethernet Optical Interface(SFP28)+8-Port 10G Ethernet Optical Interface Module(SFP+)(SF)
            type-LSCM2YGS32TS16SF0-Z(2634),        -- 32-Port 25G Ethernet Optical Interface(SFP28)+16-Port 10G Ethernet Optical Interface Module(SFP+)(SF)
            type-LSCM2SRP6C4Y06A0-Z(2635),         -- Main Processing Unit with Switching and Routing With 4-Port 25G Ethernet Optical Interface(SFP28)+6-Port 100G Ethernet Optical Interfaces(QSFP28)
            type-IE-Module-8G(2642),               -- 8*GE
            type-IE-Module-8P(2643),               -- 8*SFP
            type-IE-Module-4G4P(2644),             -- 4*GE+4*SFP
            type-MIC-GT20L1(2646),                 -- 20-port 1000BASE-X Ethernet Copper Interface Card(RJ45)
            type-MIC-XP10L-LAN(2647),              -- 10-port 10GBASE-R/W Ethernet Optical Interface Card Module(SFP+,LC)-LAN
            type-MIC-SEC-M(2648),                  -- Network Data Encryption Interface Card(MIC-SEC)
            type-MIC-GT20L1-Z(2649),               -- 20-port 1000BASE-X Ethernet Copper Interface Card Z(RJ45)
            type-MIC-XP10L-LAN-Z(2650),            -- 10-port 10GBASE-R/W Ethernet Optical Interface Card Module(SFP+,LC)-LAN-Z
            type-MIC-SEC-M-Z(2651),                -- Network Data Encryption Interface Card(MIC-SEC-Z)
            type-LSXM3TGT48CQSF2(2652),            -- 48-Port 10GBASE-T Ethernet Copper Interface(RJ45)+2-Port 100G Ethernet Optical Interface Module(QSFP28)
            type-LSDM3TGT48CQSF0-Z(2653),          -- 48-Port 10GBASE-T Ethernet Copper Interface(RJ45)+2-Port 100G Ethernet Optical Interface Module(QSFP28)
            type-LSEM1GV48TSSD0(2654),             -- 48-Port 10/100/1000BASE-T Ethernet Copper Interface(RJ45)+4-Port 10G Ethernet Optical Interface Module(SFP+),PoE Plus
            type-LSEM1GV48TSSD0-Z(2655),           -- 48-Port 10/100/1000BASE-T Ethernet Copper Interface(RJ45)+4-Port 10G Ethernet Optical Interface Module(SFP+),PoE Plus
            type-LSEM1GT24GP16TSSD0(2656),         -- 24-Port 10/100/1000BASE-T Ethernet Copper Interface(RJ45)+16-Port 1000BASE Ethernet Optical Interface(SFP)+12-Port 10G Ethernet Optical Interface Module(SFP+)
            type-LSEM1TGT48SD0(2657),              -- 48-Port 10GBASE-T Ethernet Copper Interface(RJ45)
            type-LSEM1CGQ36SF0(2658),              -- 36-Port 100G Ethernet Optical Interface Module(QSFP28)
            type-LSEM1CDQ2SF0(2659),               -- 2-Port 400G Ethernet Optical Interface Module(QSFP-DD)
            type-LSEM1GT48TS24QSSD0(2660),         -- 48-Port 10/100/1000BASE-T Ethernet Copper Interface(RJ45)+24-Port 10G Ethernet Optical Interface(SFP+)+2-Port 40G Ethernet Optical Interface Module(QSFP+)
            type-CSPEX-2612X-E(2661),              -- Service Processing Unit(2612X-E)
            type-SR05SRP1P3-DZEC(2662),            -- DZEC Main Processing Unit(1P3)
            type-RT-FIP-680-G(2663),               -- Network Processing Unit(G)
            type-LSCM3YGS32TS16SF0(2664),          -- 32-Port 25G Ethernet Optical Interface(SFP28)+16-Port 10G Ethernet Optical Interface Module(SFP+)(SF)
            type-LSCM3TGS48SF0(2665),              -- 48-Port 10G Ethernet Optical Interface Module(SFP+)(SF)
            type-LSCM3YGS16TS8SF0(2666),           -- 16-Port 25G Ethernet Optical Interface(SFP28)+8-Port 10G Ethernet Optical Interface Module(SFP+)(SF)
            type-LSCM3CGS8QS8SF0(2667),            -- 8-Port 40G Ethernet Optical Interface(QSFP+)+8-Port 100G Ethernet Optical Interface Module(QSFP28)(SF)
            type-LSCM3SRP6C4Y06A0(2668),           -- Main Processing Unit with Switching and Routing With 4-Port 25G Ethernet Optical Interface(SFP28)+6-Port 100G Ethernet Optical Interfaces(QSFP28)
            type-LSCM3YGS32TS16SF0-Z(2669),        -- 32-Port 25G Ethernet Optical Interface(SFP28)+16-Port 10G Ethernet Optical Interface Module(SFP+)(SF)
            type-LSCM3TGS48SF0-Z(2670),            -- 48-Port 10G Ethernet Optical Interface Module(SFP+)(SF)
            type-LSCM3YGS16TS8SF0-Z(2671),         -- 16-Port 25G Ethernet Optical Interface(SFP28)+8-Port 10G Ethernet Optical Interface Module(SFP+)(SF)
            type-LSCM3CGS8QS8SF0-Z(2672),          -- 8-Port 40G Ethernet Optical Interface(QSFP+)+8-Port 100G Ethernet Optical Interface Module(QSFP28)(SF)
            type-LSCM2TGS16GP32SC0-Z(2673),        -- 32-Port 1000BASE Ethernet Optical Interface(SFP)+16-Port 10G Ethernet Optical Interface Module(SFP+)(SC)
            type-LSCM3SRP6C4Y06A0-Z(2674),         -- Main Processing Unit with Switching and Routing With 4-Port 25G Ethernet Optical Interface(SFP28)+6-Port 100G Ethernet Optical Interfaces(QSFP28)
            type-LSXM1SUPCH1(2675),                -- Supervisor Engine Board
            type-LSXM1SFC08C1(2676),               -- Switch Fabric Board
            type-LSXM1TGS48CA1(2677),              -- 48-Port 10G Ethernet Optical Interface Module(SFP+)
            type-LSXM1CGQ18CA1(2678),              -- 18-Port 100G Ethernet Optical Interface Module(QSFP28)
            type-LSXM1QGS36CA1(2679),              -- 36-Port 40G Ethernet Optical Interface Module(QSFP+)
            type-LSXM3SUPCH1(2680),                -- Supervisor Engine Board
            type-LSXM3TGS48CA1(2681),              -- 48-Port 10G Ethernet Optical Interface Module(SFP+)
            type-LSXM3CGQ18CA1(2682),              -- 18-Port 100G Ethernet Optical Interface Module(QSFP28)
            type-LSXM3QGS36CA1(2683),              -- 36-Port 40G Ethernet Optical Interface Module(QSFP+)
            type-MIC-SEC(2684),                    -- Network Data Encryption Interface Card(MIC-SEC)
            type-MIC-SEC-Z(2685),                  -- Network Data Encryption Interface Card(MIC-SEC-Z)
            type-MIC-XP12LF(2686),                 -- 12-port 10GBASE-R/W Ethernet Optical Interface Card Module(SFP+,LC)
            type-MIC-XP12LF-Z(2687),               -- 12-port 10GBASE-R/W Ethernet Optical Interface Card Module(SFP+,LC)
            type-MIC-CQ1LF(2688),                  -- 2-port 100G Flexible Ethernet Optical Interface Card(QSFP28,LC)
            type-MIC-CQ1LF-Z(2689),                -- 2-port 100G Flexible Ethernet Optical Interface Card(QSFP28,LC)
            type-SR07IPUA3-M(2690),                -- Management and Route Process Board(UA3-M)
            type-LSXM1SUPS1(2691),                 -- Supervisor Engine Board
            type-LSXM1CGQ36S1(2692),               -- 36-Port 100GBASE-R Ethernet Optical Interface Board(QSFP28,LC)
            type-LSEM3SUPA3(2693),                 -- Supervisor Engine Board
            type-LSEM1SF06D3(2694),                -- Switch Fabric Board
            type-LSEM1SF08C3(2695),                -- Switch Fabric Board
            type-LSEM3CGQ8SF3(2696),               -- 8-Port 100G Ethernet Optical Interface Module(QSFP28)
            type-LSEM3TGS48SF3(2697),              -- 48-Port 10GBASE-R Ethernet SFP+ Optical Interface Board(SF)
            type-LSEM1GT48SD3(2698),               -- 48-Port 10/100/1000BASE-T Electrical Interface Board(RJ45)(SD)
            type-LSEM2GP48SD3(2699),               -- 48-Port 1000BASE-X Optical Interface Board(SFP,LC)
            type-MIC-XP10LF(2700),                 -- 10-port 10GBASE-R/W Ethernet Optical Interface Card Module(SFP+,LC)
            type-MIC-XP10LF-Z(2701),               -- 10-port 10GBASE-R/W Ethernet Optical Interface Card Module(SFP+,LC)
            type-DS-3E12508X-MPU(2702),            -- Supervisor Engine Board
            type-DS-3E12508X-CLOS(2703),           -- Switching Fabric Module
            type-DS-3E12512X-MPU(2704),            -- Supervisor Engine Board
            type-DS-3E12512X-CLOS(2705),           -- Switching Fabric Module
            type-DS-3E12500X-48T4X-SD(2706),       -- 48-Port 10/100/1000BASE-T Electrical Interface(RJ45)+4-Port 10GBASE-R Ethernet Optical Interface Board(SFP+,LC)(SD)
            type-DS-3E12500X-48X-SD(2707),         -- 48-Port 10GBASE-R Ethernet SFP+ Optical Interface Board(SD)
            type-DS-3E12500X-48Y4C-SF(2708),       -- 48-Port 25G Ethernet Optical Interface(SFP28,LC)+4-Port 100G Ethernet Optical Interface Module(QSFP28)
            type-DS-3E12500X-16C-SF(2709),         -- 16-Port 100G Ethernet Optical Interface Module(QSFP28)
            type-DS-3E12500X-16Q-SF(2710),         -- 16-Port 40G Ethernet Optical Interface Ethernet Optical Interface Module (QSFP+)(SF)
            type-DS-3E12500X-32F16X-SD(2711),      -- 16-Port 10G Ethernet Optical Interface (SFP+)+32-Port 1000BASE Ethernet Optical Interface Module (SFP)(SD)
            type-LSWM1M4CDC(2712),                 -- 4-Port 400GBASE Ethernet Optical Interface Module(QSFP-DD)
            type-LSEM2TGS48SD0(2713),              -- 48-Port 10GBASE-R Ethernet SFP+ Optical Interface Board(SD)
            type-LSEM1SF06B0(2714),                -- Switch Fabric Board
            type-LSXM3SFS08H2(2715),               -- Switch Fabric Board
            type-LSXM3SFS16H2(2716),               -- Switch Fabric Board
            type-LSXM4CGQ36SF2(2717),              -- 36-Port 100GBASE-R Ethernet Optical Interface Board(QSFP28,LC)
            type-LSEM2TGS48SD0-Z(2718),            -- 48-Port 10GBASE-R Ethernet SFP+ Optical Interface Board(SD)
            type-LSEM1SF06B0-Z(2719),              -- Switch Fabric Board
            type-LSDM3SFS08H2-Z(2720),             -- Switch Fabric Board
            type-LSDM3SFS16H2-Z(2721),             -- Switch Fabric Board
            type-LSDM4CGQ36SF2-Z(2722),            -- 36-Port 100GBASE-R Ethernet Optical Interface Board(QSFP28,LC)
            type-LSUM1MPUS06XEB8(2723),            -- Supervisor Engine Board
            type-LSUM1MPUS10XEA8(2724),            -- Supervisor Engine Board
            type-LSUM1CGS8SH8(2725),               -- 8-Port 100G Ethernet Optical Interface Module(QSFP28)(SH)
            type-LSUM2GT48SE8(2726),               -- 48-Port 1000Base-T Gigabit Ethernet Interface Board(RJ45)(SE)
            type-LSUM2GT24PTSSE8(2727),            -- 24-Port 1000Base-T Gigabit Ethernet Interface Board(RJ45)+20-Port GE Optical Interface(SFP,LC)+4-Port 10GE Optical Interface Board(SFP+,LC)(SE)
            type-LSUM2GP44TSSE8(2728),             -- 44-Port GE Optical Interface(SFP,LC)+4-Port 10GE Optical Interface Board(SFP+,LC)(SE)
            type-CSPEX-2304X-LG(2729),             -- Network Processing Unit(2304X-LG)
            type-CEPC-DQ2L1-G(2730),               -- 2-port 400G Ethernet Optical Interface Line Processing Unit(QSFP28,LC)
            type-SRFP-A3(2731),                    -- Management and Route Process Board(A3)
            type-LSXM2SUP02LR1(2732),              -- Supervisor Engine Unit
            type-LSXM12GQ48KBR1(2733),             -- 48-Port 100GBASE Ethernet Optical Interface Module(QSFP28)(KB)
            type-LSXM3QGS36SF1(2734),              -- 36-Port 40G Ethernet Optical Interface Module (QSFP+)
            type-LSXM3TGS48SF1(2735),              -- 48-Port 10GBASE-R Ethernet SFP+ Optical Interface Board(SF)
            type-CSPEX-2502X(2736),                -- Network Processing Unit(2502X)
            type-LSWM2QP2PB(2737),                 -- 2-Port QSFP+ Interface Module
            type-MPUC-1P3(2738),                   -- DNR20008C-DN Main Processing Unit(1P3)
            type-FSUC-1802X(2739),                 -- Service Processing Unit(1802X)
            type-SFUC-08E1(2740),                  -- DNR20008C-DN Fabric Module(E Type)
            type-ICC-CQ2LF(2741),                  -- 2-port 100G Flexible Ethernet Optical Interface Card(QSFP28,LC)
            type-ICC-XP20L1(2742),                 -- 20-port 10GBASE-R/W Ethernet Optical Interface Card(SFP+,LC)(NIC)
            type-MPUM-A3(2743),                    -- DNR20008M-DN Management and Route Process Board(UA3-M)
            type-SFUM-A(2744),                     -- Network Processing Unit(A)
            type-ICM-CQ1LF(2745),                  -- 1-port 100G Flexible Ethernet Optical Interface Card(QSFP28,LC)
            type-ICM-XP10L1(2746),                 -- 10-port 10GBASE-R/W Ethernet Optical Interface Card Module(SFP+,LC)
            type-LSCM2XPT24SF0(2747),              -- 24-Port 10G EPON OLT Optical Interface Board(SFP+,SC)
            type-LSCM2XPG24SF0(2748),              -- 24-Port XGS-PON OLT Optical Interface Board(SFP+,SC)
            type-MIC-XP2L-M(2749),                 -- 2-Port 10GBASE-R/W Ethernet Optical Interface Card (SFP+,LC)
            type-MIC-XP2L-M-Z(2750),               -- 2-Port 10GBASE-R/W Ethernet Optical Interface Card (SFP+,LC)
            type-MIC-XP5L2(2752),                  -- 5-Port 10GBASE-R/W Ethernet Optical Interface Card,(SFP+,LC)
            type-CSR05SRP051E3-G(2753),            -- Management and Route Process Board(1E3-G)
            type-CSR05SRP101E3-G(2754),            -- Management and Route Process Board(1E3-G)
            type-CSFC-10T-G(2755),                 -- Fabric Module(T Type-G)
            type-LSUM1FAB06XEB3(2756),             -- Switch Fabric Board
            type-LSUM2GP40TS8FD3(2757),            -- 40-Port 1000BASE-X Optical Interface(SFP,LC)+8-Port 10GBASE-R Ethernet Optical Interface
            type-LSEM1GT48TS24QSSD0-Z(2758),       -- 48-Port 10/100/1000BASE-T Ethernet Copper Interface(RJ45)+24-Port 10G Ethernet Optical Interface(SFP+)+2-Port 40G Ethernet Optical Interface Module(QSFP+)
            type-LSEM1CGQ36SF0-Z(2759),            -- 36-Port 100G Ethernet Optical Interface Module(QSFP28)
            type-LSEM1TGT48SD0-Z(2760),            -- 48-Port 10GBASE-T Ethernet Copper Interface(RJ45)
            type-LSEM3CDQ2SF0(2761),               -- 2-Port 400G Ethernet Optical Interface Module(QSFP-DD)
            type-LSEM3CGQ36SF0(2762),              -- 36-Port 100G Ethernet Optical Interface Module(QSFP28)
            type-LSEM3QGS36SF0(2763),              -- 36-Port 40G Ethernet Optical Interface Module(QSFP+)
            type-LSEM1QGS36SF0(2764),              -- 36-Port 40G Ethernet Optical Interface Module(QSFP+)
            type-S16700X-G-MPU(2765),              -- Supervisor Engine Board
            type-S16706X-G-NET(2766),              -- Switch Fabric Board
            type-S16708X-G-NET(2767),              -- Switch Fabric Board
            type-S16700-48GT4XFSD(2768),           -- 48-Port 10/100/1000BASE-T Electrical Interface(RJ45)+4-Port 10GBASE-R Ethernet Optical Interface Board(SFP+,LC)(SD)
            type-S16700-48XFSD(2769),              -- 48-Port 10GBASE-R Ethernet SFP+ Optical Interface Board(SD)
            type-S16700-16QFSF(2770),              -- 16-Port 40G Ethernet Optical Interface Ethernet Optical Interface Module (QSFP+)(SF)
            type-S16700-32GF16XFSD(2771),          -- 16-Port 10G Ethernet Optical Interface (SFP+)+32-Port 1000BASE Ethernet Optical Interface Module (SFP)(SD)
            type-LSCM3MPUS10C0(2772),              -- Supervisor Engine Board
            type-LSCM3MPUS10C0-Z(2773),            -- Supervisor Engine Board
            type-LSXM2TGS48TD2(2774),              -- 48-Port 10G Ethernet Optical Interface Module(SFP+)
            type-LSCM2YSV16TSV32SD0(2775),         -- 32-Port 10G Ethernet Optical Interface(SFP+)+16-Port 25G Ethernet Optical Interface Module(SFP28)(SD)
            type-LSCM2GP40TS8SD0(2776),            -- 40-Port 1000BASE Ethernet Optical Interface(SFP)+8-Port 10G Ethernet Optical Interface Module(SFP+)(SD)
            type-LSCM2GT24TSSD0(2777),             -- 24-Port 10/100/1000BASE-T Ethernet Interface Board(RJ45)+4-Port 10GBASE-R Optical Interface Board(SFP+,LC)(SD)
            type-LSCM3TGS32GP16SF0(2778),          -- 16-Port 1000BASE Ethernet Optical Interface(SFP)+32-Port 10G Ethernet Optical Interface Module(SFP+)(SF)
            type-LSEM2TGS16GP32SD0(2779),          -- 32-Port 1000BASE Ethernet Optical Interface(SFP)+16-Port 10G Ethernet Optical Interface Module(SFP+)(SD)
            type-DS-3E12500X-24T16F12X-SD(2780),   -- 24-Port 10/100/1000BASE-T Ethernet Copper Interface(RJ45)+16-Port 1000BASE Ethernet Optical Interface(SFP)+12-Port 10G Ethernet Optical Interface Module(SFP+)
            type-DS-3E7800-48X-SE(2781),           -- 48-Port 10GBASE-R Ethernet SFP+ Optical Interface Board(SE)
            type-CSR05SRP1R3-G(2782),              -- Management and Route Process Board(1R3-G)
            type-NIC-QP3L(2783),                   -- 3-port 40G Ethernet Optical Interface Card(QSFP+,LC)
            type-LS5M1IERS4C2-G(2787),             -- 4-RS485 Interface+2-CAN Interface Module
            type-LS5M1IEGT4GP4-G(2788),            -- 4-Port 10/100/1000BASE-T Ethernet Interface+4-Port 1000BASE-X Optical Interface(SFP,LC) Module
            type-LS5M1IEGT8-G(2789),               -- 8-Port 10/100/1000BASE-T Ethernet Interface Module
            type-LS5M1IEGP8-G(2790),               -- 8-Port 1000BASE-X Optical Interface(SFP,LC) Module
            type-LSEM1TGV48SD0(2791),              -- 48-Port 10GBASE-T Ethernet Copper Interface(RJ45)
            type-LSXM3YGS24XT24C6SF2(2792),        -- 24-Port 10GBASE-T Ethernet Copper Interface(RJ45)+24-Port 25G Ethernet Optical Interface(SFP28)+6-Port 100G Ethernet Optical Interface Module(QSFP28)(SF)
            type-LSDM3YGS24XT24C6SF0-Z(2793),      -- 24-Port 10GBASE-T Ethernet Copper Interface(RJ45)+24-Port 25G Ethernet Optical Interface(SFP28)+6-Port 100G Ethernet Optical Interface Module(QSFP28)(SF)
            type-LSXM3CGQ48SG2(2794),              -- 48-Port 100G Ethernet Optical Interface Module(QSFP28)
            type-LSDM3CGQ48SG0-Z(2795),            -- 48-Port 100G Ethernet Optical Interface Module(QSFP28)
            type-LSEM5TGS48QSSF0(2796),            -- 48-Port 10G Ethernet Optical Interface(SFP+)+4-Port 40G Ethernet Optical Interface Module (QSFP+)(SF)
            type-LSEM5TGS48QSSF0-Z(2797),          -- 48-Port 10G Ethernet Optical Interface(SFP+)+4-Port 40G Ethernet Optical Interface Module (QSFP+)(SF)
            type-LSCM5TGS48SF0(2798),              -- 48-Port 10G Ethernet Optical Interface Module(SFP+)(SF)
            type-LSCM5TGS48SF0-Z(2799),            -- 48-Port 10G Ethernet Optical Interface Module(SFP+)(SF)
            type-SRFP-A1(2800),                    -- Management and Route Process Board(A1)
            type-MIC-ET16L-G(2801),                -- 16-Port E1/T1 Electrical Interface Card
            type-MIC-CQ1L-G(2802),                 -- 1-port 100G Ethernet Optical Interface Card Module(QSFP28,LC)
            type-MIC-TCP8L-G(2803),                -- SR0MDTCP8LA1,8-port OC-3c/OC-12c POS Optical Interface Card(SFP,LC),Domestic&Overseas Version
            type-MIC-CLP2L-G(2804),                -- 2-Port OC-3/STM-1 CPOS/POS Optical Interface Card,(SFP,LC)
            type-CSPEX-2314X-G(2805),              -- Network Processing Unit(2314X-G)
            type-CSFC-08E2A(2806),                 -- Fabric Module(E2A Type)
            type-CSFC-16E2A(2807),                 -- Fabric Module(E2A Type)
            type-MIC-XP12L-G(2808),               -- 12-Port 10GBASE-R/W Ethernet Optical Interface Card,(SFP+,LC)
            type-MIC-XP6L-G(2809),                -- 6-Port 10GBASE-R/W Ethernet Optical Interface Card,(SFP+,LC)
            type-MIC-XP4L-G(2810),                -- 4-Port 10GBASE-R/W Ethernet Optical Interface Card,(SFP+,LC)
            type-MIC-GP12L-G(2811),               -- 12-Port 1000BASE-X Ethernet Optical Interface Card(SFP,LC)
            type-RX-NIC-YGS8L(2812),              -- 8-port 25G Ethernet Optical Interface Card(SFP28,LC)
            type-CSPEX-2104X-G(2883),              -- Network Processing Unit(2104X-G)
            type-CEPC-CQ8L3A(2884),                -- 8-port 100G Ethernet Optical Interface Line Processing Unit A(QSFP28,LC)
            type-CSPEX-2612X3A(2885),              -- Service Processing Unit(2612X3A)
            type-CSFC-10E-G(2886),                 -- Fabric Module(T Type-G)
            type-VO-SWCSJ02-12GPSC(2887),          -- Supervisor Engine Board With 16-Port 1000BASE-X Ethernet SFP Optical Interface+12-Port 10GBASE-R Ethernet SFP+ Optical Interfaces
            type-VO-SWCSJ02-12GTSC(2888),          -- Supervisor Engine Board With 16-Port 10/100/1000BASE-T Ethernet Interface+12-Port 10GBASE-R Ethernet SFP+ Optical Interfaces
            type-VO-SWCSJ02-GP24T(2889),           -- Supervisor Engine Board With 24-Port 1000BASE-X Ethernet SFP Optical Interface+4-Port 10GBASE-R Ethernet SFP+ Optical Interfaces
            type-VO-SWCSJ02-GT24T(2890),           -- Supervisor Engine Board With 24-Port 10/100/1000BASE-T Ethernet Interface+4-Port 10GBASE-R Ethernet SFP+ Optical Interfaces
            type-VO-SWCSJ02-GS48(2891),            -- 48-Port 10GBASE-R Ethernet SFP+ Optical Interface Board
            type-VO-SWCSJ02-GP48(2892),            -- 48-Port 1000BASE-X Ethernet Optical Interface Board(SFP,LC)
            type-VO-SWCSJ02-GT48(2893),            -- 48-Port 10/100/1000BASE-T Ethernet Interface Board(RJ45)
            type-VO-SWCSJ02-24GPT(2894),           -- 24-Port 10/100/1000BASE-T Ethernet Interface Board(RJ45)+20-Port 1000BASE-X Ethernet SFP Optical Interface(SFP,LC)+4-Port 10GBASE-R Optical Interface Board(SFP+,LC)
            type-VO-SWCSJ02-24GPS(2895),           -- 24-Port 10/100/1000BASE-T Ethernet Interface Board(RJ45)+8-Port 1000BASE-X Ethernet SFP Optical Interface(SFP,LC)
            type-VO-SLRAL02-051E3(2896),           -- VisionVera VO-SLRAL02-051E3 Management and Route Process Board(051E3)
            type-VO-SLRAL03-101E3(2897),           -- VisionVera VO-SLRAL03-101E3 Management and Route Process Board(101E3)
            type-VO-SLRAL03-10TG(2898),            -- VisionVera CSFC-10T-G Fabric Module(T Type-G)
            type-VO-SLRAL02-2304X(2899),           -- Network Processing Unit(2304X)
            type-VO-SLRAL02-CQ1L2(2900),           -- 1-port 100G Ethernet Optical Interface Card A(QSFP28)
            type-VO-SLRAL02-GP10L2(2901),          -- 10-Port 1000BASE-X Optical Interface Card,(SFP,LC)
            type-VO-SLRAL02-XP5L2(2902),           -- 5-Port 10GBASE-R/W Ethernet Optical Interface Card,(SFP+,LC)
            type-VO-SLRAL02-XP10L(2903),           -- 10-port 10GBASE-R/W Ethernet Optical Interface Card Module(SFP+,LC)
            type-GIC-CQ1L-G(2904),                 -- 1-port 100G Ethernet Optical Interface Card Module(QSFP28,LC)
            type-GIC-XP12L-G(2905),                -- 12-Port 10GBASE-R/W Ethernet Optical Interface Card,(SFP+,LC)
            type-GIC-XP6L-G(2906),                 -- 6-Port 10GBASE-R/W Ethernet Optical Interface Card,(SFP+,LC)
            type-GIC-XP4L-G(2907),                 -- 4-Port 10GBASE-R/W Ethernet Optical Interface Card,(SFP+,LC)
            type-GIC-GP12L-G(2908),                -- 12-Port 1000BASE-X Ethernet Optical Interface Card(SFP,LC)
            type-GIC-TCP8L-G(2909),                -- SR0MDTCP8LA1,8-port OC-3c/OC-12c POS Optical Interface Card(SFP,LC),Domestic&Overseas Version
            type-GIC-CLP2L-G(2910),                -- 2-Port OC-3/STM-1 CPOS/POS Optical Interface Card,(SFP,LC)
            type-GIC-ET16L-G(2911),                -- 16-Port E1/T1 Electrical Interface Card
            type-CSR05SRP101E3-G1(2912),           -- Management and Route Process Board(1E3-G1)
            type-RX-SRP1R3-G(2913),                -- Management and Route Process Board(1R3-G)
            type-RX-SPE400E-G(2914),               -- Service Processing Unit( SPE400E-G)
            type-RX-SFC-08E2(2915),                -- Fabric Module(08E2 Type)
            type-LSXM3SUPRS2-G1(2916),             -- Supervisor Engine Board
            type-LSEM3SUPB0-G1(2917),              -- Supervisor Engine Board
            type-LSEM1SF12B0-G3(2918),             -- Switching Fabric Module
            type-LSEM3TGS48QSSF0-G3(2919),         -- 48-Port 10G Ethernet Optical Interface(SFP+)+4-Port 40G Ethernet Optical Interface Module (QSFP+)(SF)
            type-LSEM3CGQ16SF0-G3(2920),           -- 16-Port 100G Ethernet Optical Interface Module(QSFP28)
            type-LSEM1GT48TSSD0-G3(2921),          -- 48-Port 10/100/1000BASE-T Electrical Interface(RJ45)+4-Port 10GBASE-R Ethernet Optical Interface Board(SFP+,LC)(SD)
            type-SFE-A1(2922),                     -- Network Processing Unit(A1)
            type-LSXM3CCQ36SG2(2923),              -- 36-Port 200G Ethernet Optical Interface Module(QSFP56)
            type-LSDM3CCQ36SG0-Z(2924),            -- 36-Port 200G Ethernet Optical Interface Module(QSFP56)
            type-CSPEX-2304X-G2(2925),             -- Network Processing Unit(2304X-G2)
            type-LSXM1CDQ18KCR1(2926),             -- 18-Port 400GBASE Ethernet Optical Interface Module (QSFP-DD)(KC)
            type-CSPEX-2314X-G2(2927),             -- Network Processing Unit(2314X-G2)

            type-LSXM3CDHQ36RSG2(2929),            -- 36-Port 400G Ethernet Optical Interface Module(QSFP112)
            type-LSXM3SFS08K2(2930),               -- Switch Fabric Board
            type-LSXM3CDHQ36SG2(2931),             -- 36-Port 400G Ethernet Optical Interface Module(QSFP112)
            type-LSXM1QGS36TD2-G(2932),            -- 36-Port 40G Ethernet Optical Interface Module (QSFP+)
            type-LSXM1CGQ18TD2-G(2933),            -- 18-Port 100G Ethernet Optical Interface Module (QSFP28)
            type-LSXM1TGS48TD2-G(2934),            -- 48-Port 10GBASE-R Ethernet SFP+ Optical Interface Board(SF)
            type-LSXM1SFT16E1-G(2935),             -- Switch Fabric Board
            type-LSXM2SFT08E2-G(2936),             -- Switch Fabric Board
            type-LSXM2SUPT2-G(2937),               -- Supervisor Engine Board
            type-SFE-A2(2938),                     -- Network Processing Unit(A2)
            type-SRFP-A2(2939),                    -- Management and Route Process Board(A2)

            type-MIC-LGQ2LF(2941),                 -- 2-port 50G Flexible Ethernet Optical Interface Card(QSFP28,LC)(MIC)
            type-MIC-YGS4L(2942),                  -- 4-port 25G Ethernet Optical Interface Card(SFP28,LC)(MIC)
            type-CSR05SRP101E3-G3(2943),           -- Management and Route Process Board(1E3-G1)
            type-LSEM3SUPA0-G1(2944),              -- Supervisor Engine Board
            type-LSEM1SF06D0-G3(2945),             -- Switch Fabric Board
            type-LSEM1SF08C0-G3(2946),             -- Switch Fabric Board
            type-RX-SRP051E3-G(2947),              -- Management and Route Process Board(1E3-G)
            type-LSUM1TGS24CSSH0(2948),            -- 24-Port 10G Ethernet Optical Interface Module(SFP+,LC)+4-Port 100G Ethernet Optical Interface Module(QSFP28)(SH)
            type-CSPEX-2314X-G1(2949),             -- Service Processing Unit(2314X-G1
            type-RX-SRP031E3-G(2950),              -- Management and Route Process Board(031E3-G)
            type-RX-SPE300E-G(2951),               -- Network Processing Unit(SPE300E-G)
            type-RX-GIC-CQ1LF(2952),               -- 1-port 100G Flexible Ethernet Optical Interface Card(QSFP28,LC)(GIC)
            type-RX-GIC-YGS4L(2953),               -- 4-port 25G Ethernet Optical Interface Card(SFP28,LC)(GIC)
            type-RX-GIC-XP10L(2954),               -- 10-port 10GBASE-R/W Ethernet Optical Interface Card Module(SFP+,LC)-LAN(GIC)
            type-RX-GIC-LGQ2L(2955),               -- 2-port 50G Flexible Ethernet Optical Interface Card(QSFP28,LC)(GIC)
            type-LSCM3MPUS06A0-G3(2956),           -- Supervisor Engine Board
            type-LSCM3MPUS10B0-G3(2957),           -- Supervisor Engine Board
            type-LSCM2TGS16GP32SD0-G3(2958),       -- 32-Port 1000BASE Ethernet Optical Interface(SFP)+16-Port 10G Ethernet Optical Interface Module(SFP+)(SD)
            type-LSCM2GP48SD0-G3(2959),            -- 48-Port 1000BASE-X Ethernet Optical Interface Board(SFP,LC)
            type-LSCM2GT48SD0-G3(2960),            -- 48-Port 10/100/1000BASE-T Ethernet Interface Board(RJ45)(SD)
            type-LSCM3TGS48SF0-G3(2961),           -- 48-Port 10G Ethernet Optical Interface Module(SFP+)(SF)
            type-LSCM3CGS8QS8SF0-G3(2962),         -- 8-Port 40G Ethernet Optical Interface(QSFP+)+8-Port 100G Ethernet Optical Interface Module(QSFP28)(SF)
            type-LSEM1GP40TS12SD0-G3(2963),        -- 40-Port 1000BASE Ethernet Optical Interface Module (SFP)+12-Port 10G Ethernet Optical Interface (SFP+)(SD)
            type-LSEM3SUPB3-G1(2964),              -- Supervisor Engine Board
            type-LSEM1SF12B3-G3(2965),             -- Switch Fabric Board
            type-LSEM3SUPA3-G1(2966),              -- Supervisor Engine Board
            type-LSEM1SF06D3-G3(2967),             -- Switch Fabric Board
            type-LSEM1SF08C3-G3(2968),             -- Switch Fabric Board
            type-LSEM1GP48SD3-G3(2969),            -- 48-Port 1000BASE-X Optical Interface Board(SFP,LC)
            type-LSEM1GT48SD3-G3(2970),            -- 48-Port 10/100/1000BASE-T Electrical Interface Board(RJ45)(SD)
            type-LSEM3TGS48SF3-G3(2971),           -- 48-Port 10GBASE-R Ethernet SFP+ Optical Interface Board(SF)
            type-LSEM3CGQ8SF3-G3(2972),            -- 8-Port 100G Ethernet Optical Interface Module(QSFP28)
            type-GIC-SP8L-G(2973),                 -- 8-Port OC-3c/STM-1c POS Optical Interface Card -(SFP,LC)(GIC)
            type-GIC-SP4L-G(2974),                 -- 4-port OC-48c/STM-16c POS Optical Interface Card(SFP,LC)(GIC)
            type-GIC-PSP4L-G(2975),                -- 4-port OC-48c/STM-16c(2.5G) POS Optical Interface Card(SFP,LC)(GIC)
            type-S7803-MPU(2976),                  -- Supervisor Engine Board
            type-S7806-MPU(2977),                  -- Supervisor Engine Board
            type-S78-16XF24GF(2978),               -- 24-Port 1000BASE-R Ethernet Optical Interface(SFP,LC)+16-Port 10GBASE-R Ethernet Optical Interface Board(SFP+,LC)
            type-S78-24GF8GT(2979),                -- 8-Port 10/100/1000BASE-T Ethernet Interface Board(RJ45)+24-Port 1000BASE-X Ethernet SFP Optical Interface(SFP,LC)
            type-S78-24GT20GF4XF(2980),            -- 24-Port 10/100/1000BASE-T Ethernet Interface Board(RJ45)+20-Port 1000BASE-X Ethernet SFP Optical Interface(SFP,LC)+4-Port 10GBASE-R Optical Interface Board(SFP+,LC)
            type-S78-24GT8GF(2981),                -- 24-Port 10/100/1000BASE-T Ethernet Interface Board(RJ45)+8-Port 1000BASE-X Ethernet SFP Optical Interface(SFP,LC)
            type-S78-48GF(2982),                   -- 48-Port 1000BASE-X Ethernet Optical Interface Board(SFP,LC)
            type-S78-48GT(2983),                   -- 48-Port 10/100/1000BASE-T Ethernet Interface Board(RJ45)
            type-S78-48XF(2984),                   -- 48-Port 10GBASE-R Ethernet SFP+ Optical Interface Board
            type-CSR05SRP1R3A-G(2985),             -- Management and Route Process Board(1R3A-G)
            type-LSXM3SUPS2-G1(2986),              -- Supervisor Engine Board
            type-LSXM3SUP04S2-G1(2987),            -- Supervisor Engine Board
            type-LSXM3CGQ18SF2-G3(2988),           -- 18-Port 100G Ethernet Optical Interface Module (QSFP28)
            type-LSXM3QGS36SF2-G3(2989),           -- 36-Port 40G Ethernet Optical Interface Module (QSFP+)
            type-LSXM4CGQ36SF2-G3(2990),           -- 36-Port 100GBASE-R Ethernet Optical Interface Board(QSFP28,LC)
            type-LSXM3YGS48SF2-G3(2991),           -- 48-Port 25GBASE-R Ethernet Optical Interface Board(SFP28,LC)
            type-LSXM3TGS48SF2-G3(2992),           -- 48-Port 10GBASE-R Ethernet SFP+ Optical Interface Board(SF)
            type-LSXM3SFS08F2-G3(2993),            -- Switching Fabric Module
            type-LSXM3SFS16F2-G3(2994),            -- Switching Fabric Module
            type-LSXM3SFS04G2-G3(2995),            -- Switching Fabric Module
            type-LSXM3SFS08G2-G3(2996),            -- Switching Fabric Module
            type-LSXM3SFS16G2-G3(2997),            -- Switching Fabric Module
            type-LSXM3SFS08H2-G3(2998),            -- Switching Fabric Module
            type-LSXM3SFS16H2-G3(2999),            -- Switching Fabric Module
            type-CR16000-M1A(3000),                -- Management and Route Process Board(M1A)
            type-NIC-GP24L1A-G(3001),              -- 24-Port 1000BASE-X Ethernet Optical Interface Card A(SFP,LC)(NIC)
            type-NIC-XP20L1A-G(3002),              -- 20-Port 10GBASE-R/W Ethernet Optical Interface Card A(SFP+,LC)(NIC)
            type-NIC-CQ2LA-G(3003),                -- 2-Port 100G Ethernet Optical Interface Card A(QSFP28)(NIC)
            type-CSFC-08E3A(3004),                 -- Fabric Module (Type E)
            type-CSFC-16E3A(3005),                 -- Fabric Module (Type E)
            type-LSWM2XMGT4PM(3006),               -- 4-Port 1G/2.5G/5G/10G BASE-T MACSec Interface Module
            type-LSDM3SUPRA0-ZG1(3007),            -- Supervisor Engine Board
            type-LSXM3SFS04K2(3008),               -- Switch Fabric Board
            type-LSDM3FAB04G0-H-Z(3009),           -- Switch Fabric Board
            type-LSDM3FAB08G0-H-Z(3010),           -- Switch Fabric Board
            type-LSDM3CGS36SF0-H-Z(3011),          -- 36-Port 100GBASE-R Ethernet Optical Interface Board(QSFP28,LC)
            type-LSXM3SFS04G2-H(3012),             -- Switch Fabric Board
            type-LSXM3SFS08G2-H(3013),             -- Switch Fabric Board
            type-LSXM4CGQ36SF2-H(3014),            -- 36-Port 100GBASE-R Ethernet Optical Interface Board(QSFP28,LC)
            type-LSXM3SUP04S2-H(3015),             -- Supervisor Engine Board
            type-LSXM3YGS48SF2-H(3016),            -- 48-Port 25GBASE-R Ethernet Optical Interface Board(SFP28,LC)
            type-GIC-GT10L-G(3017),                -- 10-port 1000BASE-X Ethernet Copper Interface Card(RJ45)(GIC)
            type-CSR05SRP051E3-G3(3018),           -- Management and Route Processing Unit (051E3-G)
            type-DS-3E-2CX-H(3019),                -- 2-Port QSFP28 Interface Module
            type-DS-3E-2YX-H(3020),                -- 2-Port SFP28 Interface Module
            type-DS-3E-8MG-H(3021),                -- 8-Port SmartGE (5/2.5/1G) Interface Module
            type-SFE-A2-Z(3022),                   -- Network Service Processing Unit (A2)
            type-RX-CEPC-CQ8LF-G(3023),            -- 8-port 100G Flexible Ethernet Optical Interface Line Processing Unit(QSFP28,LC)
            type-RX-SFC-08E3(3024),                -- Fabric Module (Type E)

            type-LSXM4CGQ48SG2(3025),              -- 48-Port 100G Ethernet Optical Interface Module(QSFP28)
            type-IM-APA-I(3026),                   -- Service Processing Unit(IM-APA-I)
            type-LSWM1CGQ16M1(3028),               -- 16-Port QSFP28 Interface Module
            type-LSWM1CDHQ4M1(3029),               -- 4-Port 400G QSFP112 Interface Module
            type-LSWM1CCQ16M1(3030),               -- 16-Port 200G QSFP56 Interface Module
            type-LSWM1CDHQ8M1(3031),               -- 8-Port 400G QSFP112 Interface Module
            type-LSXM4CGQ48SG2-H(3032),            -- 48-Port 100G Ethernet Optical Interface Module(QSFP28)
            type-LSXM3CDHQ36RSG2-H(3033),          -- 36-Port 400G Ethernet Optical Interface Module(QSFP112)
            type-LSEM1GP48SD0-G3(3034),            -- 48-Port 1000BASE-X Optical Interface Board(SFP,LC)
            type-LSEM1GT48SD0-G3(3035),            -- 48-Port 10/100/1000BASE-T Electrical Interface Board(RJ45)(SD)
            type-LSCM2TGS16SD0-G3(3036),           -- 16-Port 10G Ethernet Optical Interface Module(SFP+)(SD)
            type-GIC-XP12LF(3037),                 -- 12-port 10GBASE-R/W Ethernet Optical Interface Card Module(SFP+,LC)
            type-GIC-CQ1LF(3038),                  -- 2-port 100G Flexible Ethernet Optical Interface Card(QSFP28,LC)
            type-GIC-MSC-G(3039),                  -- Network Data Encryption Interface Card(GIC-MSC-G)
            type-GIC-SEC-G(3040),                  -- Network Data Encryption Interface Card(GIC-SEC-G)
            type-LSWM2SP2PBU(3041),                -- 2-Port SFP+ Interface Module
            type-AI-96B-NCFK(3042),                -- Switch Fabric Board,Type K
            type-AI-36B48B-NCPK(3043),             -- 36-Port 400GBASE Ethernet Optical Interface Module(KB)
            type-AI-18D48B-NCPK(3044),             -- 18-Port 400GBASE Ethernet Optical Interface Module(KB)
            type-AI-6C-NCCA(3045),                 -- Supervisor Engine Unit
            type-LSCM2CTGS16T24P20SC0-G3(3046),    -- Main Processing Unit with Switching and Routing With 24-Port 10/100/1000BASE-T Ethernet Interface+20-Port 1000BASE-X Ethernet SFP Optical Interface+16-Port 10GBASE-R Ethernet SFP+ Optical Interfaces
            type-LSCM2CTGS16T24P20SC8(3047),       -- Main Processing Unit with Switching and Routing With 24-Port 10/100/1000BASE-T Ethernet Interface+20-Port 1000BASE-X Ethernet SFP Optical Interface+16-Port 10GBASE-R Ethernet SFP+ Optical Interfaces
            type-DS-3E7803M-MPU-24T24F12X(3048),   -- Main Processing Unit with Switching and Routing With 24-Port 10/100/1000BASE-T Ethernet Interface+24-Port 1000BASE-X Ethernet SFP Optical Interface+12-Port 10GBASE-R Ethernet SFP+ Optical Interfaces
            type-ZD-S7803M-MPU-24T24F12X(3049),    -- Main Processing Unit with Switching and Routing With 24-Port 10/100/1000BASE-T Ethernet Interface+24-Port 1000BASE-X Ethernet SFP Optical Interface+12-Port 10GBASE-R Ethernet SFP+ Optical Interfaces
            type-DS-3E12508X-MPU-G(3050),          -- Supervisor Engine Board
            type-DS-3E12512X-MPU-G(3051),          -- Supervisor Engine Board
            type-DS-3E12500X-24X-SD(3052),         -- 24-Port 10GBASE-R Ethernet SFP+ Optical Interface Board(SD)
            type-DS-3E7800-24T4X-SD(3053),         -- 24-Port 10/100/1000BASE-T Ethernet Interface Board(RJ45)+4-Port 10GBASE-R Optical Interface Board(SFP+,LC)(SD)
            type-DS-3E7800-40F8X-SD(3054),         -- 40-Port 1000BASE Ethernet Optical Interface(SFP)+8-Port 10G Ethernet Optical Interface Module(SFP+)(SD)
            type-DS-3E7800-16Y8X-SF(3055),         -- 16-Port 25G Ethernet Optical Interface(SFP28)+8-Port 10G Ethernet Optical Interface Module(SFP+)(SF)
            type-DS-3E7800-8Q4C-SE(3056),          -- 8-Port 40GBASE-R QSFP+ + 4-Port 100GBASE-R QSFP28 Optical Interface Board(SE)
            type-LSXM3SUP04RS2-G1(3057),           -- Supervisor Engine Board
            type-LSXM3SFS04RG2-G3(3058),           -- Switching Fabric Module
            type-LSXM3SFS04RK2(3059),              -- Switching Fabric Module
            type-DS-8SFPPM-A2TB(3060),             -- 8-Port 10G SFP Plus Interface Module
            type-LSEM1SDNB0(3061),                 -- SDN Automation Module With 4-Port 10GBASE Ethernet SFP+ Optical Interfaces
            type-LSEM1FWESD0(3062),                -- 4-Port 10GBASE Ethernet SFP+ Optical Interfaces
            type-CSFC-08T-G3(3063),                -- Fabric Module(T Type-G)
            type-IM-APA-I-IM-SP-B(3064),           -- Service Processing Unit + Universal Line Processing Interface Card(IM-APA-I-IM-SP-B)
            type-LSCM3PG24TSSD0-G3(3065),          -- 24-Port XGS-PON OLT Optical Interface(SFP+,SC)+4-Port 10GE Optical Interface Board(SFP+,LC)
            type-LSCM2CGT24TSSC9(3066),            -- Supervisor Engine Board With 24-Port 10/100/1000BASE-T Ethernet Interface+4-Port 10GBASE-R Ethernet SFP+ Optical Interfaces
            type-LSCM2CGP24TSSC9(3067),            -- Supervisor Engine Board With 24-Port 1000BASE-X Ethernet SFP Optical Interface+4-Port 10GBASE-R Ethernet SFP+ Optical Interfaces
            type-LSCM2MPUS06AS9(3068),             -- Supervisor Engine Board
            type-LSCM2GT48SC9(3069),               -- 48-Port 10/100/1000BASE-T Ethernet Interface Board(RJ45)(SC)
            type-LSCM2GP48SC9(3070),               -- 48-Port 1000BASE-X Ethernet Optical Interface Board(SFP,LC)
            type-LSCM2GT24GPSC9(3071),             -- 24-Port 10/100/1000BASE-T Ethernet Interface Board(RJ45)+8-Port 1000BASE-X Ethernet SFP Optical Interface(SFP,LC)(SC)
            type-LSCM2GP24GTSC9(3072),             -- 8-Port 10/100/1000BASE-T Ethernet Interface Board(RJ45)+24-Port 1000BASE-X Ethernet SFP Optical Interface(SFP,LC)(SC)
            type-LSCM3QGS8CSSC9(3073),             -- 8-Port 40GBASE-R QSFP+ + 4-Port 100GBASE-R QSFP28 Optical Interface Board(SC)
            type-LSCM2TGS24SC9(3074),              -- 24-Port 10GBASE-R Ethernet SFP+ Optical Interface Board(SC)
            type-WD-M1ESP8O(3075),                 -- 8-Port SFP+ Interface Module
            type-WD-4PSPPI(3076),                  -- 4-Port SFP+ Interface Module
            type-CSFC-05E-G(3078),                 -- Fabric Module (Type E-G)
            type-CSFMC-05E-G(3079),                -- Fabric Management Module (Type E-G)
            type-CSR05SRP031E3-G(3080),            -- Management and Route Processing Module (031E3-G)
            type-MIC-MSC-M(3081),                  -- Network Data Encryption Interface Card(GIC-MSC-M)
            type-LSXM1SFN08JR1(3082),              -- Fabric Module
            type-LSXM1CEP36NFR1(3083),             -- 36-Port 800GBASE Ethernet Optical Interface Module(OSFP800)(NF)
            type-DS-2SFPPM-A9UF(3084),             -- 2-Port SFP+ Interface Module
            type-LSWM1CCQ8M1(3085),                -- 8-Port 200G QSFP56 Interface Module
            type-LSWM1CDQ4M1(3086),                -- 4-Port 400G QSFP-DD Interface Module
            type-LSWM1CEQ4M1(3087),                -- 4-Port 800G QSFP-DD Interface Module
            type-LSWM1CEQ2M1(3088),                -- 2-Port 800G QSFP-DD Interface Module
            type-LSWM1LG16C1(3089),                -- 16-Port 25G SFP56 Interface Module
            type-LSXM3CDHQ42RXG2(3090),            -- 42-Port 400G Ethernet Optical Interface Module(QSFP112)
            type-LSXM3CCQ48RXG2-G3(3091),          -- 48-Port 200G Ethernet Optical Interface Module(QSFP56)
            type-LSXM3SFX08M2-G3(3092),            -- Switch Fabric Board
            type-LSXM3SFX04RM2(3093),              -- Switch Fabric Board
            type-LSXM3SFX16M2(3094),               -- Switch Fabric Board
            type-LSCM3MPUS06C0-G3(3095),           -- Supervisor Engine Board
            type-LSCM3SRP2C4Y06B0-G3(3096),        -- Main Processing Unit with Switching and Routing With 4-Port 25G Ethernet Optical Interface(SFP28)+2-Port 100G Ethernet Optical Interfaces(QSFP28)
            type-LSCM4MPUS10B0-G3(3097),           -- Supervisor Engine Board
            type-LSCM3TGS36CSFD0-G3(3098),         -- 36-Port 10G Ethernet Optical Interface(SFP+)+4-Port 100G Ethernet Optical Interface Module(QSFP28)
            type-CSR05SRP031E3-G3(3099),           -- Management and Route Processing Module (031E3-G3)
            type-CSFC-16T3(3100),                  -- Fabric Module (Type E)
            type-CSFC-08T3(3101),                  -- Fabric Module (Type E)
            type-CSPEX-2612X3-E(3102),             -- Service Processing Unit(2612X3-E)
            type-NIC-XP20L1E-G(3103),              -- 20-Port 10GBASE-R/W Ethernet Optical Interface Card A(SFP+,LC)(NIC)
            type-NIC-GP24L1E-G(3104),              -- 24-Port 1000BASE-X Ethernet Optical Interface Card A(SFP,LC)(NIC)
            type-NIC-CQ2LE-G(3105),                -- 2-Port 100G Ethernet Optical Interface Card A(QSFP28)(NIC)
            type-IM-MSEX-B3(3106),                 -- Service Processing Unit(IM-MSEX-B3)
            type-IM-MSEX-B3-IM-SP-B3(3107),        -- Service Processing Unit + Universal Expansion Service Processing Module(IM-MSEX-B3-IM-SP-B3)
            type-IM-APA-I3-IM-SP-B3(3108),         -- Application-Aware Line Processing Unit + Universal Expansion Service Processing Module(IM-APA-I3-IM-SP-B3)
            type-IM-APA-I3(3109),                  -- Application-Aware Line Processing Unit(IM-APA-I3)
            type-DS-3E7800-SG100-T30(3110),        -- Next Generation Firewall
            type-LSCM2MPUS06AS0-G3(3111),          -- Supervisor Engine Board
            type-LSCM3SUP03B0-ZE(3112),            -- Supervisor Engine Board
            type-LSCM2GT48SD0-ZE(3113),            -- 48-Port 10/100/1000BASE-T Ethernet Interface Board(RJ45)(SD)
            type-LSCM3TGS48SF0-ZE(3114),           -- 48-Port 10G Ethernet Optical Interface Module(SFP+)(SF)
            type-LSCM3CGS8QS8SF0-ZE(3115),         -- 8-Port 40G Ethernet Optical Interface(QSFP+)+8-Port 100G Ethernet Optical Interface Module(QSFP28)(SF)
            type-LSEM3SUPA0-ZE(3116),              -- Supervisor Engine Board
            type-LSEM1SF06D0-ZE(3117),             -- Switch Fabric Board
            type-LSEM3CGQ16SF0-ZE(3118),           -- 16-Port 100G Ethernet Optical Interface Module(QSFP28)
            type-LSEM3TGS48QSSF0-ZE(3119),         -- 48-Port 10G Ethernet Optical Interface(SFP+)+4-Port 40G Ethernet Optical Interface Module (QSFP+)(SF)
            type-LSEM1GP40TS12SD0-ZE(3120),        -- 40-Port 1000BASE Ethernet Optical Interface Module (SFP)+12-Port 10G Ethernet Optical Interface (SFP+)(SD)
            type-LSEM1GT48TSSD0-ZE(3121),          -- 48-Port 10/100/1000BASE-T Electrical Interface(RJ45)+4-Port 10GBASE-R Ethernet Optical Interface Board(SFP+,LC)(SD)
            type-LSEM3CGQ36SF0-ZE(3122),           -- 36-Port 100G Ethernet Optical Interface Module(QSFP28)
            type-NW-CW-Mod-2C-5550HI(3123),        -- 2 Ports 100G QSFP28 Interface Module
            type-NW-CW-Mod-8Y-5550HI(3124),        -- 8 Ports 25G SFP28 Interface Module
            type-NW-CW-Mod-Msec-8P-5XX0HI(3125),   -- 8-Port 10G SFP Plus with MACSec Interface Module
            type-LSWM1CGQ16M1-Z(3126),             -- 16-Port QSFP28 Interface Module
            type-LSWM1CDHQ4M1-Z(3127),             -- 4-Port 400G QSFP112 Interface Module
            type-S7803M-MPU-12XF16GF(3128),        -- Supervisor Engine Board With 16-Port 1000BASE-X Ethernet SFP Optical Interface+12-Port 10GBASE-R Ethernet SFP+ Optical Interfaces
            type-S7803M-MPU-12XF16GT(3129),        -- Supervisor Engine Board With 16-Port 10/100/1000BASE-T Ethernet Interface+12-Port 10GBASE-R Ethernet SFP+ Optical Interfaces
            type-S78-8QF4CF(3130),                 -- 8-Port 40GBASE-R QSFP+ + 4-Port 100GBASE-R QSFP28 Optical Interface Board
            type-S78-16YF8XF(3131),                -- 16-Port 25G Ethernet Optical Interface(SFP28)+8-Port 10G Ethernet Optical Interface Module(SFP+)
            type-LSEM1SF08B0-G3(3132),             -- Switch Fabric Board
            type-S7810-MPU(3133),                  -- Supervisor Engine Board
            type-LSWM1SUPD1(3134),                 -- Supervisor Engine Module,Domestic&Overseas Version
            type-LSWM1SUPX1(3135),                 -- Supervisor Engine Module,Domestic&Overseas Version
            type-LSWM2SUPD1(3136),                 -- Supervisor Engine Module,Domestic&Overseas Version
            type-LSWM3SUPD1(3137),                 -- Supervisor Engine Module,Domestic&Overseas Version
            type-LSWM3SUPX1(3138),                 -- Supervisor Engine Module,Domestic&Overseas Version
            type-CSPEX-3612XA-G(3139),             -- Service Processing Unit(3612XA)
            type-NIC-CQ2L-G(3140),                 -- 2-Port 100G Ethernet Optical Interface Card (QSFP28)(NIC)
            type-LSWM5SP2PB(3141),                 -- 2-Port SFP+ Interface Module
            type-GIC-CLP4L-G(3142),                -- 4-Port OC-3/STM-1 Channelized POS Optical Interface Board (SFP,LC)(GIC),Monolithic
            type-LSDM3SUPA0-ZG1(3143),             -- Supervisor Engine Board
            type-LSDM3FAB16G0-ZG3(3144),           -- Switching Fabric Module
            type-LSDM4CGS36SF0-ZG3(3145),          -- 36-Port 100GBASE-R Ethernet Optical Interface Board(QSFP28,LC)
            type-LSDM3CGS18SF0-ZG3(3146),          -- 18-Port 100G Ethernet Optical Interface Module (QSFP28)
            type-LSDM3YGS48SF0-ZG3(3147),          -- 48-Port 25GBASE-R Ethernet Optical Interface Board(SFP28,LC)
            type-LSEM1SUPB0-ZG1(3148),             -- Supervisor Engine Board
            type-LSEM1SF12B0-ZG3(3149),            -- Switching Fabric Module
            type-LSEM1TGS48QSSF0-ZG3(3150),        -- 48-Port 10G Ethernet Optical Interface(SFP+)+4-Port 40G Ethernet Optical Interface Module (QSFP+)(SF)
            type-LSEM1CGQ16SF0-ZG3(3151),          -- 16-Port 100G Ethernet Optical Interface Module(QSFP28)
            type-DS-3E6002-24T(3152),              -- 24-Port 10/100/1000Base-T Interface Module
            type-DS-3E6002-8T16F(3153),            -- 8-Port 10/100/1000Base-T+16-Port 1G/2.5G SFP Interface Module
            type-DS-3E6002-16T8F(3154),            -- 16-Port 10/100/1000Base-T+8-Port 1G/2.5G SFP Interface Module
            type-DS-3E6002-24F(3155),              -- 24-Port 1G/2.5G SFP Interface Module
            type-LSWM1CDHQ8M1-Z(3156),             -- 8-Port 400G Ethernet Optical Interface Module
            type-LSWM1CCQ16M1-Z(3157),             -- 16-Port 200G Ethernet Optical Interface Module
            type-LSWM1TGT12CCQ2M1(3158),           -- 12-Port 10G BASE-T Ethernet Copper Interface(RJ45) + 2-Port 200G Ethernet Optical Interface Module
            type-LSWM1LG8CCQ4M1(3159),             -- 8-Port 50G Ethernet Optical Interface(SFP56) + 4-Port 200G Ethernet Optical Interface Module
            type-CSFC-10T-G3(3160),                -- Fabric Module (Type T-G3),Domestic&Overseas Version
            type-LSEM1SF12PB0(3161),               -- Switching Fabric Module
            type-RX-SPE400-G(3162),                -- Service Processing Unit(SPE400-G)
            type-V10506X-CU-EB(3163),              -- Supervisor Engine Board
            type-V10506X-SFU-EB(3164),             -- Switch Fabric Board
            type-V10510X-CU-EA(3165),              -- Supervisor Engine Board
            type-V10510X-SFU-EA(3166),             -- Switch Fabric Board
            type-V10500X-IU-25GE24-100GE4(3167),   -- 24-Port 25G Ethernet Optical Interface(SFP28,LC)+4-Port 100G Ethernet Optical Interface Module(QSFP28)
            type-V10500X-IU-10GE48(3168),          -- 48-Port 10G Ethernet Optical Interface Module(SFP+,LC)
            type-V10500X-IU-10GE24(3169),          -- 24-Port 10GBASE-R Ethernet Optical Interface Board(SFP+,LC)
            type-V10500X-IU-10GT24(3170),          -- 24-Port 10GBASE-T Ethernet Copper Interface Module(RJ45)
            type-V10500X-IU-GE48(3171),            -- 48-Port 1000BASE-X Optical Interface Board(SFP,LC)
            type-V10500X-IU-GT48(3172),            -- 48-Port 10/100/1000BASE-T Electrical Interface Board(RJ45)
            type-V10500X-IU-100GE8-40GE8(3173),    -- 8-Port 100G Ethernet Optical Interface Module(QSFP28) +8-port 40G/4-Port 100G Ethernet Optical Interface Module(QSFP28)
            type-V10500X-IU-10GE24-100GE4(3174),   -- 24-Port 10G Ethernet Optical Interface Module(SFP+,LC)+4-Port 100G Ethernet Optical Interface Module(QSFP28)
            type-V10500X-IU-GE40-10GE8(3175),      -- 40-Port 1000BASE-X Optical Interface Board(SFP,LC)+8-Port 10G Ethernet Optical Interface Module(SFP+,LC)
            type-CSPEX-3314X-G(3176),              -- Network Processing Unit(3314X-G)
            type-LSWM124T(3177),                   -- 24-Port 10/100/1000Base-T Interface Module
            type-LSWM18T16SFP(3178),               -- 8-Port 10/100/1000Base-T+16-Port 1G/2.5G SFP Interface Module
            type-LSWM224T(3179),                   -- 24-Port 10/100/1000Base-T Interface Module
            type-LSWM28T16SFP(3180),               -- 8-Port 10/100/1000Base-T+16-Port 1G/2.5G SFP Interface Module
            type-LSWM216T8SFP(3181),               -- 16-Port 10/100/1000Base-T+8-Port 1G/2.5G SFP Interface Module
            type-LSWM224SFP(3182),                 -- 24-Port 1G/2.5G SFP Interface Module
            type-LSWM116T8SFP(3183),               -- 16-Port 10/100/1000Base-T+8-Port 1G/2.5G SFP Interface Module
            type-LSWM124SFP(3184),                 -- 24-Port 1G/2.5G SFP Interface Module
            type-LSXM3CDHQ40RXG2-G3(3185),         -- 40-Port 400G Ethernet Optical Interface Module(QSFP112)
            type-S9867-128DH(3186)                 -- Management and Route Process Board(128DH)
            -- 2000 to 2399 reserved for advanced switches part III
            --
}

hh3cLswSystemPara OBJECT IDENTIFIER ::= {  hh3cLswDeviceAdmin 1  }

-- ==================================================================

hh3cLswSysIpAddr OBJECT-TYPE
SYNTAX IpAddress
MAX-ACCESS read-only
STATUS current
DESCRIPTION
"System IP address, which is the primary IP address of the VLAN
interface that has smallest VLAN ID and is configured IP address."
::= { hh3cLswSystemPara 1 }

hh3cLswSysIpMask OBJECT-TYPE
SYNTAX IpAddress
MAX-ACCESS read-only
STATUS current
DESCRIPTION
"Mask of the system IP address."
::= { hh3cLswSystemPara 2 }

hh3cLswSysCpuRatio OBJECT-TYPE
SYNTAX Integer32 (0..100)
MAX-ACCESS read-only
STATUS current
DESCRIPTION
"CPU usage of the system in accuracy of 1%, and the range of value is
1 to 100."
::= { hh3cLswSystemPara 3 }

hh3cLswSysVersion OBJECT-TYPE
SYNTAX DisplayString (SIZE(1..64))
MAX-ACCESS read-only
STATUS current
DESCRIPTION
"Information of the system version."
::= { hh3cLswSystemPara 4 }

hh3cLswSysTime OBJECT-TYPE
SYNTAX DateAndTime
MAX-ACCESS read-write
STATUS current
DESCRIPTION
"System time."
::= { hh3cLswSystemPara 5 }

hh3cLswSysUNMCastDropEnable OBJECT-TYPE
SYNTAX INTEGER
{
disable (0),
enable  (1)
}
MAX-ACCESS read-write
STATUS current
DESCRIPTION
"Enable or disable discarding of unknown multicast packet."
::= { hh3cLswSystemPara 6 }

hh3cLswSysManagementVlan OBJECT-TYPE
SYNTAX Integer32 (1..4094)
MAX-ACCESS read-write
STATUS current
DESCRIPTION
"System management VLAN."
::= { hh3cLswSystemPara 7 }

hh3cLswSysVlanRange OBJECT-TYPE
SYNTAX DisplayString (SIZE(1..10))
MAX-ACCESS read-write
STATUS current
DESCRIPTION
"System VLAN range, if set VLAN range, must bind mangement IP/Mask."
::= { hh3cLswSystemPara 8 }

hh3cLswSysManagementIpAddr OBJECT-TYPE
SYNTAX IpAddress
MAX-ACCESS read-write
STATUS current
DESCRIPTION
"System IP address."
::= { hh3cLswSystemPara 9 }

hh3cLswSysManagementIpMask OBJECT-TYPE
SYNTAX IpAddress
MAX-ACCESS read-write
STATUS current
DESCRIPTION
"Mask of the system IP address."
::= { hh3cLswSystemPara 10 }

hh3cMacAddressCountPort OBJECT-TYPE
SYNTAX Integer32
MAX-ACCESS read-only
STATUS current
DESCRIPTION
"Supportted MAC address number on port."
::= { hh3cLswSystemPara 11 }

hh3cMacAddressCountMachine OBJECT-TYPE
SYNTAX Integer32
MAX-ACCESS read-only
STATUS current
DESCRIPTION
"Supportted MAC address number on machine."
::= { hh3cLswSystemPara 12 }

hh3cLswSysPhyMemory OBJECT-TYPE
SYNTAX Unsigned32
UNITS "byte"
MAX-ACCESS read-only
STATUS current
DESCRIPTION
"The memory of physical.
For the distributed device, it represents the memory size on the master
slot.

If the amount of physical memory exceeds 4,294,967,295 bytes,
the value remains 4,294,967,295 bytes."
::= { hh3cLswSystemPara 13 }

hh3cLswSysMemory OBJECT-TYPE
SYNTAX Unsigned32
UNITS "byte"
MAX-ACCESS read-only
STATUS current
DESCRIPTION
"The memory of system.
Note that the system memory means the memory can be used by the software
platform.

For the distributed device, it represents the memory size on the master
slot.

If the amount of system memory exceeds 4,294,967,295 bytes,
the value remains 4,294,967,295 bytes."
::= { hh3cLswSystemPara 14 }

hh3cLswSysMemoryUsed OBJECT-TYPE
SYNTAX Unsigned32
UNITS "byte"
MAX-ACCESS read-only
STATUS current
DESCRIPTION
"The system memory in use.
Note that the system memory means the memory can be used by the software
platform.

For the distributed device, it represents the memory size on the master
slot.

If the amount of used memory exceeds 4,294,967,295 bytes,
the value remains 4,294,967,295 bytes."
::= { hh3cLswSystemPara 15 }

hh3cLswSysMemoryRatio OBJECT-TYPE
SYNTAX Unsigned32 (0..100)
MAX-ACCESS read-only
STATUS current
DESCRIPTION
"The percentage of system memory in use.
Note that the system memory means the memory can be used by the software
platform.

hh3cLswSysMemoryUsed
hh3cLswSysMemoryRatio = --------------------
hh3cLswSysMemory

For the distributed device, it represents the memory used ratio on the
master slot."
::= { hh3cLswSystemPara 16 }

hh3cLswSysTemperature OBJECT-TYPE
SYNTAX Integer32
MAX-ACCESS read-only
STATUS current
DESCRIPTION
"The temperature of system.

For the distributed device, it represents the temperature on the
master slot."
::= { hh3cLswSystemPara 17 }

hh3cLswSysPhyMemRev OBJECT-TYPE
SYNTAX CounterBasedGauge64
UNITS "bytes"
MAX-ACCESS read-only
STATUS current
DESCRIPTION
"Size of the physical memory space.

This node is used to replace hh3cLswSysPhyMemory.

For a distributed device, it indicates the size of the memory space
on the active MPU."
::= { hh3cLswSystemPara 18 }

hh3cLswSysMemRev OBJECT-TYPE
SYNTAX CounterBasedGauge64
UNITS "bytes"
MAX-ACCESS read-only
STATUS current
DESCRIPTION
"Size of the memory space for the software platform.

This node is used to replace hh3cLswSysMemory.

For a distributed device, it indicates the size of the memory space
on the active MPU."
::= { hh3cLswSystemPara 19 }

hh3cLswSysMemUsedRev OBJECT-TYPE
SYNTAX CounterBasedGauge64
UNITS "bytes"
MAX-ACCESS read-only
STATUS current
DESCRIPTION
"Size of the memory space used by the software system.

This node is used to replace hh3cLswSysMemoryUsed.

For a distributed device, it indicates the size of the memory space
on the active MPU"
::= { hh3cLswSystemPara 20 }

hh3cLswSysSerialNumber OBJECT-TYPE
SYNTAX     SnmpAdminString (SIZE(0..32))
MAX-ACCESS     read-only
STATUS current
DESCRIPTION
"Serial number of the device."
::= { hh3cLswSystemPara 21 }

hh3cLswSysTotalPower   OBJECT-TYPE
SYNTAX     Unsigned32
MAX-ACCESS     read-only
STATUS current
DESCRIPTION
"Total system power, in W.

In IRF mode, it is the total system power of all member devices."
::= { hh3cLswSystemPara 22 }

hh3cSysProductName   OBJECT-TYPE
SYNTAX DisplayString (SIZE(1..64))
MAX-ACCESS read-only
STATUS current
DESCRIPTION
"Information of the product name."
::= { hh3cLswSystemPara 23 }

hh3cSysProductVersion   OBJECT-TYPE
SYNTAX DisplayString (SIZE(1..64))
MAX-ACCESS read-only
STATUS current
DESCRIPTION
"Information of the product version."
::= { hh3cLswSystemPara 24 }

hh3cSysPatchPlatVersion   OBJECT-TYPE
SYNTAX DisplayString (SIZE(1..2048))
MAX-ACCESS read-only
STATUS current
DESCRIPTION
"Information of the system patch version."
::= { hh3cLswSystemPara 25 }

hh3cComponentLicense   OBJECT-TYPE
    SYNTAX OCTET STRING (SIZE(0..2048))
    MAX-ACCESS read-write
    STATUS current
    DESCRIPTION
    "License Number."
    ::= { hh3cLswSystemPara 26 }
-- ==================================================================
--
-- slot and port management group
--
-- ==================================================================

hh3cLswSlotConf OBJECT IDENTIFIER ::= { hh3cLswDeviceAdmin 4 }

-- ==================================================================
--
-- Frame information table
--
-- ==================================================================

hh3cLswFrameTable    OBJECT-TYPE
SYNTAX     SEQUENCE OF Hh3cLswFrameEntry
MAX-ACCESS     not-accessible
STATUS     current
DESCRIPTION
"Frame information table."
::= {hh3cLswSlotConf 2}

hh3cLswFrameEntry    OBJECT-TYPE
SYNTAX     Hh3cLswFrameEntry
MAX-ACCESS     not-accessible
STATUS     current
DESCRIPTION
"Frame description table entry."
INDEX { hh3cLswFrameIndex }
::= {hh3cLswFrameTable 1}

Hh3cLswFrameEntry ::= SEQUENCE
{
hh3cLswFrameIndex        Integer32,
hh3cLswFrameType         Integer32,
hh3cLswFrameDesc         DisplayString,
hh3cLswSlotNumber        Integer32,
hh3cLswFrameAdminStatus  INTEGER,
hh3cLswFrameSerialNumber SnmpAdminString,
hh3cLswFrameDisplayId    Integer32,
hh3cLswFrameName         DisplayString,
hh3cLswFrameClassType    INTEGER,
hh3cLswFrameTotalPower   Unsigned32,
hh3cLswFrameNominalPower Unsigned32,
hh3cLswFramePowerRedundancyType  DisplayString,
hh3cFrameCapacityPower   Unsigned32,
hh3cFrameResidualPower   Unsigned32,
hh3cFrameNormalPowerNum  Unsigned32
}

hh3cLswFrameIndex    OBJECT-TYPE
SYNTAX     Integer32
MAX-ACCESS     read-only
STATUS     current
DESCRIPTION
"The unique index of frame."
::= {hh3cLswFrameEntry 1}

hh3cLswFrameType    OBJECT-TYPE
SYNTAX     Integer32
MAX-ACCESS     read-only
STATUS     current
DESCRIPTION
"Frame type."
::= {hh3cLswFrameEntry 2}

hh3cLswFrameDesc    OBJECT-TYPE
SYNTAX       DisplayString (SIZE(0..64))
MAX-ACCESS     read-write
STATUS     current
DESCRIPTION
"Frame description."
::= {hh3cLswFrameEntry 3}

hh3cLswSlotNumber    OBJECT-TYPE
SYNTAX     Integer32
MAX-ACCESS     read-only
STATUS     current
DESCRIPTION
"Number of slots of the current frame."
::= {hh3cLswFrameEntry 4}

hh3cLswFrameAdminStatus    OBJECT-TYPE
SYNTAX     INTEGER
{
normal (1),
fault  (2),
other  (3)
}
MAX-ACCESS     read-only
STATUS     current
DESCRIPTION
"The status of frame."
::= {hh3cLswFrameEntry 5}

hh3cLswFrameSerialNumber    OBJECT-TYPE
SYNTAX     SnmpAdminString (SIZE(0..32))
MAX-ACCESS     read-only
STATUS     current
DESCRIPTION
"Serial number of the current frame."
::= {hh3cLswFrameEntry 6}

hh3cLswFrameDisplayId   OBJECT-TYPE
SYNTAX     Integer32
MAX-ACCESS     read-only
STATUS     current
DESCRIPTION
"Frame ID.  LCC and FCC ID is separate in the multi-chassis
cluster system."
::= {hh3cLswFrameEntry 7}

hh3cLswFrameName   OBJECT-TYPE
SYNTAX       DisplayString (SIZE(0..64))
MAX-ACCESS     read-only
STATUS     current
DESCRIPTION
"Frame name description."
::= {hh3cLswFrameEntry 8}

hh3cLswFrameClassType    OBJECT-TYPE
SYNTAX     INTEGER
{
none (1),
lcc  (2),
fcc  (3)
}
MAX-ACCESS     read-only
STATUS     current
DESCRIPTION
"The multi-chassis cluster system is made up by LCC
and FCC, this object indicate the chassis type.  Other system will
return none."
::= {hh3cLswFrameEntry 9}

hh3cLswFrameTotalPower   OBJECT-TYPE
SYNTAX       Unsigned32
MAX-ACCESS     read-only
STATUS     current
DESCRIPTION
"Total chassis power, in W."
::= {hh3cLswFrameEntry 10}

hh3cLswFrameNominalPower   OBJECT-TYPE
SYNTAX       Unsigned32
MAX-ACCESS     read-only
STATUS     current
DESCRIPTION
"Nominal chassis power, in W."
::= {hh3cLswFrameEntry 11}

hh3cLswFramePowerRedundancyType   OBJECT-TYPE
SYNTAX       DisplayString (SIZE(0..64))
MAX-ACCESS     read-only
STATUS     current
DESCRIPTION
"Redundancy Types of power."
::= {hh3cLswFrameEntry 12}
hh3cFrameCapacityPower    OBJECT-TYPE
SYNTAX       Unsigned32
UNITS      "W"
MAX-ACCESS     read-only
STATUS     current
DESCRIPTION
"Total residual power capacity."
::= {hh3cLswFrameEntry 13}
hh3cFrameResidualPower     OBJECT-TYPE
SYNTAX       Unsigned32
UNITS      "W"
MAX-ACCESS     read-only
STATUS     current
DESCRIPTION
"Total residual power."
::= {hh3cLswFrameEntry 14}
hh3cFrameNormalPowerNum      OBJECT-TYPE
SYNTAX       Unsigned32
MAX-ACCESS     read-only
STATUS     current
DESCRIPTION
"Number of power modules.
0 indicates that it is not a distributed device."
::= {hh3cLswFrameEntry 15}
-- ==================================================================
--
-- slot information table
--
-- ==================================================================

hh3cLswSlotTable    OBJECT-TYPE
SYNTAX     SEQUENCE OF Hh3cLswSlotEntry
MAX-ACCESS     not-accessible
STATUS     current
DESCRIPTION
"Slot description table."
::= {hh3cLswSlotConf 3}

hh3cLswSlotEntry    OBJECT-TYPE
SYNTAX     Hh3cLswSlotEntry
MAX-ACCESS     not-accessible
STATUS     current
DESCRIPTION
"Slot description table entry."
INDEX { hh3cLswFrameIndex, hh3cLswSlotIndex }
::= {hh3cLswSlotTable 1}

Hh3cLswSlotEntry ::= SEQUENCE
{
hh3cLswSlotIndex                Integer32,
hh3cLswSlotType                 Hh3cLswTypeOfSlot,
hh3cLswSlotDesc                 DisplayString,
hh3cLswSlotCpuRatio             Integer32,
hh3cLswSlotPcbVersion           DisplayString,
hh3cLswSlotSoftwareVersion      DisplayString,
hh3cLswSubslotNumber            Integer32,
hh3cLswSlotAdminStatus          INTEGER,
hh3cLswSlotOperStatus           INTEGER,
hh3cLswSlotPhyMemory            Unsigned32,
hh3cLswSlotMemory               Unsigned32,
hh3cLswSlotMemoryUsed           Unsigned32,
hh3cLswSlotMemoryRatio          Unsigned32,
hh3cLswSlotTemperature          Integer32,
hh3cLswSlotPktBufFree           Integer32,
hh3cLswSlotPktBufInit           Integer32,
hh3cLswSlotPktBufMin            Integer32,
hh3cLswSlotPktBufMiss           Counter64,
hh3cLswSlotRunTime              DisplayString,
hh3cLswSlotPhyMemRev            CounterBasedGauge64,
hh3cLswSlotMemRev               CounterBasedGauge64,
hh3cLswSlotMemUsedRev           CounterBasedGauge64,
hh3cLswSlotModelDesc            DisplayString,
hh3cLswSlotPktBufThreshold      Integer32,
hh3cLswSlotSerialNumber         SnmpAdminString,
hh3cLswSlotPower                Integer32,
hh3cSlotCurrentVoltage          Integer32,
hh3cSlotCurrent                 Integer32,
hh3cSlotTemperatureThreshold    Integer32,
hh3cSlotNominalPower            Unsigned32,
hh3cSlotNormalPowerNum          Unsigned32,
hh3cSlotPatchVersion            DisplayString
}

hh3cLswSlotIndex    OBJECT-TYPE
SYNTAX     Integer32
MAX-ACCESS     read-only
STATUS     current
DESCRIPTION
"Slot index.  When the slot is empty, listed as vacant slot."
::= {hh3cLswSlotEntry 1}

hh3cLswSlotType    OBJECT-TYPE
SYNTAX     Hh3cLswTypeOfSlot
MAX-ACCESS     read-only
STATUS     current
DESCRIPTION
"Slot type.  BOM number is recommended."
::= {hh3cLswSlotEntry 2}

hh3cLswSlotDesc    OBJECT-TYPE
SYNTAX     DisplayString(SIZE(0..64))
MAX-ACCESS     read-write
STATUS     current
DESCRIPTION
"Slot description."
::= {hh3cLswSlotEntry 3}

hh3cLswSlotCpuRatio     OBJECT-TYPE
SYNTAX         Integer32
MAX-ACCESS     read-only
STATUS         current
DESCRIPTION
"CPU usage of the slot in accuracy of 1%, and the range of value is 1 to
100."
::= {hh3cLswSlotEntry 4}

hh3cLswSlotPcbVersion    OBJECT-TYPE
SYNTAX       DisplayString (SIZE(0..64))
MAX-ACCESS      read-only
STATUS          current
DESCRIPTION
"Hardware version of the board."
::= {hh3cLswSlotEntry 5}

hh3cLswSlotSoftwareVersion    OBJECT-TYPE
SYNTAX               DisplayString (SIZE(0..64))
MAX-ACCESS           read-only
STATUS               current
DESCRIPTION
"Software version of the board."
::= {hh3cLswSlotEntry 6}

hh3cLswSubslotNumber    OBJECT-TYPE
SYNTAX         Integer32
MAX-ACCESS     read-only
STATUS     current
DESCRIPTION
"Number of the cards of the board."
::= {hh3cLswSlotEntry 7}

hh3cLswSlotAdminStatus    OBJECT-TYPE
SYNTAX           INTEGER
{
not-install (1),
normal      (2),
fault       (3),
forbidden   (4)
}
MAX-ACCESS       read-only
STATUS           current
DESCRIPTION
"Slot status."
::= {hh3cLswSlotEntry 8}

hh3cLswSlotOperStatus    OBJECT-TYPE
SYNTAX          INTEGER
{
disable (1),
enable  (2),
reset   (3),
test    (4)
}
MAX-ACCESS      read-write
STATUS          current
DESCRIPTION
"Slot operation status."
::= {hh3cLswSlotEntry 9}

hh3cLswSlotPhyMemory    OBJECT-TYPE
SYNTAX Unsigned32
UNITS "byte"
MAX-ACCESS read-only
STATUS current
DESCRIPTION
"The memory of physical on the board.

If the amount of physical memory exceeds 4,294,967,295 bytes,
the value remains 4,294,967,295 bytes."
::= {hh3cLswSlotEntry 10}

hh3cLswSlotMemory    OBJECT-TYPE
SYNTAX Unsigned32
UNITS "byte"
MAX-ACCESS read-only
STATUS current
DESCRIPTION
"The memory of system on the board.

Note that the system memory means the memory can be used by
the software platform.

If the amount of system memory exceeds 4,294,967,295 bytes,
the value remains 4,294,967,295 bytes."
::= {hh3cLswSlotEntry 11}

hh3cLswSlotMemoryUsed    OBJECT-TYPE
SYNTAX Unsigned32
UNITS "byte"
MAX-ACCESS read-only
STATUS current
DESCRIPTION
"The system memory in use on the board.

Note that the system memory means the memory can be used by
the software platform.

If the amount of used memory exceeds 4,294,967,295 bytes,
the value remains 4,294,967,295 bytes."
::= {hh3cLswSlotEntry 12}

hh3cLswSlotMemoryRatio    OBJECT-TYPE
SYNTAX Unsigned32 (0..100)
MAX-ACCESS read-only
STATUS current
DESCRIPTION
"The percentage of system memory in use on the board.

Note that the system memory means the memory can be used by
the software platform."
::= {hh3cLswSlotEntry 13}

hh3cLswSlotTemperature    OBJECT-TYPE
SYNTAX Integer32
MAX-ACCESS read-only
STATUS current
DESCRIPTION
"The temperature of system on the board."
::= {hh3cLswSlotEntry 14}

hh3cLswSlotPktBufFree    OBJECT-TYPE
SYNTAX Integer32
MAX-ACCESS read-only
STATUS current
DESCRIPTION
"The number of packet buffers available for internal VME transfers
or external transfers, respectively.  Because switch operations and
application software modules impose some overhead on global memory
buffers, the number of buffers available for data transfers is less
than the total number of buffers allocated when the switch boots."
::= {hh3cLswSlotEntry 15}

hh3cLswSlotPktBufInit    OBJECT-TYPE
SYNTAX Integer32
MAX-ACCESS read-only
STATUS current
DESCRIPTION
"The number of packet buffers allocated when the switch booted."
::= {hh3cLswSlotEntry 16}

hh3cLswSlotPktBufMin    OBJECT-TYPE
SYNTAX Integer32
MAX-ACCESS read-only
STATUS current
DESCRIPTION
"The smallest number of packet buffers available since the switch booted."
::= {hh3cLswSlotEntry 17}

hh3cLswSlotPktBufMiss    OBJECT-TYPE
SYNTAX Counter64
MAX-ACCESS read-only
STATUS current
DESCRIPTION
"The number of times that the switch was unable to obtain a packet
buffer.  Failure to obtain a buffer indicates that buffers were busy."
::= {hh3cLswSlotEntry 18}

hh3cLswSlotRunTime    OBJECT-TYPE
SYNTAX       DisplayString (SIZE(0..64))
MAX-ACCESS      read-only
STATUS          current
DESCRIPTION
"Runtime of board.

For example, if a board has run for 2 days 4 hours and 20 minutes,
its runtime is displayed as 0 weeks, 2 days, 4 hours, 20 minutes."
::= {hh3cLswSlotEntry 19}

hh3cLswSlotPhyMemRev    OBJECT-TYPE
SYNTAX CounterBasedGauge64
UNITS "bytes"
MAX-ACCESS read-only
STATUS current
DESCRIPTION
"Size of the memory on the board.

This node is used to replace hh3cLswSlotPhyMemory."
::= {hh3cLswSlotEntry 20}

hh3cLswSlotMemRev    OBJECT-TYPE
SYNTAX CounterBasedGauge64
UNITS "bytes"
MAX-ACCESS read-only
STATUS current
DESCRIPTION
"Size of the memory space for the software system on the board.

This node is used to replace hh3cLswSlotMemory.

Note that the system memory means the memory can be used by
the software platform."
::= {hh3cLswSlotEntry 21}

hh3cLswSlotMemUsedRev    OBJECT-TYPE
SYNTAX CounterBasedGauge64
UNITS "bytes"
MAX-ACCESS read-only
STATUS current
DESCRIPTION
"Size of the memory space used by the software system on the board.

This node is used to replace hh3cLswSlotMemoryUsed.

Note that the system memory means the memory can be used by
the software platform."
::= {hh3cLswSlotEntry 22}

hh3cLswSlotModelDesc  OBJECT-TYPE
SYNTAX DisplayString (SIZE(0..255))
MAX-ACCESS read-only
STATUS current
DESCRIPTION
"Model of the extended device in a slot.  Examples of extended devices
include PEXs and firewall modules.  If the device in the slot is not
an extended device, a zero-length string is returned."
::= {hh3cLswSlotEntry 23}

hh3cLswSlotPktBufThreshold  OBJECT-TYPE
SYNTAX Integer32 (1..100)
MAX-ACCESS read-write
STATUS current
DESCRIPTION
"The threshold of buffers for the slot, with the step
length of 1, ranging from 1 to 100 in percentage.
Default value is defined by product."
::= {hh3cLswSlotEntry 24}

hh3cLswSlotSerialNumber  OBJECT-TYPE
SYNTAX SnmpAdminString (SIZE(0..32))
MAX-ACCESS read-only
STATUS current
DESCRIPTION
"Serial number of the current slot."
::= {hh3cLswSlotEntry 25}

hh3cLswSlotPower  OBJECT-TYPE
SYNTAX Integer32
MAX-ACCESS read-only
STATUS current
DESCRIPTION
"Power of the current slot, in W."
::= {hh3cLswSlotEntry 26}

hh3cSlotCurrentVoltage OBJECT-TYPE
SYNTAX Integer32
MAX-ACCESS read-only
STATUS current
DESCRIPTION
"Real-time voltage of the current slot."
::= {hh3cLswSlotEntry 27}

hh3cSlotCurrent OBJECT-TYPE
SYNTAX Integer32
MAX-ACCESS read-only
STATUS current
DESCRIPTION
"Real-time current of the current slot."
::= {hh3cLswSlotEntry 28}

hh3cSlotTemperatureThreshold OBJECT-TYPE
SYNTAX Integer32
UNITS      "degree centigrade"
MAX-ACCESS read-only
STATUS current
DESCRIPTION
"Temperature alarm threshold of the current slot."
::= {hh3cLswSlotEntry 29}

hh3cSlotNominalPower OBJECT-TYPE
SYNTAX Unsigned32
UNITS      "W"
MAX-ACCESS read-only
STATUS current
DESCRIPTION
"Rated power of the current slot."
::= {hh3cLswSlotEntry 30}

hh3cSlotNormalPowerNum      OBJECT-TYPE
SYNTAX       Unsigned32
MAX-ACCESS     read-only
STATUS     current
DESCRIPTION
"Number of power modules."
::= {hh3cLswSlotEntry 31}

hh3cSlotPatchVersion    OBJECT-TYPE
SYNTAX     DisplayString(SIZE(1..2048))
MAX-ACCESS     read-only
STATUS     current
DESCRIPTION
"The patch version in a slot."
::= {hh3cLswSlotEntry 32}

-- ==================================================================
--
-- sub slot information table
--
-- ==================================================================

hh3cLswSubslotTable    OBJECT-TYPE
SYNTAX     SEQUENCE OF Hh3cLswSubslotEntry
MAX-ACCESS     not-accessible
STATUS     current
DESCRIPTION
"Subslot description table."
::= {hh3cLswSlotConf 4}

hh3cLswSubslotEntry    OBJECT-TYPE
SYNTAX     Hh3cLswSubslotEntry
MAX-ACCESS     not-accessible
STATUS     current
DESCRIPTION
"Subslot description table entry."
INDEX {
hh3cLswFrameIndex,
hh3cLswSlotIndex,
hh3cLswSubslotIndex
}
::= {hh3cLswSubslotTable 1}

Hh3cLswSubslotEntry ::= SEQUENCE
{
hh3cLswSubslotIndex        Integer32,
hh3cLswSubslotType         Hh3cLswTypeOfSlot,
hh3cLswSubslotPortNum      Integer32,
hh3cLswSubslotAdminStatus  INTEGER,
hh3cLswSubslotFirstIfIndex Integer32,
hh3cLswSubslotSerialNumber SnmpAdminString
}

hh3cLswSubslotIndex      OBJECT-TYPE
SYNTAX         Integer32
MAX-ACCESS     read-only
STATUS         current
DESCRIPTION
"Subslot index."
::= {hh3cLswSubslotEntry 1}

-- value list of hh3cLswSubslotType are identical with the value list of hh3cLswSlotType.
hh3cLswSubslotType      OBJECT-TYPE
SYNTAX         Hh3cLswTypeOfSlot
MAX-ACCESS     read-only
STATUS         current
DESCRIPTION
"Type of the pinch board in the subslot."
::= {hh3cLswSubslotEntry 2}

hh3cLswSubslotPortNum   OBJECT-TYPE
SYNTAX         Integer32
MAX-ACCESS     read-only
STATUS         current
DESCRIPTION
"Number of physical ports in the pinch board."
::= {hh3cLswSubslotEntry 3}


hh3cLswSubslotAdminStatus    OBJECT-TYPE
SYNTAX              INTEGER
{
not-install (1),
normal      (2),
fault       (3),
forbidden   (4)
}
MAX-ACCESS          read-only
STATUS              current
DESCRIPTION
"Status of the pinch board in the subslot."
::= {hh3cLswSubslotEntry 4}

hh3cLswSubslotFirstIfIndex   OBJECT-TYPE
SYNTAX         Integer32
MAX-ACCESS     read-only
STATUS         current
DESCRIPTION
"The value of ifIndex of the first physical port in the pinch board."
::= {hh3cLswSubslotEntry 5}

hh3cLswSubslotSerialNumber   OBJECT-TYPE
SYNTAX         SnmpAdminString (SIZE(0..32))
MAX-ACCESS     read-only
STATUS         current
DESCRIPTION
"Serial number of the current subslot card."
::= {hh3cLswSubslotEntry 6}

-- ==================================================================
--
-- port information table
--
-- ==================================================================

hh3cLswPortTable    OBJECT-TYPE
SYNTAX     SEQUENCE OF Hh3cLswPortEntry
MAX-ACCESS     not-accessible
STATUS     current
DESCRIPTION
"Port configuration table."
::= {hh3cLswSlotConf 5}

hh3cLswPortEntry    OBJECT-TYPE
SYNTAX     Hh3cLswPortEntry
MAX-ACCESS     not-accessible
STATUS     current
DESCRIPTION
"Port configuration table entry."
INDEX {
hh3cLswFrameIndex,
hh3cLswSlotIndex,
hh3cLswSubslotIndex,
hh3cLswPortIndex
}
::= {hh3cLswPortTable 1}

Hh3cLswPortEntry ::= SEQUENCE
{
hh3cLswPortIndex             Integer32,
hh3cLswPortType              INTEGER,
hh3cLswPortIfindex           Integer32,
hh3cLswPortIsPlugged         INTEGER
}

hh3cLswPortIndex    OBJECT-TYPE
SYNTAX     Integer32
MAX-ACCESS     read-only
STATUS     current
DESCRIPTION
"The port number on the device.  The first port number is 1, which is
reserved if the port does not exist."
::= {hh3cLswPortEntry 1}

hh3cLswPortType   OBJECT-TYPE
SYNTAX     INTEGER
{
type-NULL(0),                                             -- NULL
type-10OR100M(1),                                         -- 10BASE-T or 100BASE-TX  Electrical Interface
type-1000BASE-LX-SM(2),                                   -- 1000BASE-LX Single Mode Fiber Optic Transceivers IR
type-1000BASE-SX-MM(3),                                   -- 1000BASE-SX Multi Mode Fiber Optic Transceivers SR
type-1000BASE-TX(4),                                      -- 1000BASE-T Electrical Interface
type-100M-SINGLEMODE-FX(5),                               -- 100BASE-FX Single Mode Fiber Optic Transceivers
type-100M-MULTIMODE-FX(6),                                -- 100BASE-FX Multi Mode Fiber Optic Transceivers
type-100M-100BASE-TX(7),                                  -- 100BASE-TX Electrical Interface
type-100M-HUB(8),                                         -- 100M HUB
type-VDSL(9),                                             -- Very High Speed DSL
type-STACK(10),                                           -- Gigabit STACK
type-1000BASE-ZENITH-FX(11),                              -- 1000BASE-LX Single Mode Fiber Optic Transceivers VLR
type-1000BASE-LONG-FX(12),                                -- 1000BASE-LX Single Mode Fiber Optic Transceivers LR
type-ADSL(13),                                            -- Asymmetric Digital Subscriber Line
type-10OR100M-db(14),                                     -- 10/100M ethernet electric port,each RJ-45 has 2 ethernet ports
type-10GBASE-LR-SM(15),                                   -- 10GBASE-LR  Single Mode Fiber Optic Transceivers
type-10GBASE-LX4-MM(16),                                  -- 10GBASE-LX4 Multi Mode Fiber Optic Transceivers
type-10GBASE-LX4-SM(17),                                  -- 10GBASE-LX4 Single Mode Fiber Optic Transceivers
type-100M-LONG-FX(18),                                    -- 100BASE-FX Single Mode Fiber Optic Transceivers LR SC
type-1000BASE-CX(19),                                     -- 1000BASE-CX
type-1000BASE-ZENITH-FX-LC(20),                           -- 1000BASE-LX Single Mode Fiber Optic Transceivers VLR with LC Connector
type-1000BASE-LONG-FX-LC(21),                             -- 1000BASE-LX Single Mode Fiber Optic Transceivers LR with LC Connector
type-100M-SM-FX-SC(22),                                   -- 100BASE-FX Single Mode Fiber Optic Transceivers with SC Connector
type-100M-MM-FX-SC(23),                                   -- 100BASE-FX Multi Mode Fiber Optic Transceivers with SC Connector
type-100M-SM-FX-LC(24),                                   -- 100BASE-FX Single Mode Fiber Optic Transceivers with LC Connector
type-100M-MM-FX-LC(25),                                   -- 100BASE-FX Multi Mode Fiber Optic Transceivers with LC Connector
type-GBIC-NO-CONNECTOR(26),                               --
type-GBIC-1000-BASE-T(27),                                --
type-GBIC-1000-BASE-LX(28),                               --
type-GBIC-1000-BASE-SX(29),                               --
type-GBIC-1000-BASE-ZX(30),                               --
type-COMBO-NO-CONNECTOR(31),                              --
type-COMBO-1000-BASE-LX(32),                              --
type-COMBO-1000-BASE-LX-FIBER(33),                        --
type-COMBO-1000-BASE-LX-COPPER(34),                       --
type-COMBO-1000-BASE-SX(35),                              --
type-COMBO-1000-BASE-SX-FIBER(36),                        --
type-COMBO-1000-BASE-SX-COPPER(37),                       --
type-COMBO-1000-BASE-ZX(38),                              --
type-COMBO-1000-BASE-ZX-FIBER(39),                        --
type-COMBO-1000-BASE-ZX-COPPER(40),                       --
type-155-POS-SX-MMF(41),                                  --
type-155-POS-LX-SMF(42),                                  --
type-1000BASE-T(43),                                      -- 1000 Base-T Port
type-1000BASE-SX-SFP(44),                                 -- 1000 Base-SX SFP Port
type-1000BASE-LX-SFP(45),                                 -- 1000 Base-SX SFP Port
type-1000BASE-T-AN-SFP(46),                               -- 1000 Base-T AN SFP Port
type-10GBASE-LX4-XENPAK(47),                              -- 10G Base-LX4 XENPAK Port
type-10GBASE-LR-XENPAK(48),                               -- 10G Base-LR XENPAK Port
type-10GBASE-CX4(49),                                     -- 10G Base-CX4 Port
type-1000BASE-ZX-SFP(50),                                 -- 1000 Base-ZX SFP Port
type-1000BASE-MM-SFP(51),                                 -- 1000 Base-MM SFP Port
type-100BASE-SX-SFP(52),                                  -- 100 Base-SX SFP Port
type-100BASE-LX-SFP(53),                                  -- 100 Base-LX SFP Port
type-100BASE-T-AN-SFP(54),                                -- 100 Base-T SFP Port
type-100BASE-ZX-SFP(55),                                  -- 100 Base-ZX SFP Port
type-100BASE-MM-SFP(56),                                  -- 100 Base-MM SFP Port
type-SFP-NO-CONNECTOR(57),                                -- No Connector SFP Port
type-SFP-UNKNOWN-CONNECTOR(58),                           --  Unknown SFP Port
type-POS-NO-CONNECTOR(59),                                -- POS no connector
type-10G-BASE-SR(60),                                     -- 10GBASE-SR Fiber Optic Transceivers with SC Connector
type-10G-BASE-ER(61),                                     -- 10GBASE-ER Fiber Optic Transceivers with SC Connector
type-10G-BASE-LX4(62),                                    -- 10GBASE-LX4 Fiber Optic Transceivers with SC Connector
type-10G-BASE-SW(63),                                     -- 10GBASE-SW Fiber Optic Transceivers with SC Connector
type-10G-BASE-LW(64),                                     -- 10GBASE-LW Fiber Optic Transceivers with SC Connector
type-10G-BASE-EW(65),                                     -- 10GBASE-EW Fiber Optic Transceivers with SC Connector
type-10G-LR-SM-LC(66),                                    -- 10GBASE-LR Single Mode Fiber Optic Transceivers with LC Connector
type-10G-SR-MM-LC(67),                                    -- 10GBASE-SR Multi Mode Fiber Optic Transceivers with LC Connector
type-10G-ER-SM-LC(68),                                    -- 10GBASE-ER Single Mode Fiber Optic Transceivers with LC Connector
type-10G-LW-SM-LC(69),                                    -- 10GBASE-LW Single Mode Fiber Optic Transceivers with LC Connector
type-10G-SW-MM-LC(70),                                    -- 10GBASE-SW Multi Mode Fiber Optic Transceivers with LC Connector
type-10G-EW-SM-LC(71),                                    -- 10GBASE-EW Single Mode Fiber Optic Transceivers with LC Connector

type-100BASE-SM-MTRJ(72),                                 -- 100 Base-SM MTRJ Port
type-100BASE-MM-MTRJ(73),                                 -- 100 Base-MM MTRJ Port

type-XFP-NO-CONNECTOR(74),                                -- XFP without Transceiver
type-XFP-10GBASE-SR(75),                                  -- 10GBASE-SR XFP Transceiver
type-XFP-10GBASE-LR(76),                                  -- 10GBASE-LR XFP Transceiver
type-XFP-10GBASE-ER(77),                                  -- 10GBASE-ER XFP Transceiver
type-XFP-10GBASE-SW(78),                                  -- 10GBASE-SW XFP Transceiver
type-XFP-10GBASE-LW(79),                                  -- 10GBASE-LW XFP Transceiver
type-XFP-10GBASE-EW(80),                                  -- 10GBASE-EW XFP Transceiver
type-XFP-10GBASE-CX4(81),                                 -- 10GBASE-CX4 XFP Transceiver
type-XFP-10GBASE-LX4(82),                                 -- 10GBASE-LX4 XFP Transceiver
type-XFP-UNKNOWN(83),                                     -- Unknown  XFP Transceiver

type-XPK-NOCONNECTOR(84),                                 -- Xenpak without Transceiver
type-XPK-10GBASE-SR(85),                                  -- 10GBASE-SR Xenpak Transceiver
type-XPK-10GBASE-LR(86),                                  -- 10GBASE-LR Xenpak Transceiver
type-XPK-10GBASE-ER(87),                                  -- 10GBASE-ER Xenpak Transceiver
type-XPK-10GBASE-SW(88),                                  -- 10GBASE-SW Xenpak Transceiver
type-XPK-10GBASE-LW(89),                                  -- 10GBASE-LW Xenpak Transceiver
type-XPK-10GBASE-EW(90),                                  -- 10GBASE-EW Xenpak Transceiver
type-XPK-10GBASE-CX4(91),                                 -- 10GBASE-CX4 Xenpak Transceiver
type-XPK-10GBASE-LX4(92),                                 -- 10GBASE-LX4 Xenpak Transceiver
type-XPK-UNKNOWN(93),                                     -- Unknown Xenpak Transceiver

type-POS-OC48-SR-SM-LC(94),                               -- OC48-SR Single Mode Fiber Optic Transceivers with LC Connector
type-POS-OC48-IR-SM-LC(95),                               -- OC48-IR Single Mode Fiber Optic Transceivers with LC Connector
type-POS-OC48-LR-SM-LC(96),                               -- OC48-LR Single Mode Fiber Optic Transceivers with LC Connector

type-10G-BASE-CX4(97),                                    -- 10G BASE-CX4 Electrical Interface

type-OLT-1000BASE-BX-SFF-SC(98),                          -- 1000 BASE-BX SFF SC OLT Port
type-ONU-1000BASE-BX-SFF-SC(99),                          -- 1000 BASE-BX SFF SC ONU Port

type-24G-CASCADE(100),                                    -- 24G Cascade port

type-POS-OC3-SR-MM(101),                                  -- STM1/OC3 Short Reach Multi Mode Fiber Optic Transceivers with LC Connector
type-POS-OC3-IR-SM(102),                                  -- STM1/OC3 Intermediate Reach Single Mode Fiber Optic Transceivers with LC Connector
type-POS-OC3-IR-1-SM(103),                                -- STM1/OC3 Intermediate Reach Single Mode Fiber Optic Transceivers with LC Connector(variation 1)
type-POS-OC3-IR-2-SM(104),                                -- STM1/OC3 Intermediate Reach Single Mode Fiber Optic Transceivers with LC Connector(variation 2)
type-POS-OC3-LR-SM(105),                                  -- STM1/OC3 Long Reach Single Mode Fiber Optic Transceivers with LC Connector
type-POS-OC3-LR-1-SM(106),                                -- STM1/OC3 Long Reach Single Mode Fiber Optic Transceivers with LC Connector(variation 1)
type-POS-OC3-LR-2-SM(107),                                -- STM1/OC3 Long Reach Single Mode Fiber Optic Transceivers with LC Connector(variation 2)
type-POS-OC3-LR-3-SM(108),                                -- STM1/OC3 Long Reach Single Mode Fiber Optic Transceivers with LC Connector(variation 3)
type-POS-OC12-SR-MM(109),                                 -- STM4/OC12 Short Reach Multi Mode Fiber Optic Transceivers with LC Connector
type-POS-OC12-IR-SM(110),                                 -- STM4/OC12 Intermediate Reach Single Mode Fiber Optic Transceivers with LC Connector
type-POS-OC12-IR-1-SM(111),                               -- STM4/OC12 Intermediate Reach Single Mode Fiber Optic Transceivers with LC Connector(variation 1)
type-POS-OC12-IR-2-SM(112),                               -- STM4/OC12 Intermediate Reach Single Mode Fiber Optic Transceivers with LC Connector(variation 2)
type-POS-OC12-LR-SM(113),                                 -- STM4/OC12 Long Reach Single Mode Fiber Optic Transceivers with LC Connector
type-POS-OC12-LR-1-SM(114),                               -- STM4/OC12 Long Reach Single Mode Fiber Optic Transceivers with LC Connector(variation 1)
type-POS-OC12-LR-2-SM(115),                               -- STM4/OC12 Long Reach Single Mode Fiber Optic Transceivers with LC Connector(variation 2)
type-POS-OC12-LR-3-SM(116),                               -- STM4/OC12 Long Reach Single Mode Fiber Optic Transceivers with LC Connector(variation 3)
type-POS-OC48-SR-SM(117),                                 -- STM16/OC48 Short Reach Single Mode Fiber Optic Transceivers with LC Connector
type-POS-OC48-IR-SM(118),                                 -- STM16/OC48 Intermediate Reach Single Mode Fiber Optic Transceivers with LC Connector
type-POS-OC48-IR-1-SM(119),                               -- STM16/OC48 Intermediate Reach Single Mode Fiber Optic Transceivers with LC Connector(variation 1)
type-POS-OC48-IR-2-SM(120),                               -- STM16/OC48 Intermediate Reach Single Mode Fiber Optic Transceivers with LC Connector(variation 2)
type-POS-OC48-LR-SM(121),                                 -- STM16/OC48 Long Reach Single Mode Fiber Optic Transceivers with LC Connector
type-POS-OC48-LR-1-SM(122),                               -- STM16/OC48 Long Reach Single Mode Fiber Optic Transceivers with LC Connector(variation 1)
type-POS-OC48-LR-2-SM(123),                               -- STM16/OC48 Long Reach Single Mode Fiber Optic Transceivers with LC Connector(variation 2)
type-POS-OC48-LR-3-SM(124),                               -- STM16/OC48 Long Reach Single Mode Fiber Optic Transceivers with LC Connector(variation 3)
type-POS-I-64-1(125),                                     -- STM64/OC192 Interconnect Fiber Optic Transceivers with LC Connector(wavelength 1310nm G.652 fiber)
type-POS-I-64-2(126),                                     -- STM64/OC192 Interconnect Fiber Optic Transceivers with LC Connector(wavelength 1550nm G.652 fiber)
type-POS-I-64-3(127),                                     -- STM64/OC192 Interconnect Fiber Optic Transceivers with LC Connector(wavelength 1550nm G.653 fiber)
type-POS-I-64-5(128),                                     -- STM64/OC192 Interconnect Fiber Optic Transceivers with LC Connector(wavelength 1550nm G.655 fiber)
type-POS-S-64-1(129),                                     -- STM64/OC192 Short Haul Fiber Optic Transceivers with LC Connector(wavelength 1310nm G.652 fiber)
type-POS-S-64-2(130),                                     -- STM64/OC192 Short Haul Fiber Optic Transceivers with LC Connector(wavelength 1550nm G.652 fiber)
type-POS-S-64-3(131),                                     -- STM64/OC192 Short Haul Fiber Optic Transceivers with LC Connector(wavelength 1550nm G.653 fiber)
type-POS-S-64-5(132),                                     -- STM64/OC192 Short Haul Fiber Optic Transceivers with LC Connector(wavelength 1550nm G.655 fiber)
type-POS-L-64-1(133),                                     -- STM64/OC192 Long Haul Fiber Optic Transceivers with LC Connector(wavelength 1310nm G.652 fiber)
type-POS-L-64-2(134),                                     -- STM64/OC192 Long Haul Fiber Optic Transceivers with LC Connector(wavelength 1550nm G.652 fiber)
type-POS-L-64-3(135),                                     -- STM64/OC192 Long Haul Fiber Optic Transceivers with LC Connector(wavelength 1550nm G.653 fiber)
type-POS-V-64-2(136),                                     -- STM64/OC192 Very Long Haul Fiber Optic Transceivers with LC Connector(wavelength 1550nm G.652 fiber)
type-POS-V-64-3(137),                                     -- STM64/OC192 Very Long Haul Fiber Optic Transceivers with LC Connector(wavelength 1550nm G.653 fiber)
type-100BASE-FX-BIDI(138),                                -- 100 BASE-FX BIDI Port
type-100BASE-BX10-U-SFP(139),                             -- 100 BASE-BX10-U-SFP Port
type-100BASE-BX10-D-SFP(140),                             -- 100 BASE-BX10-D-SFP Port
type-1000BASE-BX10-U-SFP(141),                            -- 1000 BASE-BX10-U-SFP Port
type-1000BASE-BX10-D-SFP(142),                            -- 1000 BASE-BX10-D-SFP Port
type-STK-1000BASE-T(143),                                 -- 1000 BASE-T Stack Port
type-RPR-PHYPOS-CONNECTOR(144),                           -- Resilient Packet Ring POS physical port
type-RPR-PHY10GE-CONNECTOR(145),                          -- 10G Resilient Packet Ring physical port
type-RPR-LOGICPOS-CONNECTOR(146),                         -- Resilient Packet Ring POS logical port
type-RPR-LOGIC10GE-CONNECTOR(147),                        -- 10G Resilient Packet Ring logical port
type-10GBASE-ZR(148),                                     -- Fiber Optic Transceivers with SC Connector, XENPAK
type-TYPE-ERROR-CONNECTOR(149),                           -- Error Optic Transceivers type
type-10G-STACK(150),                                      -- 10G Stack Port
type-155-ATM-SX-MMF(151),                                 -- ATM OC-3 Multi-mode Short Reach Optical Transceiver
type-155-ATM-LX-SMF(152),                                 -- ATM OC-3 single mode long reach optical transceiver
type-622-ATM-SX-MMF(153),                                 -- ATM OC-12 Multi-mode Short Reach Optical Transceiver
type-622-ATM-LX-SMF(154),                                 -- ATM OC-12 Single Mode Long Reach Optical Transceiver
type-155-ATM-NO-CONNECTOR(155),                           -- ATM OC-3 No Connector
type-622-ATM-NO-CONNECTOR(156),                           -- ATM OC-12 No Connector
type-155-CPOS-E1-NO-CONNECTOR(157),                       -- CPOS(E1) OC-3 No Connector
type-155-CPOS-T1-NO-CONNECTOR(158),                       -- CPOS(T1) OC-3 No Connector
type-622-CPOS-E1-NO-CONNECTOR(159),                       -- CPOS(E1) OC-12 No Connector
type-622-CPOS-T1-NO-CONNECTOR(160),                       -- CPOS(T1) OC-12 No Connector
type-155-CPOS-E1-SX-MMF(161),                             -- CPOS(E1) OC-3 Multi-mode Short Reach Optical Transceiver
type-155-CPOS-T1-SX-MMF(162),                             -- CPOS(T1) OC-3 Multi-mode Short Reach Optical Transceiver
type-155-CPOS-E1-LX-SMF(163),                             -- CPOS(E1) OC-3 Single Mode Long Reach Optical Transceiver
type-155-CPOS-T1-LX-SMF(164),                             -- CPOS(T1) OC-3 Single Mode Long Reach Optical Transceiver
type-622-CPOS-E1-SX-MMF(165),                             -- CPOS(E1) OC-12 Multi-mode Short Reach Optical Transceiver
type-622-CPOS-T1-SX-MMF(166),                             -- CPOS(T1) OC-12 Multi-mode Short Reach Optical Transceiver
type-622-CPOS-E1-LX-SMF(167),                             -- CPOS(E1) OC-12 Single Mode Long Reach Optical Transceiver
type-622-CPOS-T1-LX-SMF(168),                             -- CPOS(T1) OC-12 Single Mode Long Reach Optical Transceiver
type-E1-CONNECTOR(169),                                   -- E1 RJ45 Transceiver
type-T1-CONNECTOR(170),                                   -- T1 RJ45 Transceiver
type-1000BASE-STK-SFP(171),                               -- 1-port 1000 Base-STK SFP Module
type-1000BASE-BIDI-SFP(172),                              -- 1-port 1000 Base-BIDI SFP Module
type-1000BASE-CWDM-SFP(173),                              -- 1-port 1000 Base-CWDM SFP Module
type-100BASE-BIDI-SFP(174),                               -- 1-port 100 Base-BIDI SFP Module
type-OLT-1000BASE-PX-SFP(175),                            -- 1000BASE-PX SFP OLT Interface
type-OLT-1000BASE-NO-CONNECTOR(176),                      -- 1000BASE OLT No Connector
type-RPR-PHYGE-CONNECTOR(177),                            -- Resilient Packet Ring GE physical port
type-RPR-LOGICGE-CONNECTOR(178),                          -- Resilient Packet Ring GE logical port
type-100M-1550-BIDI(179),                                 -- Single Port 100M Ethernet Bi-direction Optical Interface Module(TX1550nm, RX1310nm, 15km, SC)
type-100M-1310-BIDI(180),                                 -- Single Port 100M Ethernet Bi-direction Optical reverse Interface Module(TX1310nm, RX1550nm, 15km, SC)
type-RPR-PHYOC48-CONNECTOR(181),                          -- Resilient Packet Ring OC48 physical port
type-RPR-LOGICOC48-CONNECTOR(182),                        -- Resilient Packet Ring OC48 logical port
type-100-1000-BASE-LX-SMF(183),                           -- 100BASE-LX/1000BASE-LX Single Mode Fiber Optic Transceivers
type-10G-ZW-SM-LC(184),                                   -- 10GBASE-ZW Single Mode Fiber Optic Transceivers with LC Connector
type-10G-ZR-SM-LC(185),                                   -- 10GBASE-ZR Single Mode Fiber Optic Transceivers with LC Connector
type-XPK-10GBASE-ZR(186),                                 -- 10GBASE-ZR Xenpak Transceiver:LH80,SM1550
type-SGMII-100-BASE-LX-SFP(187),                          -- SGMII-100-BASE-LX-SFP Port
type-SGMII-100-BASE-FX-SFP(188),                          -- SGMII-100-BASE-FX-SFP Port
type-WLAN-RADIO(189),                                     -- WLAN-RADIO Port
type-SFP-PLUS-NO-CONNECTOR(191),                          -- SFP+ without Transceiver
type-SFP-PLUS-10GBASE-SR(192),                            -- 10GBASE-SR SFP+ Transceiver
type-SFP-PLUS-10GBASE-LR(193),                            -- 10GBASE-LR SFP+ Transceiver
type-SFP-PLUS-10GBASE-LRM(194),                           -- 10GBASE-LRM SFP+ Transceiver
type-SFP-PLUS-10GBASE-Cu(195),                            -- 10GBASE-Cu SFP+ Transceiver
type-SFP-PLUS-UNKNOWN(196),                               -- Unknown SFP+ Transceiver
type-SFP-PLUS-STACK-CONNECTOR(197),                       -- SFP+ STACK Transceiver
type-POS-L-64-4(198),                                     -- STM64/OC192 Long Haul Fiber Optic Transceivers with LC Connector(wavelength 1550nm G.653 fiber)
type-MINISAS-HD-STACK-CONNECTOR(199),                     -- MiniSAS HD STACK Transceiver
type-ONU-1000BASE-PX-SFF(200),                            -- 1000BASE-PX SFF ONU Interface
type-RS485(201),                                          -- RS485 Interface
type-SFP-PLUS-10GBASE-ER(202),                            -- 10GBASE-ER SFP+ Transceiver
type-SFP-PLUS-10GBASE-ZR(203),                            -- 10GBASE-ZR SFP+ Transceiver
type-XFP-10GBASE-ZR(204),                                 -- 10GBASE-ZR XFP Transceiver
type-QSFP-PLUS-40GBASE-SR4(205),                          -- 40BASE-SR4 QSFP+ Optical Transceiver
type-QSFP-PLUS-STACK-CONNECTOR(206),                      -- QSFP+ STACK Transceiver
type-QSFP-PLUS-TO-4SFP-PLUS-STACK-CONNECTOR(207),         -- QSFP+ to 4 SFP+ STACK Transceiver
type-SFP-STACK-CONNECTOR(208),                            -- SFP STACK Transceiver
type-QSFP-NO-CONNECTOR(209),                              -- QSFP No Connector
type-10GBase-T(210),                                      -- 10G Base-T Port
type-CFP-NO-CONNECTOR(211),                               -- CFP No Connector
type-CFP-40GBASE-LR4(212),                                -- 40GBASE-LR4 CFP Transceiver
type-QSFP-PLUS-NO-CONNECTOR(213),                         -- QSFP+ No Connector
type-QSFP-PLUS-40GBASE-LR4(214),                          -- 40GBASE-LR4 QSFP+ Optical Transceiver
type-CFP-40GBASE-SR4(215),                                -- 40GBASE-SR4 CFP Optical Transceiver
type-CFP-100GBASE-LR4(216),                               -- 100GBASE-LR4 CFP Optical Transceiver
type-CFP-100GBASE-SR10(217),                              -- 100GBASE-SR10 CFP Optical Transceiver
type-CXP-100GBASE-SR10(218),                              -- 100GBASE-SR10 CXP Optical Transceiver
type-CXP-NO-CONNECTOR(219),                               -- CXP No Connector
type-TRANSCEIVER-UNKNOWN(220),                            -- Unknown Transceiver
type-QSFP-PLUS-UNKNOWN(221),                              -- Unknown QSFP+ Transceiver
type-CFP-UNKNOWN(222),                                    -- Unknown CFP Transceiver
type-QSFP-PLUS-40GBASE-CSR4(223),                         -- 40GBASE-CSR4 QSFP+ Optical Transceiver
type-CFP-40GBASE-ER4(224),                                -- 40GBASE-ER4 CFP Optical Transceiver
type-SFP-1000BASE-BIDI(225),                              -- 1000BASE SFP Bi-direction Optical Transceiver
type-SFP-PLUS-10GBASE-ZR-DWDM(226),                       -- 10GBase-ZR SFP+ DWDM Optical Transceiver
type-QSFP-PLUS-40GBASE-PSM(227),                          -- 40GBASE QSFP+ Parallel SingleMode Optical Transceiver
type-SFP-8GFC-SW(228),                                    -- SFP 8G FC Optical Transceiver short wave
type-SFP-8GFC-LW(229),                                    -- SFP 8G FC Optical Transceiver long wave
type-CXP-100GBASE-AOC(230),                               -- 100GBASE CXP Active Optical Cable
type-QSFP-PLUS-ACTIVE-STACK-CONNECTOR(231),               -- QSFP+ Active STACK Transceiver
type-QSFP-PLUS-TO-4SFP-PLUS-ACTIVE-STACK-CONNECTOR(232),  -- QSFP+ to 4 SFP+ Active STACK Transceiver
type-CFP2-100GBASE-LR4(233),                              -- 100GBASE-LR4 CFP2 Optical Transceiver
type-CFP2-100GBASE-SR10(234),                             -- 100GBASE-SR10 CFP2 Optical Transceiver
type-QSFP-PLUS-ACTIVE-OPTICAL-CABLE(235),                 -- QSFP+ AOC
type-QSFP-PLUS-TO-4SFP-PLUS-ACTIVE-OPTICAL-CABLE(236),    -- QSFP+ to 4 SFP+ AOC
type-SFP-PLUS-ACTIVE-OPTICAL-CABLE(237),                  -- SFP+ AOC
type-CFP2-NO-CONNECTOR(238),                              -- CFP2 No Connector
type-QSFP28-NO-CONNECTOR(239),                            -- QSFP28 No Connector
type-QSFP28-100GBASE-SR4(240),                            -- 100BASE-SR4 QSFP28 Optical Transceiver
type-QSFP28-100GBASE-LR4(241),                            -- 100GBASE-LR4 QSFP28 Optical Transceiver
type-QSFP28-100GBASE-ER4(242),                            -- 100GBASE-ER4 QSFP28 Optical Transceiver
type-QSFP28-100GBASE-PSM4(243),                           -- 100GBASE-PSM4 QSFP28 Optical Transceiver
type-QSFP28-100GBASE-CWDM4(244),                          -- 100GBASE-CWDM4 QSFP28 Optical Transceiver
type-QSFP28-STACK-CONNECTOR(245),                         -- QSFP28 STACK Transceiver
type-QSFP28-TO-4SFP28-STACK-CONNECTOR(246),               -- QSFP28 to 4 SFP28 STACK Transceiver
type-QSFP28-ACTIVE-STACK-CONNECTOR(247),                  -- QSFP28 Active STACK Transceiver
type-QSFP28-TO-4SFP28-ACTIVE-STACK-CONNECTOR(248),        -- QSFP28 to 4 SFP28 Active STACK Transceiver
type-QSFP28-ACTIVE-OPTICAL-CABLE(249),                    -- QSFP28 AOC
type-QSFP28-TO-4SFP28-ACTIVE-OPTICAL-CABLE(250),          -- QSFP28 to 4 SFP28 AOC
type-QSFP-PLUS-40GBASE-LM4(251),                          -- 40BASE-LM4 QSFP+ Optical Transceiver
type-QSFP-PLUS-40GBASE-SWDM4(252),                        -- 40BASE-SWDM4 QSFP+ Optical Transceiver
type-CFP-100GBASE-ER4(253),                               -- 100GBASE-ER4 CFP Transceiver
type-QSFP-PLUS-40GBASE-ER4(254),                          -- 40GBASE-ER4 QSFP+ Optical Transceiver
type-QSFP-PLUS-40GBASE-ER4L(255),                         -- 40GBASE-ER4L QSFP+ Optical Transceiver
type-QSFP-PLUS-40GBASE-BIDI(256),                         -- 40GBASE-ER4 QSFP+ Optical Transceiver
type-QSFP-PLUS-40GBASE-LR4L(257),                         -- 40BASE-LR4L QSFP+ Optical Transceiver
type-CFP2-100GBASE-eSR10(258),                            -- 100GBASE-eSR10 CFP2 Optical Transceiver
type-TUNABLE-SFP-PLUS-10GBASE-ZR-DWDM(259),               -- 10GBase-ZR Tunable SFP+ DWDM Optical Transceiver
type-SFP28-25GBASE-SR(260),                               -- 25GBASE-SR SFP28 Optical Transceiver
type-SFP28-ACTIVE-OPTICAL-CABLE(261),                     -- SFP28 AOC
type-SFP28-STACK-CONNECTOR(262),                          -- SFP28 STACK Transceiver
type-2DOT5GBASE-T(263),                                   -- 2dot5G Base-T Port
type-QSFP28-100GBASE-SWDM4(264),                          -- 100BASE-SWDM4 QSFP28 Optical Transceiver
type-QSFP28-100GBASE-eSWDM4(265),                         -- 100BASE-eSWDM4 QSFP28 Optical Transceiver
type-SFP-PLUS-10GBASE-T(266),                             -- 10GBASE-T SFP+ Transceiver
type-QSFP28-100GBASE-eSR4(267),                           -- 100BASE-eSR4 QSFP28 Optical Transceiver
type-QSFP28-100GBASE-BIDI(268),                           -- 100GBASE-BIDI QSFP28 Optical Transceiver
type-QSFP28-100GBASE-WDM2(269),                           -- 100GBASE-WDM2 QSFP28 Optical Transceiver
type-SFP28-25GBASE-LR(270),                               -- 25GBASE-LR SFP28 Optical Transceiver
type-CFP2-100GBASE-ER4(271),                              -- 100GBASE-ER4 CFP2 Optical Transceiver
type-CFP2-DCO-200GBASE-ZR(272),                           -- 200GBASE-ZR CFP2-DCO Optical Transceiver
type-CFP2-100GBASE-ER4L(273),                             -- 100GBASE-ER4L CFP2 Optical Transceiver
type-SFP-16GFC-SW(274),                                   -- SFP 16G FC Optical Transceiver short wave
type-SFP-16GFC-LW(275),                                   -- SFP 16G FC Optical Transceiver long wave
type-SFP-32GFC-SW(276),                                   -- SFP 32G FC Optical Transceiver short wave
type-SFP-32GFC-LW(277),                                   -- SFP 32G FC Optical Transceiver long wave
type-XFP-10GBASE-PR-D3(278),                              -- XFP 10GBase PR-D3 Optical Transceiver
type-SFP-10GBASE-PRX-D3(279),                             -- XFP 10GBase PRX-D3 Optical Transceiver
type-QSFP28-UNKNOWN(281),                                 -- Unknown QSFP28 Transceiver
type-SFP28-UNKNOWN(282),                                  -- Unknown SFP28 Transceiver
type-SFP28-NO-CONNECTOR(283),                             -- SFP28 No Connector
type-SFP-PLUS-9-8GCRPI-IR(284),                           -- 9.8GCRPI-IR SFP+ Transceiver
type-SFP-PLUS-9-8GCRPI-LR(285),                           -- 9.8GCRPI-LR SFP+ Transceiver
type-QSFP28-50GBASE-PAM4-LR(287),                         -- 50GBASE-PAM4-LR QSFP28 Optical Transceiver
type-10GBASE-BIDI-SFP(288),                               -- 10GBASE SFP+ BIDI Optical Transceiver
type-10GBASE-BIDI-U-SFP-PLUS(291),                        -- 10GBASE SFP+ BIDI Up Optical Transceiver
type-10GBASE-BIDI-D-SFP-PLUS(292),                        -- 10GBASE SFP+ BIDI Down Optical Transceiver
type-QSFPDD-STACK-CONNECTOR(293),                         -- QSFPDD-STACK-Transceiver
type-QSFPDD-400GBASE-SR8(294),                            -- 400GBASE-SR8  QSFP-DD Optical Transceiver
type-QSFP28-100GBASE-ZR2(295),                            -- 100GBASE-ZR2 QSFP28 Optical Transceiver
type-QSFP28-50GBASE-ER(296),                              -- 50GBASE ER QSFP28 Optical Transceiver Module
type-SFP28-25GBASE-eLR(297),                              -- 25GBASE-eLR SFP28 Optical Transceiver
type-QSFP28-100GBASE-ER4-NO-FEC(298),                     -- 100GBASE-ER4 QSFP28 Optical Transceiver Module
type-QSFP28-100GBASE-ZR4(299),                            -- 100GBASE-ZR4 QSFP28 Optical Transceiver Module

type-QSFPDD-400GBASE-FR4(300),                            -- 400GBASE-FR4 QSFP-DD Optical Transceiver
type-QSFP56-200GBASE-FR4(301),                            -- 200GBASE-FR4 QSFP-56 Optical Transceiver
type-QSFP56-200GBASE-SR4(302),                            -- 200GBASE-SR4 QSFP-56 Optical Transceiver
type-QSFP56-200GBASE-AOC(303),                            -- 200GBASE-AOC QSFP-56 Active Optical Cable
type-DSFP-100GBASE-AOC(304),                              -- 100GBASE-AOC DSFP Active Optical Cable
type-SFP28-25GBASE-CSR(305),                              -- 25GBASE-CSR SFP28 Optical Transceiver
type-QSFPDD-UNKNOWN(306),                                 -- Unknown QSFPDD Transceiver
type-QSFPDD-NO-CONNECTOR(307),                            -- QSFPDD No Connector
type-DSFP-UNKNOWN(308),                                   -- Unknown DSFP Transceiver
type-DSFP-NO-CONNECTOR(309),                              -- DSFP No Connector
type-QSFPDD-400GBASE-ZR(310),                             -- 400GBASE-ZR QSFP-DD Optical Transceiver
type-QSFPDD-400GBASE-LR8(311),                            -- 400GBASE-LR8 QSFP-DD Optical Transceiver
type-QSFP56-STACK-CONNECTOR(312),                         -- QSFP56-STACK-Transceiver
type-QSFP56-UNKNOWN(313),                                 -- Unknown QSFP56 Transceiver
type-QSFP56-NO-CONNECTOR(314),                            -- QSFP56 No Connector
type-DSFP-STACK-CONNECTOR(315),                           -- DSFP-STACK-Transceiver
type-QSFP28-100GBASE-DR1(316),                            -- 100GBASE-DR1 QSFP28 Optical Transceiver
type-QSFP28-100GBASE-FR1(317),                            -- 100GBASE-FR1 QSFP28 Optical Transceiver
type-SFP-PLUS-10GBASE-EPON-OLT-PR30(318),                 -- 10G BASE SFP+ EPON OLT PR30 Optical Transceiver
type-SFP-PLUS-10GBASE-EPON-OLT-PR40(319),                 -- 10G BASE SFP+ EPON OLT PR40 Optical Transceiver
type-SFP-GPON-ONU-STICK-BP-SM1310-I(320),                 -- SFP GPON Stick Optical Transceiver
type-QSFPDD-400GBASE-LR4(321),                            -- 400GBASE-LR4 QSFP-DD Optical Transceiver
type-QSFP-PLUS-40GBASE-LX4(322),                          -- 40GBASE-LX4 QSFP+ Optical Transceiver
type-QSFPDD-400GBASE-DR4(323),                            -- 400GBASE-DR4 QSFP-DD Optical Transceiver
type-SFP-PLUS-XGPON-COMBO-C-PLUS(324),                    -- XGPON GPON COMBO C PLUS Optical Transceiver
type-SFP-PLUS-XGSPON-COMBO-C-PLUS(325),                   -- XGSPON GPON COMBO C PLUS Optical Transceiver
type-SFP-PLUS-XGSPON-OLT-N2(326),                         -- XGSPON N2 OLT Optical Transceiver
type-SFP-GPON-ONU-C-PLUS-D(328),                          -- GPON C PLUS ONU Optical Transceiver
type-SFP-PLUS-10G-EPON-ONU-PR40(329),                     -- 10G EPON PR40 ONU Optical Transceiver
type-SFP-PLUS-XGPON-ONU-N-E(330),                         -- XGPON N AND E ONU Optical Transceiver
type-SFP-PLUS-10G-EPON-ONU-PR30(331),                     -- 10G EPON PR30 ONU Optical Transceiver
type-SFP-PLUS-XGSPON-ONU-N-E(332),                        -- XGSPON N AND E ONU Optical Transceiver
type-SFP-GPON-ONU-B-PLUS(333),                            -- GPON B PLUS ONU Optical Transceiver
type-SFP-2500BASE-LX10-I(334),                            -- 2500BASE-LX10 SFP Optical Transceiver
type-QSFP56-100GBASE-AOC(335),                             -- 100GBASE-AOC QSFP56 Active Optical Cable
type-QSFPDD-TO-8SFP56-STACK-CONNECTOR(336),               -- QSFPDD to 8SFP56 STACK Transceiver
type-QSFP56-TO-2QSFP56-STACK-CONNECTOR(337),              -- QSFP56 to 2QSFP56 STACK Transceiver
type-QSFP56-TO-2QSFP56-ACTIVE-OPTICAL-CABLE(338),         -- QSFP56 to 2QSFP56 AOC
type-SFP56-STACK-CONNECTOR(339),                          -- SFP56 STACK Transceiver
type-SFP-1000BASE-PoE(340),                               -- 1000BASE SFP PoE Optical Transceiver
type-SFP-PLUS-10GBASE-PoE(341),                           -- 10GBASE SFP+ PoE Optical Transceiver
type-QSFPDD-TO-4QSFP56-STACK-CONNECTOR(342),              -- QSFPDD to 4QSFP56 STACK Transceiver
type-QSFPDD-400GBASE-AOC(343),                            -- 400GBASE-AOC QSFP-DD Active Optical Cable
type-QSFPDD-TO-2QSFP56-ACTIVE-OPTICAL-CABLE(344),         -- QSFPDD to 2 QSFP56 AOC
type-QSFPDD-TO-4QSFP56-ACTIVE-OPTICAL-CABLE(345),         -- QSFPDD to 4 QSFP56 AOC
type-QSFPDD-TO-2QSFP56-STACK-CONNECTOR(346),              -- QSFPDD to 2 QSFP56 STACK Transceiver
type-QSFP56-ACTIVE-COPPER-CONNECTOR(347),                 -- QSFP56 Active COPPER Transceiver
type-QSFP56-100GBASE-STACK-CONNECTOR(348),                -- 100GBASE QSFP56 STACK Transceiver
type-QSFP112-400GBASE-SR4(349),                           -- 400GBASE-SR4 QSFP-112 Optical Transceiver
type-QSFP112-400GBASE-DR4(350),                           -- 400GBASE-DR4 QSFP-112 Optical Transceiver
type-QSFP112-400GBASE-FR4(351),                           -- 400GBASE-FR4 QSFP-112 Optical Transceiver
type-1000BASE-BIDI-D-CSFP(352),                           -- 1000BASE  CSFP BIDI Down Optical Transceiver
type-QSFPDD-400GBASE-SR4(353),                            -- 400GBASE-SR4 QSFP-DD Optical Transceiver
type-QSFP28-100GBASE-LR1(356),                            -- 100GBASE-LR1 QSFP28 Optical Transceiver
type-QSFPDD-400GBASE-VR4(357),                            -- 400GBASE-VR4 QSFP-DD Optical Transceiver
type-QSFPDD-400GBASE-PLR4(358),                           -- 400GBASE-PLR4 QSFP-DD Optical Transceiver
type-QSFP112-400GBASE-VR4(359),                           -- 400GBASE-VR4 QSFP-112 Optical Transceiver
type-E1-TO-BNC-RJ45-SMB-CONNECTOR(360),                   -- E1 TO BNC OR RJ45 OR SMB Transceiver
type-QSFPDD-400GBASE-ZR-PLUS(361),                        -- 400GBASE-ZR+ QSFP-DD Optical Transceiver
type-QSFP28-100GBASE-ZR(362),                             -- 100GBASE-ZR QSFP28 Optical Transceiver
type-QSFP112-NO-CONNECTOR(363),                           -- QSFP112 No Connector
type-QSFP112-UNKNOWN(364),                                -- Unknown QSFP112 Transceiver
type-QSFP112-400GBASE-AOC(365),                           -- 400GBASE-AOC QSFP112 Active Optical Cable
type-QSFP112-400GBASE-STACK-CONNECTOR(366),               -- 400GBASE QSFP112 STACK Transceiver
type-OSFP800-800G-VR8-MM850-MPO(367),                     -- 800G-VR8-MM850-MPO OSFP800 Optical Transceiver
type-OSFP800-800G-VR8-MM850-DMPO(368),                    -- 800G-VR8-MM850-DMPO OSFP800 Optical Transceiver
type-OSFP800-800G-DR8-SM1310-DMPO(369),                   -- 800G-DR8-SM1310-DMPO OSFP800 Optical Transceiver
type-OSFP800-800G-2FR4-WDM1300-DLC(370),                  -- 800G-2FR4-WDM1300-DLC OSFP800 Optical Transceiver
type-QSFPDD-800G-VR8-MM850-MPO(371),                      -- 800G-VR8-MM850-MPO QSFPDD Optical Transceiver
type-QSFPDD-800G-VR8-MM850-DMPO(372),                     -- 800G-VR8-MM850-DMPO QSFPDD Optical Transceiver
type-QSFPDD-800G-DR8-SM1310-DMPO(373),                    -- 800G-DR8-SM1310-DMPO QSFPDD Optical Transceiver
type-QSFPDD-800G-2FR4-WDM1300-DLC(374),                   -- 800G-2FR4-WDM1300-DLC QSFPDD Optical Transceiver
type-QSFP112-400G-AOC-1X2(375),                           -- 400G-AOC-1X2 QSFP112 Optical Transceiver
type-QSFP112-200GBASE-AOC(376),                           -- 200GBASE-AOC QSFP112 Optical Transceiver
type-QSFP112-400G-SR8-MM850(377),                         -- 400G-SR8-MM850 QSFP112 Optical Transceiver
type-OSFP800-NO-CONNECTOR(378),                           -- OSFP800 No Connector
type-OSFP-UNKNOWN(379),                                   -- Unknown OSFP Transceiver
type-QSFPDD800-UNKNOWN(380),                              -- Unknown QSFPDD800 Transceiver
type-QSFPDD800-NO-CONNECTOR(381),                         -- QSFPDD800 No Connector
type-OSFP800-800G-SR8-MPO(382),                           -- 800G-SR8-MPO OSFP800 Optical Transceiver
type-OSFP800-800G-SR8-DMPO(383),                          -- 800G-SR8-DMPO OSFP800 Optical Transceiver
type-OSFP800-800G-DR8-SM1310-DMPO-LPO(384),               -- 800G-DR8-SM1310-DMPO-LPO OSFP800 Optical Transceiver
type-QSFPDD-800G-DR8-SM1310-DMPO-LPO (385),               -- 800G-DR8-SM1310-DMPO-LPO QSFPDD Optical Transceiver
type-QSFP112-400G-DR4-SM1310-LPO(386),                    -- 400G-DR4-SM1310-LPO QSFP112 Transceiver
type-QSFPDD-400GBASE-ER8(387),                            -- 400GBASE-ER8 QSFP-DD Optical Transceiver
type-QSFPDD-400G-eSR8-MM850 (388),                        -- 400G-eSR8-MM850 QSFPDD Optical Transceiver
type-QSFP-100G-eBIDI-MM850(389),                          -- 100G-eBIDI-MM850 QSFP Transceiver
type-QSFPDD-400GBASE-ZR-PLUS-PLUS(390),                   -- 400GBASE-ZR++ QSFP-DD Optical Transceiver
type-SFP-XGSPON-STICK-N2-SM1270-I(391),                   -- XGSPON Stick N2 SM1270 Optical Transceiver
type-SFP-GPON-B-PLUS-D-SM1490-A(392),                     -- GPON OLT B+ Optical Transceiver
type-OSFP800-800GBASE-AOC (393),                          -- 800GBASE-AOC OSFP800 AOC
type-OSFP800-800G-1X2-400G-AOC(394),                      -- OSFP800 800G 1X2 400G AOC,
type-SFP-2500BASE-BIDI-U-SFP-PLUS(395),                   -- 2500BASE SFP BIDI Up Optical Transceiver
type-SFP-2500BASE-BIDI-D-SFP-PLUS(396),                   -- 2500BASE SFP BIDI Down Optical Transceiver
type-QSFP-PLUS-40GBASE-LR4-CWDM(397),                     -- 40GBASE-LR4-CWDM QSFP+ Optical Transceiver
type-SFP-PLUS-10GBASE-LR-CWDM(398),                       -- 10GBASE-LR-CWDM SFP+ Transceiver
type-SFP28-25G-10G-BASE-SR(399)                           -- 25G-10G-BASE-SR SFP28 Optical Transceiver
}

MAX-ACCESS     read-only
STATUS     current
DESCRIPTION
"Normally the port type is the same as its card type.  When there are
different types of ports in one card, use the actual port type."
::= {hh3cLswPortEntry 2}


hh3cLswPortIfindex OBJECT-TYPE
SYNTAX     Integer32
MAX-ACCESS     read-only
STATUS     current
DESCRIPTION
"The value of ifIndex of the port."
::= {hh3cLswPortEntry 3}


hh3cLswPortIsPlugged   OBJECT-TYPE
SYNTAX     INTEGER
{
unplugged(0),
plugged(1)
}

MAX-ACCESS     read-only
STATUS     current
DESCRIPTION
"Port is plugged or not."
::= {hh3cLswPortEntry 4}


-- ==================================================================
--
-- port loopback test table
--
-- ==================================================================

hh3cLswPortLoopbackTable    OBJECT-TYPE
SYNTAX     SEQUENCE OF Hh3cLswPortLoopbackEntry
MAX-ACCESS     not-accessible
STATUS     current
DESCRIPTION
"Port loopback test table."
::= {hh3cLswSlotConf 6}

hh3cLswPortLoopbackEntry  OBJECT-TYPE
SYNTAX     Hh3cLswPortLoopbackEntry
MAX-ACCESS     not-accessible
STATUS     current
DESCRIPTION
"Port loopback test table entry."
AUGMENTS    {hh3cLswPortEntry }
::= {hh3cLswPortLoopbackTable 1}

Hh3cLswPortLoopbackEntry ::= SEQUENCE
{
hh3cLswPortLoopbackIsSupport        INTEGER,
hh3cLswPortLoopbackOperate          INTEGER,
hh3cLswPortLoopbackResult           INTEGER,
hh3cLswPortLoopbackAutoStopSupport  INTEGER,
hh3cLswPortLoopbackRemoteResult     INTEGER,
hh3cLswPortLoopbackLocalResult      INTEGER,
hh3cLswPortLoopbackInternalResult   INTEGER,
hh3cLswPortLoopbackExternalResult   INTEGER
}

hh3cLswPortLoopbackIsSupport  OBJECT-TYPE
SYNTAX     INTEGER
{
neither(1),
both(2),
internalOnly(3),
externalOnly(4)
}
MAX-ACCESS  read-only
STATUS      current
DESCRIPTION
"The loopback type can be supported by current port."
::= {hh3cLswPortLoopbackEntry 1}

hh3cLswPortLoopbackOperate OBJECT-TYPE
SYNTAX     INTEGER
{
stopRemoteOrLocalLoopBack(0),
internalLoopback(1),
externalLoopback(2),
remoteLoopback(3),
localLoopback(4)
}
MAX-ACCESS     read-write
STATUS     current
DESCRIPTION
"Port loopback operate type.  Read operation not supported."
::= {hh3cLswPortLoopbackEntry 2}

hh3cLswPortLoopbackResult OBJECT-TYPE
SYNTAX     INTEGER
{
testing (0),
testok (1),
testfailed (2)
}
MAX-ACCESS     read-only
STATUS     current
DESCRIPTION
"Loopback test result of the port, used for checking if the test is successful.
Only after the testing will the query value on the node make sense."
::= {hh3cLswPortLoopbackEntry 3}

hh3cLswPortLoopbackAutoStopSupport  OBJECT-TYPE
SYNTAX     INTEGER
{
support(1),
notSupport(2)
}
MAX-ACCESS  read-only
STATUS      current
DESCRIPTION
"Whether this port support NEED-MANNUL-NOLOOP mode or not."
::= {hh3cLswPortLoopbackEntry 4}

hh3cLswPortLoopbackRemoteResult OBJECT-TYPE
SYNTAX     INTEGER
{
loopbackTestInit(0),
loopbackTesting(1),
loopbackTestSuccessed (2),
loopbackTestFailed (3),
loopbackTestTestAndFailed (4)
}
MAX-ACCESS     read-write
STATUS     current
DESCRIPTION
"The remote loopback test result of the port, used for checking if the
test is successful.  Only after the testing will the query value on
the node make sense."
::= {hh3cLswPortLoopbackEntry 5}

hh3cLswPortLoopbackLocalResult OBJECT-TYPE
SYNTAX     INTEGER
{
loopbackTestInit(0),
loopbackTesting(1),
loopbackTestSuccessed (2),
loopbackTestFailed (3),
loopbackTestTestAndFailed (4)
}
MAX-ACCESS     read-write
STATUS     current
DESCRIPTION
"The local loopback test result of the port, used for checking if the
test is successful.  Only after the testing will the query value on the
node make sense."
::= {hh3cLswPortLoopbackEntry 6}

hh3cLswPortLoopbackInternalResult OBJECT-TYPE
SYNTAX     INTEGER
{
loopbackTestInit(0),
loopbackTesting(1),
loopbackTestSuccessed (2),
loopbackTestFailed (3),
loopbackTestTestAndFailed (4)
}
MAX-ACCESS     read-write
STATUS     current
DESCRIPTION
"The internal loopback test result of the port, used for checking if
the test is successful.  Only after the testing will the query value
on the node make sense."
::= {hh3cLswPortLoopbackEntry 7}

hh3cLswPortLoopbackExternalResult OBJECT-TYPE
SYNTAX     INTEGER
{
loopbackTestInit(0),
loopbackTesting(1),
loopbackTestSuccessed (2),
loopbackTestFailed (3),
loopbackTestTestAndFailed (4)
}
MAX-ACCESS     read-write
STATUS     current
DESCRIPTION
"The external loopback test result of the port, used for checking if the
test is successful.  Only after the testing will the query value on the
node make sense."
::= {hh3cLswPortLoopbackEntry 8}

-- ==================================================================
-- Fabric table
-- ==================================================================
hh3cLswFabricTable  OBJECT-TYPE
SYNTAX          SEQUENCE OF Hh3cLswFabricEntry
MAX-ACCESS      not-accessible
STATUS          current
DESCRIPTION     "This table contains the information of fabric."
::= {hh3cLswSlotConf 7}

hh3cLswFabricEntry  OBJECT-TYPE
SYNTAX          Hh3cLswFabricEntry
MAX-ACCESS      not-accessible
STATUS          current
DESCRIPTION     "An entry in hh3cLswFabricTable."
INDEX           {
hh3cLswFrameIndex,
hh3cLswSlotIndex,
hh3cLswSubslotIndex,
hh3cLswFabricChannelIndex
}
::= {hh3cLswFabricTable 1}

Hh3cLswFabricEntry ::= SEQUENCE {
hh3cLswFabricChannelIndex   Integer32,
hh3cLswFabricUtilIn         Integer32,
hh3cLswFabricUtilOut        Integer32,
hh3cLswFabricPeakIn         Integer32,
hh3cLswFabricPeakInTime     DateAndTime,
hh3cLswFabricPeakOut        Integer32,
hh3cLswFabricPeakOutTime    DateAndTime
}

hh3cLswFabricChannelIndex   OBJECT-TYPE
SYNTAX          Integer32
MAX-ACCESS      not-accessible
STATUS          current
DESCRIPTION
"The channel number of fabric."
::= {hh3cLswFabricEntry 1}

hh3cLswFabricUtilIn    OBJECT-TYPE
SYNTAX          Integer32 (0..100)
UNITS           "one percent"
MAX-ACCESS      read-only
STATUS          current
DESCRIPTION
"Ingress utilization of fabric."
::= {hh3cLswFabricEntry 2}

hh3cLswFabricUtilOut    OBJECT-TYPE
SYNTAX          Integer32 (0..100)
UNITS           "one percent"
MAX-ACCESS      read-only
STATUS          current
DESCRIPTION
"Egress utilization of fabric."
::= {hh3cLswFabricEntry 3}

hh3cLswFabricPeakIn     OBJECT-TYPE
SYNTAX          Integer32 (0..100)
UNITS           "one percent"
MAX-ACCESS      read-only
STATUS          current
DESCRIPTION
"Ingress peak of utilization for fabric."
::= {hh3cLswFabricEntry 4}

hh3cLswFabricPeakInTime OBJECT-TYPE
SYNTAX          DateAndTime
MAX-ACCESS      read-only
STATUS          current
DESCRIPTION
"Ingress peak time of utilization for fabric."
::= {hh3cLswFabricEntry 5}

hh3cLswFabricPeakOut    OBJECT-TYPE
SYNTAX          Integer32 (0..100)
UNITS           "one percent"
MAX-ACCESS      read-only
STATUS          current
DESCRIPTION
"Egress peak of utilization for fabric."
::= {hh3cLswFabricEntry 6}

hh3cLswFabricPeakOutTime    OBJECT-TYPE
SYNTAX          DateAndTime
MAX-ACCESS      read-only
STATUS          current
DESCRIPTION
"Egress peak time of utilization for fabric."
::= {hh3cLswFabricEntry 7}

-- ==================================================================
-- For reserving
-- ==================================================================
hh3cLswNetworkHealthMonitor  OBJECT IDENTIFIER ::= { hh3cLswSlotConf 8 }

hh3cLswExtendModelTable OBJECT-TYPE
SYNTAX          SEQUENCE OF Hh3cLswExtendModelEntry
MAX-ACCESS      not-accessible
STATUS          current
DESCRIPTION
"This table contains the extended device models supported by the
device.  Examples of extended devices include PEXs and firewall
modules."
::= {hh3cLswSlotConf 9}

hh3cLswExtendModelEntry OBJECT-TYPE
SYNTAX      Hh3cLswExtendModelEntry
MAX-ACCESS  not-accessible
STATUS      current
DESCRIPTION
"This entry contains information about an extended device model."
INDEX
{
hh3cLswExtendModelIndex
}
::= { hh3cLswExtendModelTable 1 }

Hh3cLswExtendModelEntry ::= SEQUENCE
{
hh3cLswExtendModelIndex   Integer32,
hh3cLswExtendModelDesc    DisplayString
}

hh3cLswExtendModelIndex OBJECT-TYPE
SYNTAX          Integer32 (1..2147483647)
MAX-ACCESS      not-accessible
STATUS          current
DESCRIPTION
"Index of the extended device model."
::= {hh3cLswExtendModelEntry 1}

hh3cLswExtendModelDesc OBJECT-TYPE
SYNTAX          DisplayString (SIZE(0..255))
MAX-ACCESS      read-only
STATUS          current
DESCRIPTION
"Extended device model.  Examples of extended devices include PEXs and
firewall modules."
::= {hh3cLswExtendModelEntry 2}

-- ==================================================================
-- Cpu table
-- ==================================================================
hh3cLswCpuTable  OBJECT-TYPE
SYNTAX          SEQUENCE OF Hh3cLswCpuEntry
MAX-ACCESS      not-accessible
STATUS          current
DESCRIPTION     "Cpu description table."
::= {hh3cLswSlotConf 10}

hh3cLswCpuEntry    OBJECT-TYPE
SYNTAX     Hh3cLswCpuEntry
MAX-ACCESS     not-accessible
STATUS     current
DESCRIPTION
"CPU description table entry."
INDEX { hh3cLswFrameIndex, hh3cLswSlotIndex, hh3cLswCpuIndex }
::= {hh3cLswCpuTable 1}

Hh3cLswCpuEntry ::= SEQUENCE
{
hh3cLswCpuIndex                 Integer32,
hh3cLswCpuEntityIndex           Integer32,
hh3cLswCpuRatio                 Unsigned32,
hh3cLswCpuSoftwareVersion       DisplayString,
hh3cLswCpuAdminStatus           INTEGER,
hh3cLswCpuOperStatus            INTEGER,
hh3cLswCpuPhyMemory             CounterBasedGauge64,
hh3cLswCpuMemory                CounterBasedGauge64,
hh3cLswCpuMemoryUsed            CounterBasedGauge64,
hh3cLswCpuMemoryRatio           Unsigned32,
hh3cLswCpuUsageMinorThreshold      Unsigned32,
hh3cLswCpuUsageSevereThreshold     Unsigned32,
hh3cLswCpuUsageRecoverThreshold     Unsigned32,
hh3cLswCpuMemoryFree                CounterBasedGauge64,
hh3cLswCpuMemoryFreeRatio           Unsigned32,
hh3cLswCpuMemoryHighTotal        CounterBasedGauge64,
hh3cLswCpuMemoryHighFree         CounterBasedGauge64,
hh3cLswCpuMemoryLowTotal         CounterBasedGauge64,
hh3cLswCpuMemoryLowFree          CounterBasedGauge64,
hh3cLswCpuMemoryVmallocTotal     CounterBasedGauge64,
hh3cLswCpuMemoryVmallocUsed      CounterBasedGauge64,
hh3cLswCpuMemoryVmallocChunk     CounterBasedGauge64,
hh3cLswCpuMemoryCommitLimit      CounterBasedGauge64,
hh3cLswCpuMemoryCommittedAs      CounterBasedGauge64,
hh3cLswCpuMemoryThresholdUnit       INTEGER,
hh3cLswCpuMemorySecureThreshold   Unsigned32,
hh3cLswCpuMemoryEarlyWarningThreshold    Unsigned32,
hh3cLswCpuMemoryNormalThreshold     Unsigned32,
hh3cLswCpuMemoryMinorThreshold      Unsigned32,
hh3cLswCpuMemorySevereThreshold     Unsigned32,
hh3cLswCpuMemoryCriticalThreshold   Unsigned32,
hh3cLswCpuMemoryCurrentState        INTEGER
}

hh3cLswCpuIndex    OBJECT-TYPE
SYNTAX     Integer32 (0..2147483647)
MAX-ACCESS     not-accessible
STATUS     current
DESCRIPTION
"CPU index."
::= {hh3cLswCpuEntry 1}

hh3cLswCpuEntityIndex    OBJECT-TYPE
SYNTAX     Integer32
MAX-ACCESS     read-only
STATUS     current
DESCRIPTION
"The entity index of the CPU."
::= {hh3cLswCpuEntry 2}

hh3cLswCpuRatio     OBJECT-TYPE
SYNTAX         Unsigned32 (0..100)
MAX-ACCESS     read-only
STATUS         current
DESCRIPTION
"CPU usage in accuracy of 1%"
::= {hh3cLswCpuEntry 3}

hh3cLswCpuSoftwareVersion    OBJECT-TYPE
SYNTAX               DisplayString (SIZE(0..64))
MAX-ACCESS           read-only
STATUS               current
DESCRIPTION
"Software version of the CPU."
::= {hh3cLswCpuEntry 4}

hh3cLswCpuAdminStatus    OBJECT-TYPE
SYNTAX           INTEGER
{
notInstall  (1),
normal      (2),
fault       (3),
forbidden   (4)
}
MAX-ACCESS       read-only
STATUS           current
DESCRIPTION
"CPU status."
::= {hh3cLswCpuEntry 5}

hh3cLswCpuOperStatus    OBJECT-TYPE
SYNTAX          INTEGER
{
disable (1),
enable  (2),
reset   (3),
test    (4)
}
MAX-ACCESS      read-write
STATUS          current
DESCRIPTION
"CPU operation status."
::= {hh3cLswCpuEntry 6}

hh3cLswCpuPhyMemory    OBJECT-TYPE
SYNTAX CounterBasedGauge64
UNITS "byte"
MAX-ACCESS read-only
STATUS current
DESCRIPTION
"The physical memory on the node."
::= {hh3cLswCpuEntry 7}

hh3cLswCpuMemory    OBJECT-TYPE
SYNTAX CounterBasedGauge64
UNITS "byte"
MAX-ACCESS read-only
STATUS current
DESCRIPTION
"The system memory on the node.

Note that the system memory means the memory that can be used by
the software platform."
::= {hh3cLswCpuEntry 8}

hh3cLswCpuMemoryUsed    OBJECT-TYPE
SYNTAX CounterBasedGauge64
UNITS "byte"
MAX-ACCESS read-only
STATUS current
DESCRIPTION
"The system memory in use on the node.

Note that the system memory means the memory that can be used by
the software platform."
::= {hh3cLswCpuEntry 9}

hh3cLswCpuMemoryRatio    OBJECT-TYPE
SYNTAX Unsigned32 (0..100)
MAX-ACCESS read-only
STATUS current
DESCRIPTION
"The percentage of system memory in use on the node.

Note that the system memory means the memory that can be used by
the software platform."
::= {hh3cLswCpuEntry 10}

hh3cLswCpuUsageMinorThreshold   OBJECT-TYPE
SYNTAX Unsigned32 (1..99)
MAX-ACCESS read-write
STATUS current
DESCRIPTION
"The minor threshold for CPU usage on the node.

When the CPU usage exceeds this threshold, a notification will be sent.
The hh3cLswCpuUsageMinorThreshold must be less than or equal to
the hh3cLswCpuUsageSevereThreshold.
"
::= {hh3cLswCpuEntry 11}

hh3cLswCpuUsageSevereThreshold   OBJECT-TYPE
SYNTAX Unsigned32 (2..100)
MAX-ACCESS read-write
STATUS current
DESCRIPTION
"The severe threshold for CPU usage on the node.

When the CPU usage exceeds this threshold, a notification will be sent.
"
::= {hh3cLswCpuEntry 12}

hh3cLswCpuUsageRecoverThreshold   OBJECT-TYPE
SYNTAX Unsigned32 (0..98)
MAX-ACCESS read-write
STATUS current
DESCRIPTION
"The recovery threshold for CPU usage.

When the CPU usage falls down to this threshold, a notification is sent.
The hh3cLswCpuUsageRecoverThreshold must be less than or equal to
the hh3cLswCpuUsageMinorThreshold.
"
::= {hh3cLswCpuEntry 13}

hh3cLswCpuMemoryFree    OBJECT-TYPE
SYNTAX CounterBasedGauge64
UNITS "byte"
MAX-ACCESS read-only
STATUS current
DESCRIPTION
"The amount of free memory on the node."
::= {hh3cLswCpuEntry 14}

hh3cLswCpuMemoryFreeRatio    OBJECT-TYPE
SYNTAX Unsigned32 (0..100)
MAX-ACCESS read-only
STATUS current
DESCRIPTION
"The percentage of free memory on the node."
::= {hh3cLswCpuEntry 15}

hh3cLswCpuMemoryHighTotal    OBJECT-TYPE
SYNTAX CounterBasedGauge64
MAX-ACCESS read-only
STATUS current
DESCRIPTION
"The total high-memory on the node "
::= {hh3cLswCpuEntry 16}

hh3cLswCpuMemoryHighFree    OBJECT-TYPE
SYNTAX CounterBasedGauge64
MAX-ACCESS read-only
STATUS current
DESCRIPTION
"The free high-memory on the node "
::= {hh3cLswCpuEntry 17}

hh3cLswCpuMemoryLowTotal    OBJECT-TYPE
SYNTAX CounterBasedGauge64
MAX-ACCESS read-only
STATUS current
DESCRIPTION
"The total low-memory on the node "
::= {hh3cLswCpuEntry 18}

hh3cLswCpuMemoryLowFree    OBJECT-TYPE
SYNTAX CounterBasedGauge64
MAX-ACCESS read-only
STATUS current
DESCRIPTION
"The free low-memory on the node "
::= {hh3cLswCpuEntry 19}

hh3cLswCpuMemoryVmallocTotal    OBJECT-TYPE
SYNTAX CounterBasedGauge64
MAX-ACCESS read-only
STATUS current
DESCRIPTION
"The total Vmalloc memory on the node "
::= {hh3cLswCpuEntry 20}

hh3cLswCpuMemoryVmallocUsed    OBJECT-TYPE
SYNTAX CounterBasedGauge64
MAX-ACCESS read-only
STATUS current
DESCRIPTION
"The used Vmalloc memory on the node "
::= {hh3cLswCpuEntry 21}

hh3cLswCpuMemoryVmallocChunk    OBJECT-TYPE
SYNTAX CounterBasedGauge64
MAX-ACCESS read-only
STATUS current
DESCRIPTION
"The Vmalloc memory in chunk on the node "
::= {hh3cLswCpuEntry 22}

hh3cLswCpuMemoryCommitLimit    OBJECT-TYPE
SYNTAX CounterBasedGauge64
MAX-ACCESS read-only
STATUS current
DESCRIPTION
" The memory that can be allocated on the system(KB)."
::= {hh3cLswCpuEntry 23}

hh3cLswCpuMemoryCommittedAs    OBJECT-TYPE
SYNTAX CounterBasedGauge64
MAX-ACCESS read-only
STATUS current
DESCRIPTION
"The CommittedAs memory on the node "
::= {hh3cLswCpuEntry 24}

hh3cLswCpuMemoryThresholdUnit    OBJECT-TYPE
SYNTAX          INTEGER
{
inMB (1),
inPercentage (2)
}
MAX-ACCESS      read-write
STATUS          current
DESCRIPTION
"The unit of memory threshold."
::= {hh3cLswCpuEntry 25}

hh3cLswCpuMemorySecureThreshold   OBJECT-TYPE
SYNTAX               Unsigned32
MAX-ACCESS           read-write
STATUS               current
DESCRIPTION
"The sufficient-memory.
The unit is set by hh3cLswCpuMemoryThresholdUnit, MB or percentage.

When the free memory exceeds this threshold, a notification will be sent.
The hh3cLswCpuMemorySecureThreshold must be more than
or equal to the hh3cLswCpuMemoryEarlywarningThreshold.
"
::= {hh3cLswCpuEntry 26}

hh3cLswCpuMemoryEarlyWarningThreshold   OBJECT-TYPE
SYNTAX               Unsigned32
MAX-ACCESS           read-write
STATUS               current
DESCRIPTION
"The early-warning threshold for free memory.
The unit is set by hh3cLswCpuMemoryThresholdUnit, MB or percentage.

When the free memory decreases to or below this threshold, a notification will be sent.
The hh3cLswCpuMemoryEarlyWarningThreshold must be more than
or equal to the hh3cLswCpuMemoryNormalThreshold.
"
::= {hh3cLswCpuEntry 27}

hh3cLswCpuMemoryNormalThreshold   OBJECT-TYPE
SYNTAX               Unsigned32
MAX-ACCESS           read-write
STATUS               current
DESCRIPTION
"The normal state threshold for free memory.
The unit is set by hh3cLswCpuMemoryThresholdUnit, MB or percentage.

When the free memory decreases to or below this threshold, a notification will be sent.
The hh3cLswCpuMemoryNormalThreshold must be more than or equal to
the hh3cLswCpuMemoryMinorThreshold.
"
::= {hh3cLswCpuEntry 28}

hh3cLswCpuMemoryMinorThreshold   OBJECT-TYPE
SYNTAX               Unsigned32
MAX-ACCESS           read-write
STATUS               current
DESCRIPTION
"The minor alarm threshold for free memory.
The unit is set by hh3cLswCpuMemoryThresholdUnit, MB or percentage.

When the free memory decreases to or below this threshold, a notification will be sent.
The hh3cLswCpuMemoryMinorThreshold must be more than or equal to
the hh3cLswCpuMemorySevereThreshold.
"
::= {hh3cLswCpuEntry 29}

hh3cLswCpuMemorySevereThreshold   OBJECT-TYPE
SYNTAX               Unsigned32
MAX-ACCESS           read-write
STATUS               current
DESCRIPTION
"The severe alarm threshold for free memory.
The unit is set by hh3cLswCpuMemoryThresholdUnit, MB or percentage.

When free memory decreases to or below this threshold, a notification will be sent.
The hh3cLswCpuMemorySevereThreshold must be less than or equal to
the hh3cLswCpuMemoryCriticalThreshold.
"
::= {hh3cLswCpuEntry 30}

hh3cLswCpuMemoryCriticalThreshold   OBJECT-TYPE
SYNTAX               Unsigned32
MAX-ACCESS           read-write
STATUS               current
DESCRIPTION
"The critical alarm threshold for free memory.
The unit is set by hh3cLswCpuMemoryThresholdUnit, MB or percentage.

When free memory decreases to or below this threshold, a notification will be sent.
"
::= {hh3cLswCpuEntry 31}

hh3cLswCpuMemoryCurrentState    OBJECT-TYPE
SYNTAX          INTEGER
{
secure (1),
earlywarning (2),
normal (3),
minor (4),
severe (5),
critical (6)
}
MAX-ACCESS      read-only
STATUS          current
DESCRIPTION
"Current status of free memory.

secure
earlywarning
normal
minor
severe
critical
"
::= {hh3cLswCpuEntry 32}

-- ==================================================================
-- Power table
-- ==================================================================
hh3cLswPowerTable  OBJECT-TYPE
SYNTAX          SEQUENCE OF Hh3cLswPowerEntry
MAX-ACCESS      not-accessible
STATUS          current
DESCRIPTION     "Power module description table."
::= {hh3cLswSlotConf 11}

hh3cLswPowerEntry    OBJECT-TYPE
SYNTAX     Hh3cLswPowerEntry
MAX-ACCESS     not-accessible
STATUS     current
DESCRIPTION
"Power module description table entry."
INDEX { hh3cLswFrameIndex, hh3cLswSlotIndex, hh3cLswPowerIndex }
::= {hh3cLswPowerTable 1}

Hh3cLswPowerEntry ::= SEQUENCE
{
hh3cLswPowerIndex                  Integer32,
hh3cLswPowerSerialNumber           SnmpAdminString
}

hh3cLswPowerIndex    OBJECT-TYPE
SYNTAX     Integer32
MAX-ACCESS     read-only
STATUS     current
DESCRIPTION
"Power module index."
::= {hh3cLswPowerEntry 1}

hh3cLswPowerSerialNumber    OBJECT-TYPE
SYNTAX     SnmpAdminString (SIZE(0..32))
MAX-ACCESS     read-only
STATUS     current
DESCRIPTION
"Power module serial number."
::= {hh3cLswPowerEntry 2}

-- ==================================================================
-- Fan table
-- ==================================================================
hh3cLswFanTable  OBJECT-TYPE
SYNTAX          SEQUENCE OF Hh3cLswFanEntry
MAX-ACCESS      not-accessible
STATUS          current
DESCRIPTION     "Fan tray description table."
::= {hh3cLswSlotConf 12}

hh3cLswFanEntry    OBJECT-TYPE
SYNTAX     Hh3cLswFanEntry
MAX-ACCESS     not-accessible
STATUS     current
DESCRIPTION
"Fan tray description table entry."
INDEX { hh3cLswFrameIndex, hh3cLswSlotIndex, hh3cLswFanIndex }
::= {hh3cLswFanTable 1}

Hh3cLswFanEntry ::= SEQUENCE
{
hh3cLswFanIndex                  Integer32,
hh3cLswFanSerialNumber           SnmpAdminString
}

hh3cLswFanIndex    OBJECT-TYPE
SYNTAX     Integer32
MAX-ACCESS     read-only
STATUS     current
DESCRIPTION
"Fan tray index."
::= {hh3cLswFanEntry 1}

hh3cLswFanSerialNumber    OBJECT-TYPE
SYNTAX     SnmpAdminString (SIZE(0..32))
MAX-ACCESS     read-only
STATUS     current
DESCRIPTION
"Fan tray serial number."
::= {hh3cLswFanEntry 2}

-- ==================================================================
-- Transceiver table
-- ==================================================================
hh3cLswTransceiverTable  OBJECT-TYPE
SYNTAX          SEQUENCE OF Hh3cLswTransceiverEntry
MAX-ACCESS      not-accessible
STATUS          current
DESCRIPTION     "Transceiver description table."
::= {hh3cLswSlotConf 13}

hh3cLswTransceiverEntry    OBJECT-TYPE
SYNTAX     Hh3cLswTransceiverEntry
MAX-ACCESS     not-accessible
STATUS     current
DESCRIPTION
"Transceiver description table entry."
INDEX {
hh3cLswFrameIndex,
hh3cLswSlotIndex,
hh3cLswSubslotIndex,
hh3cLswTransceiverIndex
}
::= {hh3cLswTransceiverTable 1}

Hh3cLswTransceiverEntry ::= SEQUENCE
{
hh3cLswTransceiverIndex                  Integer32,
hh3cLswTransceiverSerialNumber           SnmpAdminString
}

hh3cLswTransceiverIndex    OBJECT-TYPE
SYNTAX     Integer32
MAX-ACCESS     read-only
STATUS     current
DESCRIPTION
"Transceiver index."
::= {hh3cLswTransceiverEntry 1}

hh3cLswTransceiverSerialNumber    OBJECT-TYPE
SYNTAX     SnmpAdminString (SIZE(0..32))
MAX-ACCESS     read-only
STATUS     current
DESCRIPTION
"Transceiver serial number."
::= {hh3cLswTransceiverEntry 2}

-- ==================================================================
-- cpu group table
-- ==================================================================
hh3cLswCpuGroupTable  OBJECT-TYPE
SYNTAX          SEQUENCE OF Hh3cLswCpuGroupEntry
MAX-ACCESS      not-accessible
STATUS          current
DESCRIPTION     "CPU group table."
::= {hh3cLswSlotConf 14}

hh3cLswCpuGroupEntry    OBJECT-TYPE
SYNTAX         Hh3cLswCpuGroupEntry
MAX-ACCESS     not-accessible
STATUS         current
DESCRIPTION
"CPU group table entry."
INDEX {
hh3cLswFrameIndex,
hh3cLswSlotIndex,
hh3cLswCpuIndex,
hh3cLswCpuGroupIndex
}
::= {hh3cLswCpuGroupTable 1}

Hh3cLswCpuGroupEntry ::= SEQUENCE
{
hh3cLswCpuGroupIndex          Integer32,
hh3cLswCpuGroupName           OCTET STRING,
hh3cLswCurrentCpuUsage        Unsigned32,
hh3cLswLast1mCpuUsage         Unsigned32,
hh3cLswLast5mCpuUsage         Unsigned32
}

hh3cLswCpuGroupIndex     OBJECT-TYPE
SYNTAX      Integer32
MAX-ACCESS  read-only
STATUS      current
DESCRIPTION
"CPU group index."
::= {hh3cLswCpuGroupEntry 1}

hh3cLswCpuGroupName     OBJECT-TYPE
SYNTAX         OCTET STRING (SIZE(0..64))
MAX-ACCESS     read-only
STATUS         current
DESCRIPTION
"Name of a CPU group."
::= {hh3cLswCpuGroupEntry 2}

hh3cLswCurrentCpuUsage     OBJECT-TYPE
SYNTAX         Unsigned32
MAX-ACCESS     read-only
STATUS         current
DESCRIPTION
"CPU usage in last 5 seconds, accurate to 1%."
::= {hh3cLswCpuGroupEntry 3}

hh3cLswLast1mCpuUsage      OBJECT-TYPE
SYNTAX        Unsigned32
MAX-ACCESS    read-only
STATUS        current
DESCRIPTION
"CPU usage in last 1 minute, accurate to 1%."
::= {hh3cLswCpuGroupEntry 4}

hh3cLswLast5mCpuUsage     OBJECT-TYPE
SYNTAX        Unsigned32
MAX-ACCESS    read-only
STATUS        current
DESCRIPTION
"CPU usage in last 5 minutes, accurate to 1%."
::= {hh3cLswCpuGroupEntry 5}

-- ==================================================================
-- Core table
-- ==================================================================
hh3cLswCoreTable  OBJECT-TYPE
SYNTAX          SEQUENCE OF Hh3cLswCoreEntry
MAX-ACCESS      not-accessible
STATUS          current
DESCRIPTION     "Core description table."
::= {hh3cLswSlotConf 15}

hh3cLswCoreEntry    OBJECT-TYPE
SYNTAX     Hh3cLswCoreEntry
MAX-ACCESS     not-accessible
STATUS     current
DESCRIPTION
"Core description table entry."
INDEX
{
hh3cLswFrameIndex,
hh3cLswSlotIndex,
hh3cLswCpuIndex,
hh3cLswCoreIndex
}
::= {hh3cLswCoreTable 1}

Hh3cLswCoreEntry ::= SEQUENCE
{
hh3cLswCoreIndex            Integer32,
hh3cLswCoreUsageInLast5Sec  Unsigned32,
hh3cLswCoreUsageInLast1Min  Unsigned32,
hh3cLswCoreUsageInLast5Min  Unsigned32,
hh3cLswCoreThreshold        Unsigned32,
hh3cLswCoreState            INTEGER,
hh3cLswCoreMinorThreshold   Unsigned32,
hh3cLswCoreRecoveryThreshold  Unsigned32
}

hh3cLswCoreIndex   OBJECT-TYPE
SYNTAX     Integer32
MAX-ACCESS     read-only
STATUS     current
DESCRIPTION
"Core index."
::= {hh3cLswCoreEntry 1}

hh3cLswCoreUsageInLast5Sec   OBJECT-TYPE
SYNTAX     Unsigned32
MAX-ACCESS     read-only
STATUS     current
DESCRIPTION
"Core usage in last 5 seconds."
::= {hh3cLswCoreEntry 2}

hh3cLswCoreUsageInLast1Min   OBJECT-TYPE
SYNTAX     Unsigned32
MAX-ACCESS     read-only
STATUS     current
DESCRIPTION
"Core usage in last 1 minute."
::= {hh3cLswCoreEntry 3}

hh3cLswCoreUsageInLast5Min   OBJECT-TYPE
SYNTAX     Unsigned32
MAX-ACCESS     read-only
STATUS     current
DESCRIPTION
"Core usage in last 5 minutes."
::= {hh3cLswCoreEntry 4}

hh3cLswCoreThreshold   OBJECT-TYPE
SYNTAX     Unsigned32
MAX-ACCESS     read-write
STATUS     current
DESCRIPTION
"Core usage threshold.
When the core usage decreases to or below this threshold, a notification is sent.
"
::= {hh3cLswCoreEntry 5}

hh3cLswCoreState   OBJECT-TYPE
SYNTAX          INTEGER
{
normal (1),
warning (2)
}
MAX-ACCESS     read-only
STATUS     current
DESCRIPTION
"Last state of core.
normal
warning
"
::= {hh3cLswCoreEntry 6}

hh3cLswCoreMinorThreshold   OBJECT-TYPE
SYNTAX     Unsigned32
MAX-ACCESS     read-write
STATUS     current
DESCRIPTION
"Core usage minor threshold.
When the core usage exceeds this threshold, a notification is sent.
"
::= {hh3cLswCoreEntry 7}

hh3cLswCoreRecoveryThreshold   OBJECT-TYPE
SYNTAX     Unsigned32
MAX-ACCESS     read-write
STATUS     current
DESCRIPTION
"Core usage recovery threshold.
When the core usage falls down to this threshold, a notification is sent.
"
::= {hh3cLswCoreEntry 8}

-- ==================================================================
-- Output-power table
-- ==================================================================
hh3cLswOutputPowerTable  OBJECT-TYPE
SYNTAX          SEQUENCE OF Hh3cLswOutputPowerEntry
MAX-ACCESS      not-accessible
STATUS          current
DESCRIPTION     "Output-power description table."
::= {hh3cLswSlotConf 16}

hh3cLswOutputPowerEntry    OBJECT-TYPE
SYNTAX     Hh3cLswOutputPowerEntry
MAX-ACCESS     not-accessible
STATUS     current
DESCRIPTION
"Output-power description table entry."
INDEX
{
hh3cLswFrameIndex,
hh3cLswSlotIndex,
hh3cLswOutputPowerPortID
}
::= {hh3cLswOutputPowerTable 1}

Hh3cLswOutputPowerEntry ::= SEQUENCE
{
hh3cLswOutputPowerPortID       Integer32,
hh3cLswOutputPowerStatus       INTEGER
}

hh3cLswOutputPowerPortID   OBJECT-TYPE
SYNTAX     Integer32 (1..2147483647)
MAX-ACCESS     read-only
STATUS     current
DESCRIPTION
"Output-power port index."
::= {hh3cLswOutputPowerEntry 1}

hh3cLswOutputPowerStatus   OBJECT-TYPE
SYNTAX          INTEGER
{
disable (1),
normal (2),
open (3),
overvol (4),
undervol (5),
overcur (6),
overpower (7)
}
MAX-ACCESS     read-only
STATUS     current
DESCRIPTION
"Output-power port status.
disable
normal
open
overvol
undervol
overcur
overpower
"
::= {hh3cLswOutputPowerEntry 2}

-- ==================================================================
-- Component table
-- ==================================================================
hh3cComponentTable  OBJECT-TYPE
    SYNTAX          SEQUENCE OF Hh3cComponentEntry
    MAX-ACCESS      not-accessible
    STATUS          current
    DESCRIPTION     "Component description table."
    ::= {hh3cLswSlotConf 17}

hh3cComponentEntry    OBJECT-TYPE
    SYNTAX     Hh3cComponentEntry
    MAX-ACCESS     not-accessible
    STATUS     current
    DESCRIPTION
    "Component description table entry."
    INDEX
    {
        hh3cLswFrameIndex,
        hh3cLswSlotIndex,
        hh3cLswSubslotIndex,
        hh3cComponentClass,
        hh3cComponentID
    }
    ::= {hh3cComponentTable 1}

Hh3cComponentEntry ::= SEQUENCE
{
    hh3cComponentClass       INTEGER,
    hh3cComponentID          Integer32,
    hh3cComponentKeyPos      Unsigned32,
    hh3cComponentBoardName   DisplayString,
    hh3cComponentTypeName    OCTET STRING,
    hh3cComponentTypeCount   OCTET STRING
}

hh3cComponentClass   OBJECT-TYPE
    SYNTAX     INTEGER
    {
          cpu (1),
          forward (2),
          switch (3),
          clock (4),
          memory (5),
          flash (6),
          phychip (7),
          powerC (8),
          invalid (65535)
    }
    MAX-ACCESS     accessible-for-notify
    STATUS     current
    DESCRIPTION
    "Component class.
    cpu,
    forward,
    switch,
    clock,
    memory,
    flash,
    phychip,
    powerC,
    invalid"
    ::= {hh3cComponentEntry 1}

hh3cComponentID   OBJECT-TYPE
    SYNTAX          Integer32(0..65535)
    MAX-ACCESS     accessible-for-notify
    STATUS     current
    DESCRIPTION
    "Component ID."
    ::= {hh3cComponentEntry 2}

hh3cComponentKeyPos   OBJECT-TYPE
    SYNTAX         Unsigned32
    MAX-ACCESS     read-only
    STATUS     current
    DESCRIPTION
    "Key Subscript."
    ::= {hh3cComponentEntry 3}

hh3cComponentBoardName   OBJECT-TYPE
    SYNTAX         DisplayString (SIZE(1..64))
    MAX-ACCESS     read-only
    STATUS     current
    DESCRIPTION
    "Board name."
    ::= {hh3cComponentEntry 4}

hh3cComponentTypeName   OBJECT-TYPE
    SYNTAX         OCTET STRING(SIZE(0..2048))
    MAX-ACCESS     read-only
    STATUS     current
    DESCRIPTION
    "Component type."
    ::= {hh3cComponentEntry 5}

hh3cComponentTypeCount  OBJECT-TYPE
    SYNTAX         OCTET STRING(SIZE(0..2048))
    MAX-ACCESS     read-only
    STATUS     current
    DESCRIPTION
    "Component count."
    ::= {hh3cComponentEntry 6}

-- ==================================================================
-- cpu group usage table
-- ==================================================================
hh3cCpuGroupUsageTable  OBJECT-TYPE
    SYNTAX          SEQUENCE OF Hh3cCpuGroupUsageEntry
    MAX-ACCESS      not-accessible
    STATUS          current
    DESCRIPTION     "CPU group table."
    ::= {hh3cLswSlotConf 18}

hh3cCpuGroupUsageEntry    OBJECT-TYPE
    SYNTAX         Hh3cCpuGroupUsageEntry
    MAX-ACCESS     not-accessible
    STATUS         current
    DESCRIPTION
    "CPU group table entry."
    INDEX {
    hh3cLswFrameIndex,
    hh3cLswSlotIndex,
    hh3cLswCpuIndex,
    hh3cCpuGroupUsageGroupName
    }
    ::= {hh3cCpuGroupUsageTable 1}

Hh3cCpuGroupUsageEntry ::= SEQUENCE
{
    hh3cCpuGroupUsageGroupName              OCTET STRING,
    hh3cCpuGroupUsageSevereThreshold        Unsigned32,
    hh3cCpuGroupUsageMinorThreshold         Unsigned32,
    hh3cCpuGroupUsageRecovThreshold         Unsigned32,
    hh3cCpuGroupUsageInterval               Unsigned32,
    hh3cCpuGroupUsageAverageCpuUsage        Unsigned32,
    hh3cCpuGroupUsageLast5sCpuUsage         Unsigned32,
    hh3cCpuGroupUsageLast1mCpuUsage         Unsigned32,
    hh3cCpuGroupUsageLast5mCpuUsage         Unsigned32,
    hh3cCpuGroupUsageCurrentState           OCTET STRING
}

hh3cCpuGroupUsageGroupName    OBJECT-TYPE
    SYNTAX     OCTET STRING (SIZE(0..64))
    MAX-ACCESS     read-only
    STATUS     current
    DESCRIPTION
    "Name of a CPU group."
    ::= {hh3cCpuGroupUsageEntry 1}

hh3cCpuGroupUsageSevereThreshold   OBJECT-TYPE
    SYNTAX     Unsigned32 (2..100)
    MAX-ACCESS     read-write
    STATUS     current
    DESCRIPTION
    "The severe threshold for CPU group usage on the node.
    When the CPU group usage exceeds this threshold, a notification will be sent."
    ::= {hh3cCpuGroupUsageEntry 2}

hh3cCpuGroupUsageMinorThreshold   OBJECT-TYPE
    SYNTAX     Unsigned32 (1..99)
    MAX-ACCESS     read-write
    STATUS     current
    DESCRIPTION
    "The minor threshold for CPU group usage on the node.
    When the CPU group usage exceeds this threshold, a notification will be sent.
    The value for hh3cCpuGroupUsageMinorThreshold must be less than or equal to that for hh3cCpuGroupUsageSevereThreshold."
    ::= {hh3cCpuGroupUsageEntry 3}

hh3cCpuGroupUsageRecovThreshold   OBJECT-TYPE
    SYNTAX     Unsigned32 (0..98)
    MAX-ACCESS     read-write
    STATUS     current
    DESCRIPTION
    "The recovery threshold for CPU group usage.
    When the CPU group usage falls down to this threshold, a notification is sent.
    The value for hh3cCpuGroupUsageRecovThreshold must be less than or equal to that for hh3cCpuGroupUsageMinorThreshold."
    ::= {hh3cCpuGroupUsageEntry 4}

hh3cCpuGroupUsageInterval     OBJECT-TYPE
    SYNTAX         Unsigned32 (10..3600)
    MAX-ACCESS     read-write
    STATUS         current
    DESCRIPTION
    "CPU usage alarm interval."
    ::= {hh3cCpuGroupUsageEntry 5}

hh3cCpuGroupUsageAverageCpuUsage     OBJECT-TYPE
    SYNTAX         Unsigned32 (0..100)
    MAX-ACCESS     read-only
    STATUS         current
    DESCRIPTION
    "Average CPU usage in the interval, accurate to 1%."
    ::= {hh3cCpuGroupUsageEntry 6}

hh3cCpuGroupUsageLast5sCpuUsage     OBJECT-TYPE
    SYNTAX         Unsigned32 (0..100)
    MAX-ACCESS     read-only
    STATUS         current
    DESCRIPTION
    "CPU usage in last 5 seconds, accurate to 1%."
    ::= {hh3cCpuGroupUsageEntry 7}

hh3cCpuGroupUsageLast1mCpuUsage      OBJECT-TYPE
    SYNTAX        Unsigned32 (0..100)
    MAX-ACCESS    read-only
    STATUS        current
    DESCRIPTION
    "CPU usage in last 1 minute, accurate to 1%."
    ::= {hh3cCpuGroupUsageEntry 8}

hh3cCpuGroupUsageLast5mCpuUsage     OBJECT-TYPE
    SYNTAX        Unsigned32 (0..100)
    MAX-ACCESS    read-only
    STATUS        current
    DESCRIPTION
    "CPU usage in last 5 minutes, accurate to 1%."
    ::= {hh3cCpuGroupUsageEntry 9}


hh3cCpuGroupUsageCurrentState   OBJECT-TYPE
    SYNTAX          OCTET STRING(SIZE(0..64))
    MAX-ACCESS     read-only
    STATUS     current
    DESCRIPTION
    "Last state of CPU group usage.
    normal
    minor
    severe"
    ::= {hh3cCpuGroupUsageEntry 10}

-- ==================================================================
-- remote laser module table
-- ==================================================================
hh3cDevAdmRlmTable OBJECT-TYPE
    SYNTAX          SEQUENCE OF Hh3cDevAdmRlmEntry
    MAX-ACCESS      not-accessible
    STATUS          current
    DESCRIPTION     "Remote laser module table."
    ::= {hh3cLswSlotConf 19}

hh3cDevAdmRlmEntry    OBJECT-TYPE
    SYNTAX         Hh3cDevAdmRlmEntry
    MAX-ACCESS     not-accessible
    STATUS         current
    DESCRIPTION
    "Remote laser module table entry."
    INDEX {
    hh3cLswFrameIndex,
    hh3cLswSlotIndex,
    hh3cLswCpuIndex,
    hh3cLswSubslotIndex,
    hh3cDevAdmRlmPortIndex
    }
    ::= {hh3cDevAdmRlmTable  1}

Hh3cDevAdmRlmEntry ::= SEQUENCE
{
    hh3cDevAdmRlmPortIndex              Integer32,
    hh3cDevAdmRlmStatus                    INTEGER,
    hh3cDevAdmRlmCurrentTxPower    Integer32
}
hh3cDevAdmRlmPortIndex    OBJECT-TYPE
    SYNTAX     Integer32
    MAX-ACCESS     read-only
    STATUS     current
    DESCRIPTION
    "Index of remote laser module port."
    ::= {hh3cDevAdmRlmEntry 1}

hh3cDevAdmRlmStatus   OBJECT-TYPE
    SYNTAX     INTEGER
    {
        invalid(1),
        normal(2),
        absent(3),
        fault(4),
        lowPower(5)
    }
    MAX-ACCESS     read-only
    STATUS     current
    DESCRIPTION
    "Present status of remote laser module.
    invalid,
    normal,
    absent,
    fault,
    lowPower"
    ::= {hh3cDevAdmRlmEntry 2}

hh3cDevAdmRlmCurrentTxPower   OBJECT-TYPE
    SYNTAX     Integer32
    MAX-ACCESS     read-only
    STATUS     current
    DESCRIPTION
    "Current transmit power of remote laser module.
    The unit is in hundredths of dBm."
    ::= {hh3cDevAdmRlmEntry 3}

END
