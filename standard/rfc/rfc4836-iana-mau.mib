IANA-MAU-MIB DEFINITIONS ::= BEGIN

    IMPORTS
        MODULE-IDENTITY, OBJECT-IDENTITY, mib-2
            FROM SNMPv2-SMI
        TEXTUAL-CONVENTION
            FROM SNMPv2-TC
            ;

    ianaMauMIB MODULE-IDENTITY
        LAST-UPDATED "202404020000Z" -- April 2, 2024
        ORGANIZATION "IANA"
        CONTACT-INFO "        Internet Assigned Numbers Authority

                      Postal: ICANN
                              Los Angeles, CA 90094-2536
                              Marina del Rey, CA 90292

                         Tel: +1-310-301-5800
                       EMail: iana&iana.org"

        DESCRIPTION
          "This MIB module defines dot3MauType OBJECT-IDENTITIES and
          IANAifMauListBits, IANAifMauMediaAvailable,
          IANAifMauAutoNegCapBits, and IANAifJackType
          TEXTUAL-CONVENTIONs, specifying enumerated values of the
          ifMauTypeListBits, ifMauMediaAvailable / rpMauMediaAvailable,
          ifMauAutoNegCapabilityBits / ifMauAutoNegCapAdvertisedBits /
          ifMauAutoNegCapReceivedBits and ifJackType / rpJackType objects
          respectively, defined in the MAU-MIB.

          It is intended that each new MAU type, Media Availability
          state, Auto Negotiation capability and/or Jack type defined by
          the IEEE 802.3 working group and approved for publication in a
          revision of IEEE Std 802.3 will be added to this MIB module,
          provided that it is suitable for being managed by the base
          objects in the MAU-MIB.  An Expert Review, as defined in
          RFC 2434 [RFC2434], is REQUIRED for such additions.

          The following reference is used throughout this MIB module:

          [IEEE802.3] refers to IEEE Std 802.3-2022:
          'IEEE Standard for Ethernet'.

          This reference should be updated as appropriate when new
          MAU types, Media Availability states, Auto Negotiation
          capabilities, and/or Jack types are added to this MIB module.

          Copyright (C) The IETF Trust (2007).
          The initial version of this MIB module was published in
          RFC 4836; for full legal notices see the RFC itself.
          Supplementary information may be available at:
          http://www.ietf.org/copyrights/ianamib.html"

       REVISION     "202404020000Z" -- April 2, 2024
       DESCRIPTION  "Added support for IEEE Std 802.3df-2024 (400GBASE-DR4-2,
                     800GBASE-CR8, 800GBASE-DR8, 800GBASE-DR8-2, 800GBASE-KR8,
                     800GBASE-R, 800GBASE-SR8, and 800GBASE-VR8PHYs)."
       REVISION     "202309070000Z"  -- September 7, 2023
       DESCRIPTION  "Added support for IEEE Std 802.3cy-2023 (25GBASE-T1 PHYs)."
       REVISION     "202306140000Z"  -- June 14, 2023
       DESCRIPTION  "Added coverage for IEEE Std 802.3cz-2023 (entries for
                     2.5GBASE-AU, 5GBASE-AU, 10GBASE-AU, 25GBASE-AU, and
                     50GBASE-AU)."
       REVISION     "202302060000Z"  -- February 6, 2023
       DESCRIPTION  "Added MAU types specified in the IEEE Std 802.3cm-2020,
                     IEEE Std 802.3ch-2020, IEEE Std 802.3ca-2020, IEEE Std
                     802.3ct-2021, IEEE Std 802.3cp-2021, and aligned with
                     IEEE Std 802.3-2022."
       REVISION     "202208100000Z"  -- August 10, 2022
       DESCRIPTION  "Added MAU types specified in IEEE Std 802.3cu-2021"
       REVISION     "202001300000Z"  -- January 30, 2020
       DESCRIPTION  "Added MAU types and associated AutoNeg
                     capability bits specified in the IEEE Std 802.3-2018,
                     as well as IEEE Std 802.3cb-2018, IEEE Std 802.3bt-2018,
                     IEEE Std 802.3cd-2018, IEEE Std 802.3cn-2019, and
                     IEEE Std 802.3cg-2019"
       REVISION     "201907110000Z"  -- July 11, 2019
       DESCRIPTION  "Added support for 2.5GBase-T and 5GBase-T media
                     types."
       REVISION     "201704100000Z"  -- April 10, 2017
       DESCRIPTION  "Added new MAU types and associated AutoNeg
                     capability bits specified in the IEEE 802.3
                     amendments IEEE Std 802.3bk-2013, IEEE Std
                     802.3bj-2014 and IEEE Std 802.3bm-2015, which
                     are now published in IEEE Std 802.3-2015, as
                     well as IEEE Std 802.3bw-2015, IEEE Std
                     802.3by-2016, IEEE Std 802.3bq-2016 and IEEE
                     Std 802.3bp-2016."
       REVISION     "201408010000Z"  -- August 1, 2014
       DESCRIPTION  "Added IANAifJackType 16."

       REVISION     "201405220000Z"  -- May 22, 2014
       DESCRIPTION  "Updated contact info."
       REVISION     "201108120000Z"  -- August 12, 2011
       DESCRIPTION  "Added MAU types and associated AutoNeg capability
                     bits specified in amendments to IEEE Std
                     802.3-2008: IEEE Std 802.3ba-2010 and IEEE Std
                     802.3bg-2011."
       REVISION     "201002230000Z"  -- February 23, 2010
       DESCRIPTION  "Added assignments that will be included in
                     Clause 14 of IEEE P802.3.1."
       REVISION     "200704210000Z"  -- April 21, 2007
       DESCRIPTION  "Initial version of this MIB as published in
                     RFC 4836."
        ::= { mib-2 154 }

    -- Textual Conventions

    IANAifMauTypeListBits ::= TEXTUAL-CONVENTION
        STATUS       current
        DESCRIPTION
          "This data type is used as the syntax of the ifMauTypeListBits
          object in the (updated) definition of MAU-MIB's ifMauTable.

          The most recent version of this textual convention is available
          in the online version of this MIB module on the IANA web site.

          Requests for new values should be made to IANA via email
          (iana&iana.org).

          Note that changes in this textual convention SHALL be
          synchronized with relevant changes in the dot3MauType
          OBJECT-IDENTITIES."
        REFERENCE
          "[IEEE802.3], Section 30.5.1.1.2"
        SYNTAX       BITS {
            bOther(0),          -- other or unknown
            bAUI(1),            -- AUI
            b10base5(2),        -- 10BASE-5
            bFoirl(3),          -- FOIRL

            b10base2(4),        -- 10BASE-2
            b10baseT(5),        -- 10BASE-T duplex mode unknown
            b10baseFP(6),       -- 10BASE-FP
            b10baseFB(7),       -- 10BASE-FB
            b10baseFL(8),       -- 10BASE-FL duplex mode unknown
            b10broad36(9),      -- 10BROAD36
            b10baseTHD(10),     -- 10BASE-T  half duplex mode
            b10baseTFD(11),     -- 10BASE-T  full duplex mode
            b10baseFLHD(12),    -- 10BASE-FL half duplex mode
            b10baseFLFD(13),    -- 10BASE-FL full duplex mode
            b100baseT4(14),     -- 100BASE-T4
            b100baseTXHD(15),   -- 100BASE-TX half duplex mode
            b100baseTXFD(16),   -- 100BASE-TX full duplex mode
            b100baseFXHD(17),   -- 100BASE-FX half duplex mode
            b100baseFXFD(18),   -- 100BASE-FX full duplex mode
            b100baseT2HD(19),   -- 100BASE-T2 half duplex mode
            b100baseT2FD(20),   -- 100BASE-T2 full duplex mode

            b1000baseXHD(21),   -- 1000BASE-X half duplex mode
            b1000baseXFD(22),   -- 1000BASE-X full duplex mode
            b1000baseLXHD(23),  -- 1000BASE-LX half duplex mode
            b1000baseLXFD(24),  -- 1000BASE-LX full duplex mode
            b1000baseSXHD(25),  -- 1000BASE-SX half duplex mode
            b1000baseSXFD(26),  -- 1000BASE-SX full duplex mode
            b1000baseCXHD(27),  -- 1000BASE-CX half duplex mode
            b1000baseCXFD(28),  -- 1000BASE-CX full duplex mode
            b1000baseTHD(29),   -- 1000BASE-T half duplex mode
            b1000baseTFD(30),   -- 1000BASE-T full duplex mode

            b10GbaseX(31),      -- 10GBASE-X
            b10GbaseLX4(32),    -- 10GBASE-LX4
            b10GbaseR(33),      -- 10GBASE-R
            b10GbaseER(34),     -- 10GBASE-ER
            b10GbaseLR(35),     -- 10GBASE-LR
            b10GbaseSR(36),     -- 10GBASE-SR
            b10GbaseW(37),      -- 10GBASE-W
            b10GbaseEW(38),     -- 10GBASE-EW
            b10GbaseLW(39),     -- 10GBASE-LW
            b10GbaseSW(40),     -- 10GBASE-SW
            -- new since RFC 3636
            b10GbaseCX4(41),    -- 10GBASE-CX4
            b2BaseTL(42),       -- 2BASE-TL
            b10PassTS(43),      -- 10PASS-TS
            b100BaseBX10D(44),  -- 100BASE-BX10D
            b100BaseBX10U(45),  -- 100BASE-BX10U
            b100BaseLX10(46),   -- 100BASE-LX10
            b1000BaseBX10D(47), -- 1000BASE-BX10D
            b1000BaseBX10U(48), -- 1000BASE-BX10U
            b1000BaseLX10(49),  -- 1000BASE-LX10
            b1000BasePX10D(50), -- 1000BASE-PX10D
            b1000BasePX10U(51), -- 1000BASE-PX10U
            b1000BasePX20D(52), -- 1000BASE-PX20D
            b1000BasePX20U(53), -- 1000BASE-PX20U
            b10GbaseT(54),      -- 10GBASE-T
            b10GbaseLRM(55),    -- 10GBASE-LRM
            b1000baseKX(56),    -- 1000BASE-KX
            b10GbaseKX4(57),    -- 10GBASE-KX4
            b10GbaseKR(58),     -- 10GBASE-KR
            b10G1GbasePRXD1(59),-- 10/1GBASE-PRX-D1
            b10G1GbasePRXD2(60),-- 10/1GBASE-PRX-D2
            b10G1GbasePRXD3(61),-- 10/1GBASE-PRX-D3
            b10G1GbasePRXU1(62),-- 10/1GBASE-PRX-U1
            b10G1GbasePRXU2(63),-- 10/1GBASE-PRX-U2
            b10G1GbasePRXU3(64),-- 10/1GBASE-PRX-U3
            b10GbasePRD1(65),   -- 10GBASE-PR-D1
            b10GbasePRD2(66),   -- 10GBASE-PR-D2
            b10GbasePRD3(67),   -- 10GBASE-PR-D3
            b10GbasePRU1(68),   -- 10GBASE-PR-U1
            b10GbasePRU3(69),   -- 10GBASE-PR-U3
            b40GbaseKR4(70),    -- 40GBASE-KR4
            b40GbaseCR4(71),    -- 40GBASE-CR4
            b40GbaseSR4(72),    -- 40GBASE-SR4
            b40GbaseFR(73),     -- 40GBASE-FR
            b40GbaseLR4(74),    -- 40GBASE-LR4
            b100GbaseCR10(75),  -- 100GBASE-CR10
            b100GbaseSR10(76),  -- 100GBASE-SR10
            b100GbaseLR4(77),   -- 100GBASE-LR4
            b100GbaseER4(78),    -- 100GBASE-ER4
            b1000baseT1(79), -- 1000BASE-T1
            b1000basePX30D(80), -- 1000BASE-PX30D
            b1000basePX30U(81), -- 1000BASE-PX30U
            b1000basePX40D(82), -- 1000BASE-PX40D
            b1000basePX40U(83), -- 1000BASE-PX40U
            b10G1GbasePRXD4(84), -- 10/1GBASE-PRX-D4
            b10G1GbasePRXU4(85), -- 10/1GBASE-PRX-U4
            b10GbasePRD4(86), -- 10GBASE-PRD4
            b10GbasePRU4(87), -- 10GBASE-PRU4
            b25GbaseCR(88), -- 25GBASE-CR
            b25GbaseCRS(89), -- 25GBASE-CR-S
            b25GbaseKR(90), -- 25GBASE-KR
            b25GbaseKRS(91), -- 25GBASE-KR-S
            b25GbaseR(92), -- 25GBASE-R
            b25GbaseSR(93), -- 25GBASE-SR
            b25GbaseT(94), -- 25GBASE-T
            b40GbaseER4(95), -- 40GBASE-ER4
            b40GbaseR(96), -- 40GBASE-R
            b40GbaseT(97), -- 40GBASE-T
            b100GbaseCR4(98), -- 100GBASE-CR4
            b100GbaseKR4(99), -- 100GBASE-KR4
            b100GbaseKP4(100), -- 100GBASE-KP4
            b100GbaseR(101), -- 100GBASE-R
            b100GbaseSR4(102), -- 100GBASE-SR4
            b2p5GbaseT(103), -- 2.5GBASE-T
            b5GbaseT(104), -- 5GBASE-T
            b100baseT1(105), -- 100BASE-T1
            b1000baseRHA(106), -- 1000BASE-RHA
            b1000baseRHB(107), -- 1000BASE-RHB
            b1000baseRHC(108), -- 1000BASE-RHC
            b2p5GbaseKX(109), -- 2.5GBASE-KX
            b2p5GbaseX(110), -- 2.5GBASE-X
            b5GbaseKR(111), -- 5GBASE-KR
            b5GbaseR(112), -- 5GBASE-R
            b10GpassXR(113), -- 10GPASS-XR
            b25GbaseLR(114), -- 25GBASE-LR
            b25GbaseER(115), -- 25GBASE-ER
            b50GbaseR(116), -- 50GBASE-R
            b50GbaseCR(117), -- 50GBASE-CR
            b50GbaseKR(118), -- 50GBASE-KR
            b50GbaseSR(119), -- 50GBASE-SR
            b50GbaseFR(120), -- 50GBASE-FR
            b50GbaseLR(121), -- 50GBASE-LR
            b50GbaseER(122), -- 50GBASE-ER
            b100GbaseCR2(123), -- 100GBASE-CR2
            b100GbaseKR2(124), -- 100GBASE-KR2
            b100GbaseSR2(125), -- 100GBASE-SR2
            b100GbaseDR(126), -- 100GBASE-DR
            b200GbaseR(127), -- 200GBASE-R
            b200GbaseDR4(128), -- 200GBASE-DR4
            b200GbaseFR4(129), -- 200GBASE-FR4
            b200GbaseLR4(130), -- 200GBASE-LR4
            b200GbaseCR4(131), -- 200GBASE-CR4
            b200GbaseKR4(132), -- 200GBASE-KR4
            b200GbaseSR4(133), -- 200GBASE-SR4
            b200GbaseER4(134), -- 200GBASE-ER4
            b400GbaseR(135), -- 400GBASE-R
            b400GbaseSR16(136), -- 400GBASE-SR16
            b400GbaseDR4(137), -- 400GBASE-DR4
            b400GbaseFR8(138), -- 400GBASE-FR8
            b400GbaseLR8(139), -- 400GBASE-LR8
            b400GbaseER8(140), -- 400GBASE-ER8
            b10baseT1L(141), -- 10BASE-T1L
            b10baseT1SHD(142), -- 10BASE-T1S half duplex mode
            b10baseT1SMD(143), -- 10BASE-T1S multidrop mode
            b10baseT1SFD(144), -- 10BASE-T1S full duplex mode
            b100GbaseFR1(145), -- 100GBASE-FR1
            b100GbaseLR1(146), -- 100GBASE-LR1
            b400GbaseFR4(147), -- 400GBASE-FR4
            b400GbaseLR46(148), -- 400GBASE-LR4-6
            b400GbaseSR8(149), -- 400GBASE-SR8
            b400GbaseSR4p2(150), -- 400GBASE-LR4.2
            b2p5GbaseT1(151), -- 2.5GBASE-T1
            b5GbaseT1(152), -- 5GBASE-T1
            b10GbaseT1(153), -- 10GBASE-T1
            b25G10GbasePQGD2(154), -- 25/10GBASE-PQG-D2
            b25G10GbasePQGD3(155), -- 25/10GBASE-PQG-D3
            b25G10GbasePQGU2(156), -- 25/10GBASE-PQG-U2
            b25G10GbasePQGU3(157), -- 25/10GBASE-PQG-U3
            b25G10GbasePQXD2(158), -- 25/10GBASE-PQX-D2
            b25G10GbasePQXD3(159), -- 25/10GBASE-PQX-D3
            b25G10GbasePQXU2(160), -- 25/10GBASE-PQX-U2
            b25G10GbasePQXU3(161), -- 25/10GBASE-PQX-U3
            b25GbasePQGD2(162), -- 25GBASE-PQG-D2
            b25GbasePQGD3(163), -- 25GBASE-PQG-D3
            b25GbasePQGU2(164), -- 25GBASE-PQG-U2
            b25GbasePQGU3(165), -- 25GBASE-PQG-U3
            b25GbasePQXD2(166), -- 25GBASE-PQX-D2
            b25GbasePQXD3(167), -- 25GBASE-PQX-D3
            b25GbasePQXU2(168), -- 25GBASE-PQX-U2
            b25GbasePQXU3(169), -- 25GBASE-PQX-U3
            b50G10GbasePQGD2(170), -- 50/10GBASE-PQG-D2
            b50G10GbasePQGD3(171), -- 50/10GBASE-PQG-D3
            b50G10GbasePQGU2(172), -- 50/10GBASE-PQG-U2
            b50G10GbasePQGU3(173), -- 50/10GBASE-PQG-U3
            b50G10GbasePQXD2(174), -- 50/10GBASE-PQX-D2
            b50G10GbasePQXD3(175), -- 50/10GBASE-PQX-D3
            b50G10GbasePQXU2(176), -- 50/10GBASE-PQX-U2
            b50G10GbasePQXU3(177), -- 50/10GBASE-PQX-U3
            b50G25GbasePQGD2(178), -- 50/25GBASE-PQG-D2
            b50G25GbasePQGD3(179), -- 50/25GBASE-PQG-D3
            b50G25GbasePQGU2(180), -- 50/25GBASE-PQG-U2
            b50G25GbasePQGU3(181), -- 50/25GBASE-PQG-U3
            b50G25GbasePQXD2(182), -- 50/25GBASE-PQX-D2
            b50G25GbasePQXD3(183), -- 50/25GBASE-PQX-D3
            b50G25GbasePQXU2(184), -- 50/25GBASE-PQX-U2
            b50G25GbasePQXU3(185), -- 50/25GBASE-PQX-U3
            b50GbasePQGD2(186), -- 50GBASE-PQG-D2
            b50GbasePQGD3(187), -- 50GBASE-PQG-D3
            b50GbasePQGU2(188), -- 50GBASE-PQG-U2
            b50GbasePQGU3(189), -- 50GBASE-PQG-U3
            b50GbasePQXD2(190), -- 50GBASE-PQX-D2
            b50GbasePQXD3(191), -- 50GBASE-PQX-D3
            b50GbasePQXU2(192), -- 50GBASE-PQX-U2
            b50GbasePQXU3(193), -- 50GBASE-PQX-U3
            b100GbaseZR(194), -- 100GBASE-ZR
            b10GbaseBR10D(195), -- 10GBASE-BR10-D
            b10GbaseBR10U(196), -- 10GBASE-BR10-U
            b10GbaseBR20D(197), -- 10GBASE-BR20-D
            b10GbaseBR20U(198), -- 10GBASE-BR20-U
            b10GbaseBR40D(199), -- 10GBASE-BR40-D
            b10GbaseBR40U(200), -- 10GBASE-BR40-U
            b25GbaseBR10D(201), -- 25GBASE-BR10-D
            b25GbaseBR10U(202), -- 25GBASE-BR10-U
            b25GbaseBR20D(203), -- 25GBASE-BR20-D
            b25GbaseBR20U(204), -- 25GBASE-BR20-U
            b25GbaseBR40D(205), -- 25GBASE-BR40-D
            b25GbaseBR40U(206), -- 25GBASE-BR40-U
            b50GbaseBR10D(207), -- 50GBASE-BR10-D
            b50GbaseBR10U(208), -- 50GBASE-BR10-U
            b50GbaseBR20D(209), -- 50GBASE-BR20-D
            b50GbaseBR20U(210), -- 50GBASE-BR20-U
            b50GbaseBR40D(211), -- 50GBASE-BR40-D
            b50GbaseBR40U(212), -- 50GBASE-BR40-U
            b2p5GbaseAU(213), -- 2.5GBASE-AU
            b5GbaseAU(214), -- 5GBASE-AU
            b10GbaseAU(215), -- 10GBASE-AU
            b25GbaseAU(216), -- 25GBASE-AU
            b50GbaseAU(217), -- 50GBASE-AU
            b25GbaseT1(218), -- 25GBASE-T1
            b400GbaseDR42(219), -- 400GBASE-DR4-2
            b800GbaseCR8(220), -- 800GBASE-CR8
            b800GbaseDR8(221), -- 800GBASE-DR8
            b800GbaseDR82(222), -- 800GBASE-DR8-2
            b800GbaseKR8(223), -- 800GBASE-KR8
            b800GbaseR(224), -- 800GBASE-R
            b800GbaseSR8(225), -- 800GBASE-SR8
            b800GbaseVR8(226) -- 800GBASE-VR8
         }

    IANAifMauMediaAvailable ::= TEXTUAL-CONVENTION
        STATUS       current
        DESCRIPTION
          "This data type is used as the syntax of the
          ifMauMediaAvailable and rpMauMediaAvailable objects in the
          (updated) definition of MAU-MIB's ifMauTable and rpMauTable
          respectively.

          Possible values are:
            other(1)             - undefined (not listed below)
            unknown(2)           - MAU's true state is unknown; e.g.,
                                   during initialization
            available(3)         - link, light, or loopback is normal
            notAvailable(4)      - link loss, low light, or no loopback
            remoteFault(5)       - a fault has been detected at the
                                   remote end of the link.  This value
                                   applies to 10BASE-FB, 100BASE-T4 Far
                                   End Fault Indication and non-specified
                                   remote faults from a system running
                                   auto-negotiation
            invalidSignal(6)     - invalid signal has been received from
                                   the other end of the link, 10BASE-FB
                                   only
            remoteJabber(7)      - remote fault, due to jabber
            remoteLinkLoss(8)    - remote fault, due to link loss
            remoteTest(9)        - remote fault, due to test
            offline(10)          - offline, Clause 37 Auto-Negotiation
                                   only
            autoNegError(11)     - Auto-Negotiation Error, Clause 37
                                   Auto-Negotiation only
            pmdLinkFault(12)     - PMA/PMD receive link fault.  In case
                                   of PAF (2BASE-TL / 10PASS-TS PHYs),
                                   all PMEs in the aggregation group have
                                   detected a link fault
            wisFrameLoss(13)     - WIS loss of frame, 10GBASE-W only
            wisSignalLoss(14)    - WIS loss of signal, 10GBASE-W only
            pcsLinkFault(15)     - PCS receive link fault
            excessiveBER(16)     - PCS Bit Error Ratio monitor
                                   reporting excessive error ratio
            dxsLinkFault(17)     - DTE XGXS receive link fault, XAUI only
            pxsLinkFault(18)     - PHY XGXS receive link fault, XAUI only
            availableReduced(19) - link normal, reduced bandwidth,
                                   2BASE-TL / 10PASS-TS only
            ready(20)            - at least one PME in the aggregation
                                   group is detecting handshake tones,
                                   2BASE-TL / 10PASS-TS only

          If the MAU is a 10M b/s link or fiber type (FOIRL, 10BASE-T,
          10BASE-F), then this is equivalent to the link test fail
          state/low light function.  For an AUI, 10BASE2, 10BASE5, or
          10BROAD36 MAU, this indicates whether loopback is detected on
          the DI circuit.  The value of this attribute persists between
          packets for MAU types AUI, 10BASE5, 10BASE2, 10BROAD36, and
          10BASEFP.

          At power-up or following a reset, the Media Available state
          will be unknown(2) for AUI, 10BASE5, 10BASE2, 10BROAD36, and
          10BASE-FP MAUs.  For these MAUs loopback will be tested on each
          transmission during which no collision is detected.
          If DI is receiving input when DO returns to IDL after a
          transmission and there has been no collision during the
          transmission, then loopback will be detected.  The Media
          Available state will only change during noncollided
          transmissions for AUI, 10BASE2, 10BASE5, 10BROAD36, and
          10BASE-FP MAUs.

          For 100BASE-T2, 100BASE-T4, 100BASE-TX, 100BASE-FX,
          100BASE-LX10, and 100BASE-BX10 PHYs the enumerations match the
          states within the link integrity state diagram.
          Any MAU that implements management of [IEEE802.3] Clause
          28 Auto-Negotiation, will map remote fault indication to
          remoteFault(5).

          Any MAU that implements management of Clause 37
          Auto-Negotiation, will map the received RF1 and RF2 bits as
          follows: Offline maps to offline(10), Link_Failure maps to
          remoteFault(5), and Auto-Negotiation Error maps to
          autoNegError(11).

          The value remoteFault(5) applies to 10BASE-FB remote
          fault indication, the 100BASE-X far-end fault indication, and
          nonspecified remote faults from a system running Clause 28
          Auto-Negotiation.

          The value remoteJabber(7), remoteLink loss(8), or remoteTest(9)
          SHOULD be used instead of remoteFault(5) where the reason for
          remote fault is identified in the remote signaling protocol.
          Where a Clause 22 MII or Clause 35 GMII is present, a logic
          one in the remote fault bit maps to the value remoteFault(5),
          a logic zero in the link status bit maps to the enumeration
          notAvailable(4).  The value notAvailable(4) takes precedence
          over remoteFault(5).

          For 2BASE-TL and 10PASS-TS PHYs, the value unknown(2) maps to
          the condition where the PHY (PCS with connected PMEs) is
          initializing, the value ready(20) maps to the condition where
          the interface is down and at least one PME in the aggregation
          group is ready for handshake, the value available(3) maps to
          the condition where all the PMEs in the aggregation group are
          up, the value notAvailable(4) maps to the condition where all
          the PMEs in the aggregation group are down and no handshake
          tones are detected, the value availableReduced(19) maps to the
          condition where the interface is up, a link fault is detected
          at the receive direction by one or more PMEs in the
          aggregation group, but at least one PME is up and the
          enumeration pmdLinkFault(12) maps to the condition where a link
          fault is detected at the receive direction by all of the PMEs
          in the aggregation group.

          For 10 Gb/s the enumerations map to value of the link_fault
          variable within the Link Fault Signaling state diagram
          as follows: the value OK maps to the value available(3),
          the value Local Fault maps to the value notAvailable(4),
          and the value Remote Fault maps to the value remoteFault(5).
          The value pmdLinkFault(12), wisFrameLoss(13),
          wisSignalLoss(14), pcsLinkFault(15), excessiveBER(16), or
          dxsLinkFault(17) SHOULD be used instead of the value
          notAvailable(4), where the reason for the Local Fault state can
          be identified through the use of the Clause 45 MDIO Interface.
          Where multiple reasons for the Local Fault state can be
          identified, only the highest precedence error SHOULD be
          reported.  This precedence in descending order is as follows:

            pxsLinkFault
            pmdLinkFault
            wisFrameLoss
            wisSignalLoss
            pcsLinkFault
            excessiveBER
            dxsLinkFault.

          Where a Clause 45 MDIO interface is present a logic zero in
          the PMA/PMD Receive link status bit ([IEEE802.3]
          Section 45.2.1.2.2) maps to the value pmdLinkFault(12),
          logic one in the LOF status bit (Section 45.2.2.10.4) maps
          to the value wisFrameLoss(13), a logic one in the LOS
          status bit (Section 45.2.2.10.5) maps to the value
          wisSignalLoss, a logic zero in the PCS Receive
          link status bit (Section 45.2.3.2.2) maps to the value
          pcsLinkFault(15), a logic one in the 10GBASE-R PCS Latched
          high BER status bit (Section 45.2.3.12.2) maps to the value
          excessiveBER, a logic zero in the DTE XS receive link status
          bit (Section 45.2.5.2.2) maps to the value dxsLinkFault(17)
          and a logic zero in the PHY XS transmit link status bit
          (Section 45.2.4.2.2) maps to the value pxsLinkFault(18).

          The most recent version of this textual convention is available
          in the online version of this MIB module on the IANA web site.

          Requests for new values should be made to IANA via email
          (iana&iana.org)."
        REFERENCE
          "[IEEE802.3], Section 30.5.1.1.4"
        SYNTAX       INTEGER {
            other(1),
            unknown(2),
            available(3),
            notAvailable(4),
            remoteFault(5),
            invalidSignal(6),
            remoteJabber(7),
            remoteLinkLoss(8),
            remoteTest(9),
            offline(10),
            autoNegError(11),
            pmdLinkFault(12),
            wisFrameLoss(13),
            wisSignalLoss(14),
            pcsLinkFault(15),
            excessiveBER(16),
            dxsLinkFault(17),
            pxsLinkFault(18),
            availableReduced(19),
            ready(20)
        }

    IANAifMauAutoNegCapBits ::= TEXTUAL-CONVENTION
        STATUS       current
        DESCRIPTION
          "This data type is used as the syntax of the
          ifMauAutoNegCapabilityBits, ifMauAutoNegCapAdvertisedBits, and
          ifMauAutoNegCapReceivedBits objects in the (updated) definition
          of MAU-MIB's ifMauAutoNegTable.

          The most recent version of this textual convention is available
          in the online version of this MIB module on the IANA web site.

          Requests for new values should be made to IANA via email
          (iana&iana.org)."
        REFERENCE
          "[IEEE802.3], Section 30.6.1.1.5"
        SYNTAX       BITS {
            bOther(0),          -- other or unknown
            b10baseT(1),        -- 10BASE-T  half duplex mode
            b10baseTFD(2),      -- 10BASE-T  full duplex mode
            b100baseT4(3),      -- 100BASE-T4
            b100baseTX(4),      -- 100BASE-TX half duplex mode
            b100baseTXFD(5),    -- 100BASE-TX full duplex mode
            b100baseT2(6),      -- 100BASE-T2 half duplex mode
            b100baseT2FD(7),    -- 100BASE-T2 full duplex mode
            bFdxPause(8),       -- PAUSE for full-duplex links
            bFdxAPause(9),      -- Asymmetric PAUSE for full-duplex
                                --     links
            bFdxSPause(10),     -- Symmetric PAUSE for full-duplex
                                --     links
            bFdxBPause(11),     -- Asymmetric and Symmetric PAUSE for
                                --     full-duplex links
            b1000baseX(12),     -- 1000BASE-X, -LX, -SX, -CX half
                                --     duplex mode
            b1000baseXFD(13),   -- 1000BASE-X, -LX, -SX, -CX full
                                --     duplex mode
            b1000baseT(14),     -- 1000BASE-T half duplex mode
            b1000baseTFD(15)    -- 1000BASE-T full duplex mode
        }

    IANAifJackType ::= TEXTUAL-CONVENTION
        STATUS       current
        DESCRIPTION
          "Common enumeration values for repeater and interface MAU
          jack types.  This data type is used as the syntax of the
          ifJackType and rpJackType objects in the (updated) definition
          of MAU-MIB's ifJackTable and rpJackTable respectively.

          Possible values are:
               other(1)          - undefined or unknown
               rj45(2)           - RJ45
               rj45S(3)          - RJ45 shielded
               db9(4)            - DB9
               bnc(5)            - BNC
               fAUI(6)           - AUI female
               mAUI(7)           - AUI male
               fiberSC(8)        - SC fiber
               fiberMIC(9)       - MIC fiber
               fiberST(10)       - ST fiber
               telco(11)         - Telco
               mtrj(12)          - MT-RJ fiber
               hssdc(13)         - fiber channel style-2
               fiberLC(14)       - LC fiber
               cx4(15)           - IB4X for 10GBASE-CX4

          The most recent version of this textual convention is available
          in the online version of this MIB module on the IANA web site.

          Requests for new values should be made to IANA via email
          (iana&iana.org)."
        SYNTAX       INTEGER {
            other(1),
            rj45(2),
            rj45S(3),
            db9(4),
            bnc(5),
            fAUI(6),
            mAUI(7),
            fiberSC(8),
            fiberMIC(9),
            fiberST(10),
            telco(11),
            mtrj(12),
            hssdc(13),
            fiberLC(14),
            -- new since RFC 3636
            cx4(15)
        }

    -- OBJECT IDENTITIES for MAU types
    -- (see rpMauType and ifMauType of MAU-MIB for usage)
    -- The following definitions has been moved from RFC 3636 and
    -- no longer appear in its revision.

    dot3MauType OBJECT IDENTIFIER ::= { mib-2 snmpDot3MauMgt(26) 4 }

    dot3MauTypeAUI OBJECT-IDENTITY
        STATUS      current
        DESCRIPTION "no internal MAU, view from AUI"
        REFERENCE   "[IEEE802.3], Section 7"
        ::= { dot3MauType 1 }

    dot3MauType10Base5 OBJECT-IDENTITY
        STATUS      current
        DESCRIPTION "thick coax MAU"
        REFERENCE   "[IEEE802.3], Section 7"
        ::= { dot3MauType 2 }

    dot3MauTypeFoirl OBJECT-IDENTITY
        STATUS      current
        DESCRIPTION "FOIRL MAU"
        REFERENCE   "[IEEE802.3], Section 9.9"
        ::= { dot3MauType 3 }

    dot3MauType10Base2 OBJECT-IDENTITY
        STATUS      current
        DESCRIPTION "thin coax MAU"
        REFERENCE   "[IEEE802.3], Section 10"
        ::= { dot3MauType 4 }

    dot3MauType10BaseT OBJECT-IDENTITY
        STATUS      current
        DESCRIPTION "UTP MAU.
                    Note that it is strongly recommended that
                    agents return either dot3MauType10BaseTHD or
                    dot3MauType10BaseTFD if the duplex mode is
                    known.  However, management applications should
                    be prepared to receive this MAU type value from
                    older agent implementations."
        REFERENCE   "[IEEE802.3], Section 14"
        ::= { dot3MauType 5 }

    dot3MauType10BaseFP OBJECT-IDENTITY
        STATUS      current
        DESCRIPTION "passive fiber MAU"
        REFERENCE   "[IEEE802.3], Section 16"
        ::= { dot3MauType 6 }

    dot3MauType10BaseFB OBJECT-IDENTITY
        STATUS      current
        DESCRIPTION "sync fiber MAU"
        REFERENCE   "[IEEE802.3], Section 17"
        ::= { dot3MauType 7 }

    dot3MauType10BaseFL OBJECT-IDENTITY
        STATUS      current
        DESCRIPTION "async fiber MAU.
                    Note that it is strongly recommended that
                    agents return either dot3MauType10BaseFLHD or
                    dot3MauType10BaseFLFD if the duplex mode is
                    known.  However, management applications should
                    be prepared to receive this MAU type value from
                    older agent implementations."
        REFERENCE   "[IEEE802.3], Section 18"
        ::= { dot3MauType 8 }

    dot3MauType10Broad36 OBJECT-IDENTITY
        STATUS      current
        DESCRIPTION "broadband DTE MAU.
                    Note that 10BROAD36 MAUs can be attached to
                    interfaces but not to repeaters."
        REFERENCE   "[IEEE802.3], Section 11"
        ::= { dot3MauType 9 }

    -- new since RFC 1515:
    dot3MauType10BaseTHD OBJECT-IDENTITY
        STATUS      current
        DESCRIPTION "UTP MAU, half duplex mode"
        REFERENCE   "[IEEE802.3], Section 14"
        ::= { dot3MauType 10 }

    dot3MauType10BaseTFD OBJECT-IDENTITY
        STATUS      current
        DESCRIPTION "UTP MAU, full duplex mode"
        REFERENCE   "[IEEE802.3], Section 14"
        ::= { dot3MauType 11 }

    dot3MauType10BaseFLHD OBJECT-IDENTITY
        STATUS      current
        DESCRIPTION "async fiber MAU, half duplex mode"
        REFERENCE   "[IEEE802.3], Section 18"
        ::= { dot3MauType 12 }

    dot3MauType10BaseFLFD OBJECT-IDENTITY
        STATUS      current
        DESCRIPTION "async fiber MAU, full duplex mode"
        REFERENCE   "[IEEE802.3], Section 18"
        ::= { dot3MauType 13 }

    dot3MauType100BaseT4 OBJECT-IDENTITY
        STATUS      current
        DESCRIPTION "4 pair category 3 UTP"
        REFERENCE   "[IEEE802.3], Section 23"
        ::= { dot3MauType 14 }

    dot3MauType100BaseTXHD OBJECT-IDENTITY
        STATUS      current
        DESCRIPTION "2 pair category 5 UTP, half duplex mode"
        REFERENCE   "[IEEE802.3], Section 25"
        ::= { dot3MauType 15 }

    dot3MauType100BaseTXFD OBJECT-IDENTITY
        STATUS      current
        DESCRIPTION "2 pair category 5 UTP, full duplex mode"
        REFERENCE   "[IEEE802.3], Section 25"
        ::= { dot3MauType 16 }

    dot3MauType100BaseFXHD OBJECT-IDENTITY
        STATUS      current
        DESCRIPTION "X fiber over PMT, half duplex mode"
        REFERENCE   "[IEEE802.3], Section 26"
        ::= { dot3MauType 17 }

    dot3MauType100BaseFXFD OBJECT-IDENTITY
        STATUS      current
        DESCRIPTION "X fiber over PMT, full duplex mode"
        REFERENCE   "[IEEE802.3], Section 26"
        ::= { dot3MauType 18 }

    dot3MauType100BaseT2HD OBJECT-IDENTITY
        STATUS      current
        DESCRIPTION "2 pair category 3 UTP, half duplex mode"
        REFERENCE   "[IEEE802.3], Section 32"
        ::= { dot3MauType 19 }

    dot3MauType100BaseT2FD OBJECT-IDENTITY
        STATUS      current
        DESCRIPTION "2 pair category 3 UTP, full duplex mode"
        REFERENCE   "[IEEE802.3], Section 32"
        ::= { dot3MauType 20 }

    -- new since RFC 2239:
    dot3MauType1000BaseXHD OBJECT-IDENTITY
        STATUS      current
        DESCRIPTION "PCS/PMA, unknown PMD, half duplex mode"
        REFERENCE   "[IEEE802.3], Section 36"
        ::= { dot3MauType 21 }

    dot3MauType1000BaseXFD OBJECT-IDENTITY
        STATUS      current
        DESCRIPTION "PCS/PMA, unknown PMD, full duplex mode"
        REFERENCE   "[IEEE802.3], Section 36"
        ::= { dot3MauType 22 }

    dot3MauType1000BaseLXHD OBJECT-IDENTITY
        STATUS      current
        DESCRIPTION "Fiber over long-wavelength laser, half duplex
                    mode"
        REFERENCE   "[IEEE802.3], Section 38"
        ::= { dot3MauType 23 }

    dot3MauType1000BaseLXFD OBJECT-IDENTITY
        STATUS      current
        DESCRIPTION "Fiber over long-wavelength laser, full duplex
                    mode"
        REFERENCE   "[IEEE802.3], Section 38"
        ::= { dot3MauType 24 }

    dot3MauType1000BaseSXHD OBJECT-IDENTITY
        STATUS      current
        DESCRIPTION "Fiber over short-wavelength laser, half
                    duplex mode"
        REFERENCE   "[IEEE802.3], Section 38"
        ::= { dot3MauType 25 }

    dot3MauType1000BaseSXFD OBJECT-IDENTITY
        STATUS      current
        DESCRIPTION "Fiber over short-wavelength laser, full
                    duplex mode"
        REFERENCE   "[IEEE802.3], Section 38"
        ::= { dot3MauType 26 }

    dot3MauType1000BaseCXHD OBJECT-IDENTITY
        STATUS      current
        DESCRIPTION "Copper over 150-Ohm balanced cable, half
                    duplex mode"
        REFERENCE   "[IEEE802.3], Section 39"
        ::= { dot3MauType 27 }

    dot3MauType1000BaseCXFD OBJECT-IDENTITY
        STATUS      current
        DESCRIPTION "Copper over 150-Ohm balanced cable, full
                    duplex mode"
        REFERENCE   "[IEEE802.3], Section 39"
        ::= { dot3MauType 28 }

    dot3MauType1000BaseTHD OBJECT-IDENTITY
        STATUS      current
        DESCRIPTION "Four-pair Category 5 UTP, half duplex mode"
        REFERENCE   "[IEEE802.3], Section 40"
        ::= { dot3MauType 29 }

    dot3MauType1000BaseTFD OBJECT-IDENTITY
        STATUS      current
        DESCRIPTION "Four-pair Category 5 UTP, full duplex mode"
        REFERENCE   "[IEEE802.3], Section 40"
        ::= { dot3MauType 30 }

    -- new since RFC 2668:
    dot3MauType10GigBaseX OBJECT-IDENTITY
        STATUS      current
        DESCRIPTION "X PCS/PMA, unknown PMD."
        REFERENCE   "[IEEE802.3], Section 48"
        ::= { dot3MauType 31 }

    dot3MauType10GigBaseLX4 OBJECT-IDENTITY
        STATUS      current
        DESCRIPTION "X fiber over WWDM optics"
        REFERENCE   "[IEEE802.3], Section 53"
        ::= { dot3MauType 32 }

    dot3MauType10GigBaseR OBJECT-IDENTITY
        STATUS      current
        DESCRIPTION "R PCS/PMA, unknown PMD."
        REFERENCE   "[IEEE802.3], Section 49"
        ::= { dot3MauType 33 }

    dot3MauType10GigBaseER OBJECT-IDENTITY
        STATUS      current
        DESCRIPTION "R fiber over 1550 nm optics"
        REFERENCE   "[IEEE802.3], Section 52"
        ::= { dot3MauType 34 }

    dot3MauType10GigBaseLR OBJECT-IDENTITY
        STATUS      current
        DESCRIPTION "R fiber over 1310 nm optics"
        REFERENCE   "[IEEE802.3], Section 52"
        ::= { dot3MauType 35 }

    dot3MauType10GigBaseSR OBJECT-IDENTITY
        STATUS      current
        DESCRIPTION "R fiber over 850 nm optics"
        REFERENCE   "[IEEE802.3], Section 52"
        ::= { dot3MauType 36 }

    dot3MauType10GigBaseW OBJECT-IDENTITY
        STATUS      current
        DESCRIPTION "W PCS/PMA, unknown PMD."
        REFERENCE   "[IEEE802.3], Section 49 and 50"
        ::= { dot3MauType 37 }

    dot3MauType10GigBaseEW OBJECT-IDENTITY
        STATUS      current
        DESCRIPTION "W fiber over 1550 nm optics"
        REFERENCE   "[IEEE802.3], Section 52"
        ::= { dot3MauType 38 }

    dot3MauType10GigBaseLW OBJECT-IDENTITY
        STATUS      current
        DESCRIPTION "W fiber over 1310 nm optics"
        REFERENCE   "[IEEE802.3], Section 52"
        ::= { dot3MauType 39 }

    dot3MauType10GigBaseSW OBJECT-IDENTITY
        STATUS      current
        DESCRIPTION "W fiber over 850 nm optics"
        REFERENCE   "[IEEE802.3], Section 52"
        ::= { dot3MauType 40 }

    -- new since RFC 3636:
    dot3MauType10GigBaseCX4 OBJECT-IDENTITY
        STATUS      current
        DESCRIPTION "X copper over 8 pair 100-Ohm balanced cable"
        REFERENCE   "[IEEE802.3], Section 54"
        ::= { dot3MauType 41 }

    dot3MauType2BaseTL OBJECT-IDENTITY
        STATUS      current
        DESCRIPTION "Voice grade UTP copper, up to 2700m, optional PAF"
        REFERENCE   "[IEEE802.3], Sections 61 and 63"
        ::= { dot3MauType 42 }

    dot3MauType10PassTS OBJECT-IDENTITY
        STATUS      current
        DESCRIPTION "Voice grade UTP copper, up to 750m, optional PAF"
        REFERENCE   "[IEEE802.3], Sections 61 and 62"
        ::= { dot3MauType 43 }

    dot3MauType100BaseBX10D OBJECT-IDENTITY
        STATUS      current
        DESCRIPTION "One single-mode fiber OLT, long wavelength, 10km"
        REFERENCE   "[IEEE802.3], Section 58"
        ::= { dot3MauType 44 }

    dot3MauType100BaseBX10U OBJECT-IDENTITY
        STATUS      current
        DESCRIPTION "One single-mode fiber ONU, long wavelength, 10km"
        REFERENCE   "[IEEE802.3], Section 58"
        ::= { dot3MauType 45 }

    dot3MauType100BaseLX10 OBJECT-IDENTITY
        STATUS      current
        DESCRIPTION "Two single-mode fibers, long wavelength, 10km"
        REFERENCE   "[IEEE802.3], Section 58"
        ::= { dot3MauType 46 }

    dot3MauType1000BaseBX10D OBJECT-IDENTITY
        STATUS      current
        DESCRIPTION "One single-mode fiber OLT, long wavelength, 10km"
        REFERENCE   "[IEEE802.3], Section 59"
        ::= { dot3MauType 47 }

    dot3MauType1000BaseBX10U OBJECT-IDENTITY
        STATUS      current
        DESCRIPTION "One single-mode fiber ONU, long wavelength, 10km"
        REFERENCE   "[IEEE802.3], Section 59"
        ::= { dot3MauType 48 }

    dot3MauType1000BaseLX10 OBJECT-IDENTITY
        STATUS      current
        DESCRIPTION "Two sigle-mode fiber, long wavelength, 10km"
        REFERENCE   "[IEEE802.3], Section 59"
        ::= { dot3MauType 49 }

    dot3MauType1000BasePX10D OBJECT-IDENTITY
        STATUS      current
        DESCRIPTION "One single-mode fiber EPON OLT, 10km"
        REFERENCE   "[IEEE802.3], Section 60"
        ::= { dot3MauType 50 }

    dot3MauType1000BasePX10U OBJECT-IDENTITY
        STATUS      current
        DESCRIPTION "One single-mode fiber EPON ONU, 10km"
        REFERENCE   "[IEEE802.3], Section 60"
        ::= { dot3MauType 51 }

    dot3MauType1000BasePX20D OBJECT-IDENTITY
        STATUS      current
        DESCRIPTION "One single-mode fiber EPON OLT, 20km"
        REFERENCE   "[IEEE802.3], Section 60"
        ::= { dot3MauType 52 }

    dot3MauType1000BasePX20U OBJECT-IDENTITY
        STATUS      current
        DESCRIPTION "One single-mode fiber EPON ONU, 20km"
        REFERENCE   "[IEEE802.3], Section 60"
        ::= { dot3MauType 53 }

    dot3MauType10GbaseT OBJECT-IDENTITY
        STATUS      current
        DESCRIPTION "Four-pair Category 6A or better, full duplex mode only"
        REFERENCE   "IEEE Std 802.3, Clause 55"
        ::= { dot3MauType 54 }

    dot3MauType10GbaseLRM OBJECT-IDENTITY
        STATUS      current
        DESCRIPTION "R multimode fiber over 1310 nm optics"
        REFERENCE   "IEEE Std 802.3, Clause 68"
        ::= { dot3MauType 55 }

    dot3MauType1000baseKX OBJECT-IDENTITY
        STATUS      current
        DESCRIPTION "X backplane, full duplex mode only"
        REFERENCE   "IEEE Std 802.3, Clause 70"
        ::= { dot3MauType 56 }

    dot3MauType10GbaseKX4 OBJECT-IDENTITY
        STATUS      current
        DESCRIPTION "4 lane X backplane, full duplex mode only"
        REFERENCE   "IEEE Std 802.3, Clause 71"
        ::= { dot3MauType 57 }

    dot3MauType10GbaseKR OBJECT-IDENTITY
        STATUS      current
        DESCRIPTION "R backplane, full duplex mode only"
        REFERENCE   "IEEE Std 802.3, Clause 72"
        ::= { dot3MauType 58 }

    dot3MauType10G1GbasePRXD1 OBJECT-IDENTITY
        STATUS      current
        DESCRIPTION "One single-mode fiber asymmetric-rate EPON OLT, supporting low
                    power budget (PRX10)"
        REFERENCE   "IEEE Std 802.3, Clause 75"
        ::= { dot3MauType 59 }

    dot3MauType10G1GbasePRXD2 OBJECT-IDENTITY
        STATUS      current
        DESCRIPTION "One single-mode fiber asymmetric-rate EPON OLT, supporting
                    medium power budget (PRX20)"
        REFERENCE   "IEEE Std 802.3, Clause 75"
        ::= { dot3MauType 60 }

    dot3MauType10G1GbasePRXD3 OBJECT-IDENTITY
        STATUS      current
        DESCRIPTION "One single-mode fiber asymmetric-rate EPON OLT, supporting high
                    power budget (PRX30)"
        REFERENCE   "IEEE Std 802.3, Clause 75"
        ::= { dot3MauType 61 }

    dot3MauType10G1GbasePRXU1 OBJECT-IDENTITY
        STATUS      current
        DESCRIPTION "One single-mode fiber asymmetric-rate EPON ONU, supporting low
                    power budget (PRX10)"
        REFERENCE   "IEEE Std 802.3, Clause 75"
        ::= { dot3MauType 62 }

    dot3MauType10G1GbasePRXU2 OBJECT-IDENTITY
        STATUS      current
        DESCRIPTION "One single-mode fiber asymmetric-rate EPON ONU, supporting
                    medium power budget (PRX20)"
        REFERENCE   "IEEE Std 802.3, Clause 75"
        ::= { dot3MauType 63 }

    dot3MauType10G1GbasePRXU3 OBJECT-IDENTITY
        STATUS      current
        DESCRIPTION "One single-mode fiber asymmetric-rate EPON ONU, supporting high
                    power budget (PRX30)"
        REFERENCE   "IEEE Std 802.3, Clause 75"
        ::= { dot3MauType 64 }

    dot3MauType10GbasePRD1 OBJECT-IDENTITY
        STATUS      current
        DESCRIPTION "One single-mode fiber symmetric-rate EPON OLT, supporting low
                    power budget (PR10)"
        REFERENCE   "IEEE Std 802.3, Clause 75"
        ::= { dot3MauType 65 }

    dot3MauType10GbasePRD2 OBJECT-IDENTITY
        STATUS      current
        DESCRIPTION "One single-mode fiber symmetric-rate EPON OLT, supporting
                    medium power budget (PR20)"
        REFERENCE   "IEEE Std 802.3, Clause 75"
        ::= { dot3MauType 66 }

    dot3MauType10GbasePRD3 OBJECT-IDENTITY
        STATUS      current
        DESCRIPTION "One single-mode fiber symmetric-rate EPON OLT, supporting high
                    power budget (PR30)"
        REFERENCE   "IEEE Std 802.3, Clause 75"
        ::= { dot3MauType 67 }

    dot3MauType10GbasePRU1 OBJECT-IDENTITY
        STATUS      current
        DESCRIPTION "One single-mode fiber symmetric-rate EPON ONU, supporting
                    low and medium power budget (PR10 and PR20)"
        REFERENCE   "IEEE Std 802.3, Clause 75"
        ::= { dot3MauType 68 }

    dot3MauType10GbasePRU3 OBJECT-IDENTITY
        STATUS      current
        DESCRIPTION "One single-mode fiber symmetric-rate EPON ONU, supporting high
                    power budget (PR30)"
        REFERENCE   "IEEE Std 802.3, Clause 75"
        ::= { dot3MauType 69 }

    dot3MauType40GbaseKR4 OBJECT-IDENTITY
        STATUS      current
        DESCRIPTION "40GBASE-R PCS/PMA over an electrical
                    backplane"
        REFERENCE   "IEEE Std 802.3, Clause 84"
        ::= { dot3MauType 70 }

    dot3MauType40GbaseCR4 OBJECT-IDENTITY
        STATUS      current
        DESCRIPTION "40GBASE-R PCS/PMA over 4 lane shielded
                    copper balanced cable"
        REFERENCE   "IEEE Std 802.3, Clause 85"
        ::= { dot3MauType 71 }

    dot3MauType40GbaseSR4 OBJECT-IDENTITY
        STATUS      current
        DESCRIPTION "40GBASE-R PCS/PMA over 4 lane multimode
                    fiber"
        REFERENCE   "IEEE Std 802.3, Clause 86"
        ::= { dot3MauType 72 }

    dot3MauType40GbaseFR OBJECT-IDENTITY
        STATUS      current
        DESCRIPTION "40GBASE-R PCS/PMA over single mode
                    fiber"
        REFERENCE   "IEEE Std 802.3, Clause 89"
        ::= { dot3MauType 73 }

    dot3MauType40GbaseLR4 OBJECT-IDENTITY
        STATUS      current
        DESCRIPTION "40GBASE-R PCS/PMA over 4 WDM lane
                    single mode fiber"
        REFERENCE   "IEEE Std 802.3, Clause 87"
        ::= { dot3MauType 74 }

    dot3MauType100GbaseCR10 OBJECT-IDENTITY
        STATUS      current
        DESCRIPTION "100GBASE-R PCS/PMA over 10 lane
                     shielded copper balanced cable"
        REFERENCE   "IEEE Std 802.3, Clause 85"
        ::= { dot3MauType 75 }

    dot3MauType100GbaseSR10 OBJECT-IDENTITY
        STATUS      current
        DESCRIPTION "100GBASE-R PCS/PMA over 10 lane
                    multimode fiber"
        REFERENCE   "IEEE Std 802.3, Clause 86"
        ::= { dot3MauType 76 }

    dot3MauType100GbaseLR4 OBJECT-IDENTITY
        STATUS      current
        DESCRIPTION "100GBASE-R PCS/PMA over 4 WDM lane
                    single mode fiber, long reach"
        REFERENCE   "IEEE Std 802.3, Clause 88"
        ::= { dot3MauType 77 }

    dot3MauType100GbaseER4 OBJECT-IDENTITY
        STATUS      current
        DESCRIPTION "100GBASE-R PCS/PMA over 4 WDM lane
                    single mode fiber PMD, extended reach"
        REFERENCE   "IEEE Std 802.3, Clause 88"
        ::= { dot3MauType 78 }

    dot3MauType1000baseT1 OBJECT-IDENTITY
        STATUS      current
        DESCRIPTION "1000BASE-T1 single balanced twisted-pair copper cabling PHY"
        REFERENCE   "IEEE Std 802.3, Clause 97"
        ::= { dot3MauType 79 }

    dot3MauType1000basePX30D OBJECT-IDENTITY
        STATUS      current
        DESCRIPTION "One single-mode fiber EPON OLT, 20km, 1:32 split ratio"
        REFERENCE   "IEEE Std 802.3, Clause 60"
        ::= { dot3MauType 80 }

    dot3MauType1000basePX30U OBJECT-IDENTITY
        STATUS      current
        DESCRIPTION "One single-mode fiber EPON ONU, 20km, 1:32 split ratio"
        REFERENCE   "IEEE Std 802.3, Clause 60"
        ::= { dot3MauType 81 }

    dot3MauType1000basePX40D OBJECT-IDENTITY
        STATUS      current
        DESCRIPTION "One single-mode fiber EPON OLT, 20km, 1:64 split ratio"
        REFERENCE   "IEEE Std 802.3, Clause 60"
        ::= { dot3MauType 82 }

    dot3MauType1000basePX40U OBJECT-IDENTITY
        STATUS      current
        DESCRIPTION "One single-mode fiber EPON ONU, 20km, 1:64 split ratio"
        REFERENCE   "IEEE Std 802.3, Clause 60"
        ::= { dot3MauType 83 }

    dot3MauType10G1GbasePRXD4 OBJECT-IDENTITY
        STATUS      current
        DESCRIPTION "One single-mode fiber asymmetric-rate EPON OLT, supporting
                     extended power budget (PRX40)"
        REFERENCE   "IEEE Std 802.3, Clause 75"
        ::= { dot3MauType 84 }

    dot3MauType10G1GbasePRXU4 OBJECT-IDENTITY
        STATUS      current
        DESCRIPTION "One single-mode fiber asymmetric-rate EPON ONU, supporting
                    extended power budget (PRX40)"
        REFERENCE   "IEEE Std 802.3, Clause 75"
        ::= { dot3MauType 85 }

    dot3MauType10GbasePRD4 OBJECT-IDENTITY
        STATUS      current
        DESCRIPTION "One single-mode fiber symmetric-rate EPON OLT, supporting
                    extended power budget (PR40)"
        REFERENCE   "IEEE Std 802.3, Clause 75"
        ::= { dot3MauType 86 }

    dot3MauType10GbasePRU4 OBJECT-IDENTITY
        STATUS      current
        DESCRIPTION "One single-mode fiber symmetric-rate EPON ONU, supporting
                    extended power budget (PR40)"
        REFERENCE   "IEEE Std 802.3, Clause 75"
        ::= { dot3MauType 87 }

    dot3MauType25GbaseCR OBJECT-IDENTITY
        STATUS      current
        DESCRIPTION "25GBASE-R PCS/PMA over shielded balanced copper cable"
        REFERENCE   "IEEE Std 802.3, Clause 110"
        ::= { dot3MauType 88 }

    dot3MauType25GbaseCRS OBJECT-IDENTITY
        STATUS      current
        DESCRIPTION "25GBASE-R PCS/PMA over shielded balanced copper cable
                    without RS-FEC"
        REFERENCE   "IEEE Std 802.3, Clause 110"
        ::= { dot3MauType 89 }

    dot3MauType25GbaseKR OBJECT-IDENTITY
        STATUS      current
        DESCRIPTION "25GBASE-R PCS/PMA over an electrical backplane"
        REFERENCE   "IEEE Std 802.3, Clause 111"
        ::= { dot3MauType 90 }

    dot3MauType25GbaseKRS OBJECT-IDENTITY
        STATUS      current
        DESCRIPTION "25GBASE-R PCS/PMA over an electrical backplane without RS-FEC"
        REFERENCE   "IEEE Std 802.3, Clause 111"
        ::= { dot3MauType 91 }

    dot3MauType25GbaseR OBJECT-IDENTITY
        STATUS      current
        DESCRIPTION "25GBASE-R PCS/PMA over undefined PMD"
        REFERENCE   "IEEE Std 802.3, Clause 107 and 109"
        ::= { dot3MauType 92 }

    dot3MauType25GbaseSR OBJECT-IDENTITY
        STATUS      current
        DESCRIPTION "25GBASE-R PCS/PMA over multimode fiber"
        REFERENCE   "IEEE Std 802.3, Clause 112"
        ::= { dot3MauType 93 }

    dot3MauType25GbaseT OBJECT-IDENTITY
        STATUS      current
        DESCRIPTION "Four-pair twisted-pair balanced copper cabling"
        REFERENCE   "IEEE Std 802.3, Clause 113"
        ::= { dot3MauType 94 }

    dot3MauType40GbaseER4 OBJECT-IDENTITY
        STATUS      current
        DESCRIPTION "40GBASE-R PCS/PMA over 4 WDM lane single mode fiber"
        REFERENCE   "IEEE Std 802.3, Clause 82"
        ::= { dot3MauType 95 }

    dot3MauType40GbaseR OBJECT-IDENTITY
        STATUS      current
        DESCRIPTION "40GBASE-R PCS as over undefined PMA/PMD"
        REFERENCE   "IEEE Std 802.3, Clause 82"
        ::= { dot3MauType 96 }

    dot3MauType40GbaseT OBJECT-IDENTITY
        STATUS      current
        DESCRIPTION "Four-pair twisted-pair balanced copper cabling"
        REFERENCE   "IEEE Std 802.3, Clause 113"
        ::= { dot3MauType 97 }

    dot3MauType100GbaseCR4 OBJECT-IDENTITY
        STATUS      current
        DESCRIPTION "100GBASE-R PCS/PMA over 4 lane shielded copper balanced cable"
        REFERENCE   "IEEE Std 802.3, Clause 92"
        ::= { dot3MauType 98 }

    dot3MauType100GbaseKR4 OBJECT-IDENTITY
        STATUS      current
        DESCRIPTION "100GBASE-R PCS/PMA over an electrical backplane"
        REFERENCE   "IEEE Std 802.3, Clause 93"
        ::= { dot3MauType 99 }

    dot3MauType100GbaseKP4 OBJECT-IDENTITY
        STATUS      current
        DESCRIPTION "100GBASE-P PCS/PMA over an electrical backplane PMD"
        REFERENCE   "IEEE Std 802.3, Clause 94"
        ::= { dot3MauType 100 }

    dot3MauType100GbaseR OBJECT-IDENTITY
        STATUS      current
        DESCRIPTION "100GBASE-R Multi-lane PCS over undefined PMA/PMD"
        REFERENCE   "IEEE Std 802.3, Clause 82"
        ::= { dot3MauType 101 }

    dot3MauType100GbaseSR4 OBJECT-IDENTITY
        STATUS      current
        DESCRIPTION "100GBASE-R PCS/PMA over 4 lane multimode fiber"
        REFERENCE   "IEEE Std 802.3, Clause 95"
        ::= { dot3MauType 102 }

    dot3MauType2p5GigT OBJECT-IDENTITY
        STATUS      current
        DESCRIPTION "2.5GBASE-T Four-pair twisted-pair balanced copper cabling PHY"
        REFERENCE   "IEEE Std 802.3-2018, Clause 126"
        ::= { dot3MauType 103 }

    dot3MauType5GigT OBJECT-IDENTITY
        STATUS      current
        DESCRIPTION "5GBASE-T Four-pair twisted-pair balanced copper cabling PHY"
        REFERENCE   "IEEE Std 802.3-2018, Clause 126"
        ::= { dot3MauType 104 }

    dot3MauType100baseT1 OBJECT-IDENTITY
        STATUS current
        DESCRIPTION "100BASE-T1 Single balanced twisted-pair copper cabling PHY"
        REFERENCE   "IEEE Std 802.3, Clause 96"
        ::= { dot3MauType 105 }

    dot3MauType1000baseRHA OBJECT-IDENTITY
        STATUS current
        DESCRIPTION "1000BASE-RHA Plastic optical fiber PHY"
        REFERENCE   "IEEE Std 802.3, Clause 115"
        ::= { dot3MauType 106 }

    dot3MauType1000baseRHB OBJECT-IDENTITY
        STATUS current
        DESCRIPTION "1000BASE-RHB Plastic optical fiber PHY"
        REFERENCE   "IEEE Std 802.3, Clause 115"
        ::= { dot3MauType 107 }

    dot3MauType1000baseRHC OBJECT-IDENTITY
        STATUS current
        DESCRIPTION "1000BASE-RHC Plastic optical fiber PHY"
        REFERENCE   "IEEE Std 802.3, Clause 115"
        ::= { dot3MauType 108 }

    dot3MauType2p5GbaseKX OBJECT-IDENTITY
        STATUS current
        DESCRIPTION "2.5GBASE-X PMD over an electrical backplane"
        REFERENCE   "IEEE Std 802.3, Clause 128"
        ::= { dot3MauType 109 }

    dot3MauType2p5GbaseX OBJECT-IDENTITY
        STATUS current
        DESCRIPTION "2.5GBASE-X PCS/PMA over undefined PMD"
        REFERENCE   "IEEE Std 802.3, Clause 127"
        ::= { dot3MauType 110 }

    dot3MauType5GbaseKR OBJECT-IDENTITY
        STATUS current
        DESCRIPTION "5GBASE-KR PMD over an electrical backplane"
        REFERENCE   "IEEE Std 802.3, Clause 130"
        ::= { dot3MauType 111 }

    dot3MauType5GbaseR OBJECT-IDENTITY
        STATUS current
        DESCRIPTION "5GBASE-R PCS/PMA over undefined PMD"
        REFERENCE   "IEEE Std 802.3, Clause 129"
        ::= { dot3MauType 112 }

    dot3MauType10GpassXR OBJECT-IDENTITY
        STATUS current
        DESCRIPTION "Coax cable distribution network PHY continuous downstream/burst mode upstream PHY"
        REFERENCE   "IEEE Std 802.3, Clause 100 and 101"
        ::= { dot3MauType 113 }

    dot3MauType25GbaseLR OBJECT-IDENTITY
        STATUS current
        DESCRIPTION "25GBASE-R PCS/PMA over single-mode fiber PMD, with long reach"
        REFERENCE   "IEEE Std 802.3, Clause 114"
        ::= { dot3MauType 114 }

    dot3MauType25GbaseER OBJECT-IDENTITY
        STATUS current
        DESCRIPTION "25GBASE-R PCS/PMA over single-mode fiber PMD, with extended reach"
        REFERENCE   "IEEE Std 802.3, Clause 114"
        ::= { dot3MauType 115 }

    dot3MauType50GbaseR OBJECT-IDENTITY
        STATUS current
        DESCRIPTION "50GBASE-R Multi-lane PCS over undefined PMA/PMD"
        REFERENCE   "IEEE Std 802.3, Clause 133 and 135"
        ::= { dot3MauType 116 }

    dot3MauType50GbaseCR OBJECT-IDENTITY
        STATUS current
        DESCRIPTION "50GBASE-R PCS/PMA over shielded copper balanced cable PMD"
        REFERENCE   "IEEE Std 802.3, Clause 136"
        ::= { dot3MauType 117 }

    dot3MauType50GbaseKR OBJECT-IDENTITY
        STATUS current
        DESCRIPTION "50GBASE-R PCS/PMA over an electrical backplane PMD"
        REFERENCE   "IEEE Std 802.3, Clause 137"
        ::= { dot3MauType 118 }

    dot3MauType50GbaseSR OBJECT-IDENTITY
        STATUS current
        DESCRIPTION "50GBASE-R PCS/PMA over multimode fiber PMD"
        REFERENCE   "IEEE Std 802.3, Clause 138"
        ::= { dot3MauType 119 }

    dot3MauType50GbaseFR OBJECT-IDENTITY
        STATUS current
        DESCRIPTION "50GBASE-R PCS/PMA over single mode fiber PMD with reach up to at least 2 km"
        REFERENCE   "IEEE Std 802.3, Clause 139"
        ::= { dot3MauType 120 }

    dot3MauType50GbaseLR OBJECT-IDENTITY
        STATUS current
        DESCRIPTION "50GBASE-R PCS/PMA over single mode fiber PMD with reach up to at least 10 km"
        REFERENCE   "IEEE Std 802.3, Clause 139"
        ::= { dot3MauType 121 }

    dot3MauType50GbaseER OBJECT-IDENTITY
        STATUS current
        DESCRIPTION "50GBASE-R PCS/PMA over single-mode fiber PMD with reach up to at least 40 km"
        REFERENCE   "IEEE Std 802.3, Clause 139"
        ::= { dot3MauType 122 }

    dot3MauType100GbaseCR2 OBJECT-IDENTITY
        STATUS current
        DESCRIPTION "100GBASE-R PCS/PMA over 2 lane shielded copper balanced cable PMD"
        REFERENCE   "IEEE Std 802.3, Clause 136"
        ::= { dot3MauType 123 }

    dot3MauType100GbaseKR2 OBJECT-IDENTITY
        STATUS current
        DESCRIPTION "100GBASE-R PCS/PMA over an electrical backplane PMD"
        REFERENCE   "IEEE Std 802.3, Clause 137"
        ::= { dot3MauType 124 }

    dot3MauType100GbaseSR2 OBJECT-IDENTITY
        STATUS current
        DESCRIPTION "100GBASE-R PCS/PMA over 2 lane multimode fiber PMD"
        REFERENCE   "IEEE Std 802.3, Clause 138"
        ::= { dot3MauType 125 }

    dot3MauType100GbaseDR OBJECT-IDENTITY
        STATUS current
        DESCRIPTION "100GBASE-R PCS/PMA over single mode fiber PMD"
        REFERENCE   "IEEE Std 802.3, Clause 140"
        ::= { dot3MauType 126 }

    dot3MauType200GbaseR OBJECT-IDENTITY
        STATUS current
        DESCRIPTION "200GBASE-R Multi-lane PCS over undefined PMA/PMD"
        REFERENCE   "IEEE Std 802.3, Clause 119"
        ::= { dot3MauType 127 }

    dot3MauType200GbaseDR4 OBJECT-IDENTITY
        STATUS current
        DESCRIPTION "200GBASE-R PCS/PMA over 4-lane single-mode fiber PMD"
        REFERENCE   "IEEE Std 802.3, Clause 121"
        ::= { dot3MauType 128 }

    dot3MauType200GbaseFR4 OBJECT-IDENTITY
        STATUS current
        DESCRIPTION "200GBASE-R PCS/PMA over 4 WDM lane single-mode fiber PMD with reach up to at least 2 km"
        REFERENCE   "IEEE Std 802.3, Clause 122"
        ::= { dot3MauType 129 }

    dot3MauType200GbaseLR4 OBJECT-IDENTITY
        STATUS current
        DESCRIPTION "200GBASE-R PCS/PMA over 4 WDM lane single-mode fiber PMD with reach up to at least 10 km"
        REFERENCE   "IEEE Std 802.3, Clause 122"
        ::= { dot3MauType 130 }

    dot3MauType200GbaseCR4 OBJECT-IDENTITY
        STATUS current
        DESCRIPTION "200GBASE-R PCS/PMA over 4 lane shielded copper balanced cable PMD"
        REFERENCE   "IEEE Std 802.3, Clause 136"
        ::= { dot3MauType 131 }

    dot3MauType200GbaseKR4 OBJECT-IDENTITY
        STATUS current
        DESCRIPTION "200GBASE-R PCS/PMA over an electrical backplane PMD"
        REFERENCE   "IEEE Std 802.3, Clause 137"
        ::= { dot3MauType 132 }

    dot3MauType200GbaseSR4 OBJECT-IDENTITY
        STATUS current
        DESCRIPTION "200GBASE-R PCS/PMA over 4 lane multimode fiber PMD"
        REFERENCE   "IEEE Std 802.3, Clause 138"
        ::= { dot3MauType 133 }

    dot3MauType200GbaseER4 OBJECT-IDENTITY
        STATUS current
        DESCRIPTION "200GBASE-R PCS/PMA over 4 WDM lane single-mode fiber PMD with reach up to at least 40 km"
        REFERENCE   "IEEE Std 802.3, Clause 122"
        ::= { dot3MauType 134 }

    dot3MauType400GbaseR OBJECT-IDENTITY
        STATUS current
        DESCRIPTION "400GBASE-R Multi-lane PCS over undefined PMA/PMD"
        REFERENCE   "IEEE Std 802.3, Clause 119"
        ::= { dot3MauType 135 }

    dot3MauType400GbaseSR16 OBJECT-IDENTITY
        STATUS current
        DESCRIPTION "400GBASE-R PCS/PMA over 16-lane multimode fiber PMD"
        REFERENCE   "IEEE Std 802.3, Clause 123"
        ::= { dot3MauType 136 }

    dot3MauType400GbaseDR4 OBJECT-IDENTITY
        STATUS current
        DESCRIPTION "400GBASE-R PCS/PMA over 4-lane single-mode fiber PMD"
        REFERENCE   "IEEE Std 802.3, Clause 124"
        ::= { dot3MauType 137 }

    dot3MauType400GbaseFR8 OBJECT-IDENTITY
        STATUS current
        DESCRIPTION "400GBASE-R PCS/PMA over 8 WDM lane single-mode fiber PMD with reach up to at least 2 km"
        REFERENCE   "IEEE Std 802.3, Clause 122"
        ::= { dot3MauType 138 }

    dot3MauType400GbaseLR8 OBJECT-IDENTITY
        STATUS current
        DESCRIPTION "400GBASE-R PCS/PMA over 8 WDM lane single-mode fiber PMD with reach up to at least 10 km"
        REFERENCE   "IEEE Std 802.3, Clause 122"
        ::= { dot3MauType 139 }

    dot3MauType400GbaseER8 OBJECT-IDENTITY
        STATUS current
        DESCRIPTION "400GBASE-R PCS/PMA over 8 WDM lane single-mode fiber PMD with reach up to at least 40 km"
        REFERENCE   "IEEE Std 802.3, Clause 122"
        ::= { dot3MauType 140 }

    dot3MauType10baseT1L OBJECT-IDENTITY
        STATUS current
        DESCRIPTION "10BASE-T1L Single balanced pair PHY"
        REFERENCE   "IEEE Std 802.3, Clause 146"
        ::= { dot3MauType 141 }

    dot3MauType10baseT1SHD OBJECT-IDENTITY
        STATUS current
        DESCRIPTION "10BASE-T1S Single balanced pair PHY, half duplex mode"
        REFERENCE   "IEEE Std 802.3, Clause 147"
        ::= { dot3MauType 142 }

    dot3MauType10baseT1SMD OBJECT-IDENTITY
        STATUS current
        DESCRIPTION "10BASE-T1S Single balanced pair PHY, multidrop mode"
        REFERENCE   "IEEE Std 802.3, Clause 147"
        ::= { dot3MauType 143 }

    dot3MauType10baseT1SFD OBJECT-IDENTITY
        STATUS current
        DESCRIPTION "10BASE-T1S Single balanced pair PHY, full duplex mode"
        REFERENCE   "IEEE Std 802.3, Clause 147"
        ::= { dot3MauType 144 }

    dot3MauType100GbaseFR1 OBJECT-IDENTITY
        STATUS current
        DESCRIPTION "100GBASE-R PCS/PMA over single-mode fiber PMD with reach up to at least 2 km"
        REFERENCE   "IEEE Std 802.3, Clause 140"
        ::= { dot3MauType 145 }

    dot3MauType100GbaseLR1 OBJECT-IDENTITY
        STATUS current
        DESCRIPTION "100GBASE-R PCS/PMA over single-mode fiber PMD with reach up to at least 10 km"
        REFERENCE   "IEEE Std 802.3, Clause 140"
        ::= { dot3MauType 146 }

    dot3MauType400GbaseFR4 OBJECT-IDENTITY
        STATUS current
        DESCRIPTION "400GBASE-R PCS/PMA over 4 WDM lane single-mode fiber PMD with reach up to at least 2 km"
        REFERENCE   "IEEE Std 802.3, Clause 151"
        ::= { dot3MauType 147 }

    dot3MauType400GbaseLR46 OBJECT-IDENTITY
        STATUS current
        DESCRIPTION "400GBASE-R PCS/PMA over 4 WDM lane single-mode fiber PMD with reach up to at least 6 km"
        REFERENCE   "IEEE Std 802.3, Clause 151"
        ::= { dot3MauType 148 }

    dot3MauType400GbaseSR8 OBJECT-IDENTITY
        STATUS current
        DESCRIPTION "400GBASE-R PCS/PMA over 8-lane multimode fiber PMD as specified in Clause 138"
        ::= { dot3MauType 149 }

    dot3MauType400GbaseSR4p2 OBJECT-IDENTITY
        STATUS current
        DESCRIPTION "400GBASE-R PCS/PMA over 8-lane multimode fiber PMD as specified in Clause 150"
        ::= { dot3MauType 150 }

    dot3MauType2p5GbaseT1 OBJECT-IDENTITY
        STATUS current
        DESCRIPTION "Single balanced pair of conductors PHY as specified in Clause 149"
        ::= { dot3MauType 151 }

    dot3MauType5GbaseT1 OBJECT-IDENTITY
        STATUS current
        DESCRIPTION "Single balanced pair of conductors PHY as specified in Clause 149"
        ::= { dot3MauType 152 }

    dot3MauType10GbaseT1 OBJECT-IDENTITY
        STATUS current
        DESCRIPTION "Single balanced pair of conductors PHY as specified in Clause 149"
        ::= { dot3MauType 153 }

    dot3MauType25G10GbasePQGD2 OBJECT-IDENTITY
        STATUS current
        DESCRIPTION "One single mode fiber, 1 x 25.78125 GBd continuous transmission / 1 x 10.3125 GBd burst mode reception, medium power class, as specified in Clause 141"
        ::= { dot3MauType 154 }

    dot3MauType25G10GbasePQGD3 OBJECT-IDENTITY
        STATUS current
        DESCRIPTION "One single mode fiber, 1 x 25.78125 GBd continuous transmission / 1 x 10.3125 GBd burst mode reception, high power class, as specified in Clause 141"
        ::= { dot3MauType 155 }

    dot3MauType25G10GbasePQGU2 OBJECT-IDENTITY
        STATUS current
        DESCRIPTION "One single mode fiber, 1 x 25.78125 GBd continuous reception / 1 x 10.3125 GBd burst mode transmission, medium power class, as specified in Clause 141"
        ::= { dot3MauType 156 }

    dot3MauType25G10GbasePQGU3 OBJECT-IDENTITY
        STATUS current
        DESCRIPTION "One single mode fiber, 1 x 25.78125 GBd continuous reception / 1 x 10.3125 GBd burst mode transmission, high power class, as specified in Clause 141"
        ::= { dot3MauType 157 }

    dot3MauType25G10GbasePQXD2 OBJECT-IDENTITY
        STATUS current
        DESCRIPTION "One single mode fiber, 1 x 25.78125 GBd continuous transmission / 1 x 10.3125 GBd burst mode reception, medium power class, as specified in Clause 141"
        ::= { dot3MauType 158 }

    dot3MauType25G10GbasePQXD3 OBJECT-IDENTITY
        STATUS current
        DESCRIPTION "One single mode fiber, 1 x 25.78125 GBd continuous transmission / 1 x 10.3125 GBd burst mode reception, high power class, as specified in Clause 141"
        ::= { dot3MauType 159 }

    dot3MauType25G10GbasePQXU2 OBJECT-IDENTITY
        STATUS current
        DESCRIPTION "One single mode fiber, 1 x 25.78125 GBd continuous reception / 1 x 10.3125 GBd burst mode transmission, medium power class, as specified in Clause 141"
        ::= { dot3MauType 160 }

    dot3MauType25G10GbasePQXU3 OBJECT-IDENTITY
        STATUS current
        DESCRIPTION "One single mode fiber, 1 x 25.78125 GBd continuous reception / 1 x 10.3125 GBd burst mode transmission, high power class, as specified in Clause 141"
        ::= { dot3MauType 161 }

    dot3MauType25GbasePQGD2 OBJECT-IDENTITY
        STATUS current
        DESCRIPTION "One single mode fiber, 1 x 25.78125 GBd continuous transmission / 1 x 25.78125 GBd burst mode reception, medium power class, as specified in Clause 141"
        ::= { dot3MauType 162 }

    dot3MauType25GbasePQGD3 OBJECT-IDENTITY
        STATUS current
        DESCRIPTION "One single mode fiber, 1 x 25.78125 GBd continuous transmission / 1 x 25.78125 GBd burst mode reception, high power class, as specified in Clause 141"
        ::= { dot3MauType 163 }

    dot3MauType25GbasePQGU2 OBJECT-IDENTITY
        STATUS current
        DESCRIPTION "One single mode fiber, 1 x 25.78125 GBd continuous reception / 1 x 25.78125 GBd burst mode transmission, medium power class, as specified in Clause 141"
        ::= { dot3MauType 164 }

    dot3MauType25GbasePQGU3 OBJECT-IDENTITY
        STATUS current
        DESCRIPTION "One single mode fiber, 1 x 25.78125 GBd continuous reception / 1 x 25.78125 GBd burst mode transmission, high power class, as specified in Clause 141"
        ::= { dot3MauType 165 }

    dot3MauType25GbasePQXD2 OBJECT-IDENTITY
        STATUS current
        DESCRIPTION "One single mode fiber, 1 x 25.78125 GBd continuous transmission / 1 x 25.78125 GBd burst mode reception, medium power class, as specified in Clause 141"
        ::= { dot3MauType 166 }

    dot3MauType25GbasePQXD3 OBJECT-IDENTITY
        STATUS current
        DESCRIPTION "One single mode fiber, 1 x 25.78125 GBd continuous transmission / 1 x 25.78125 GBd burst mode reception, high power class, as specified in Clause 141"
        ::= { dot3MauType 167 }

    dot3MauType25GbasePQXU2 OBJECT-IDENTITY
        STATUS current
        DESCRIPTION "One single mode fiber, 1 x 25.78125 GBd continuous reception / 1 x 25.78125 GBd burst mode transmission, medium power class, as specified in Clause 141"
        ::= { dot3MauType 168 }

    dot3MauType25GbasePQXU3 OBJECT-IDENTITY
        STATUS current
        DESCRIPTION "One single mode fiber, 1 x 25.78125 GBd continuous reception / 1 x 25.78125 GBd burst mode transmission, high power class, as specified in Clause 141"
        ::= { dot3MauType 169 }

    dot3MauType50G10GbasePQGD2 OBJECT-IDENTITY
        STATUS current
        DESCRIPTION "One single mode fiber, 2 x 25.78125 GBd continuous transmission / 1 x 10.3125 GBd burst mode reception, medium power class, as specified in Clause 141"
        ::= { dot3MauType 170 }

    dot3MauType50G10GbasePQGD3 OBJECT-IDENTITY
        STATUS current
        DESCRIPTION "One single mode fiber, 2 x 25.78125 GBd continuous transmission / 1 x 10.3125 GBd burst mode reception, high power class, as specified in Clause 141"
        ::= { dot3MauType 171 }

    dot3MauType50G10GbasePQGU2 OBJECT-IDENTITY
        STATUS current
        DESCRIPTION "One single mode fiber, 2 x 25.78125 GBd continuous reception / 1 x 10.3125 GBd burst mode transmission, medium power class, as specified in Clause 141"
        ::= { dot3MauType 172 }

    dot3MauType50G10GbasePQGU3 OBJECT-IDENTITY
        STATUS current
        DESCRIPTION "One single mode fiber, 2 x 25.78125 GBd continuous reception / 1 x 10.3125 GBd burst mode transmission, high power class, as specified in Clause 141"
        ::= { dot3MauType 173 }

    dot3MauType50G10GbasePQXD2 OBJECT-IDENTITY
        STATUS current
        DESCRIPTION "One single mode fiber, 2 x 25.78125 GBd continuous transmission / 1 x 10.3125 GBd burst mode reception, medium power class, as specified in Clause 141"
        ::= { dot3MauType 174 }

    dot3MauType50G10GbasePQXD3 OBJECT-IDENTITY
        STATUS current
        DESCRIPTION "One single mode fiber, 2 x 25.78125 GBd continuous transmission / 1 x 10.3125 GBd burst mode reception, high power class, as specified in Clause 141"
        ::= { dot3MauType 175 }

    dot3MauType50G10GbasePQXU2 OBJECT-IDENTITY
        STATUS current
        DESCRIPTION "One single mode fiber, 2 x 25.78125 GBd continuous reception / 1 x 10.3125 GBd burst mode transmission, medium power class, as specified in Clause 141"
        ::= { dot3MauType 176 }

    dot3MauType50G10GbasePQXU3 OBJECT-IDENTITY
        STATUS current
        DESCRIPTION "One single mode fiber, 2 x 25.78125 GBd continuous reception / 1 x 10.3125 GBd burst mode transmission, high power class, as specified in Clause 141"
        ::= { dot3MauType 177 }

    dot3MauType50G25GbasePQGD2 OBJECT-IDENTITY
        STATUS current
        DESCRIPTION "One single mode fiber, 2 x 25.78125 GBd continuous transmission / 1 x 25.78125 GBd burst mode reception, medium power class, as specified in Clause 141"
        ::= { dot3MauType 178 }

    dot3MauType50G25GbasePQGD3 OBJECT-IDENTITY
        STATUS current
        DESCRIPTION "One single mode fiber, 2 x 25.78125 GBd continuous transmission / 1 x 25.78125 GBd burst mode reception, high power class, as specified in Clause 141"
        ::= { dot3MauType 179 }

    dot3MauType50G25GbasePQGU2 OBJECT-IDENTITY
        STATUS current
        DESCRIPTION "One single mode fiber, 2 x 25.78125 GBd continuous reception / 1 x 25.78125 GBd burst mode transmission, medium power class, as specified in Clause 141"
        ::= { dot3MauType 180 }

    dot3MauType50G25GbasePQGU3 OBJECT-IDENTITY
        STATUS current
        DESCRIPTION "One single mode fiber, 2 x 25.78125 GBd continuous reception / 1 x 25.78125 GBd burst mode transmission, high power class, as specified in Clause 141"
        ::= { dot3MauType 181 }

    dot3MauType50G25GbasePQXD2 OBJECT-IDENTITY
        STATUS current
        DESCRIPTION "One single mode fiber, 2 x 25.78125 GBd continuous transmission / 1 x 25.78125 GBd burst mode reception, medium power class, as specified in Clause 141"
        ::= { dot3MauType 182 }

    dot3MauType50G25GbasePQXD3 OBJECT-IDENTITY
        STATUS current
        DESCRIPTION "One single mode fiber, 2 x 25.78125 GBd continuous transmission / 1 x 25.78125 GBd burst mode reception, high power class, as specified in Clause 141"
        ::= { dot3MauType 183 }

    dot3MauType50G25GbasePQXU2 OBJECT-IDENTITY
        STATUS current
        DESCRIPTION "One single mode fiber, 2 x 25.78125 GBd continuous reception / 1 x 25.78125 GBd burst mode transmission, medium power class, as specified in Clause 141"
        ::= { dot3MauType 184 }

    dot3MauType50G25GbasePQXU3 OBJECT-IDENTITY
        STATUS current
        DESCRIPTION "One single mode fiber, 2 x 25.78125 GBd continuous reception / 1 x 25.78125 GBd burst mode transmission, high power class, as specified in Clause 141"
        ::= { dot3MauType 185 }

    dot3MauType50GbasePQGD2 OBJECT-IDENTITY
        STATUS current
        DESCRIPTION "One single mode fiber, 2 x 25.78125 GBd continuous transmission / 2 x 25.78125 GBd burst mode reception, medium power class, as specified in Clause 141"
        ::= { dot3MauType 186 }

    dot3MauType50GbasePQGD3 OBJECT-IDENTITY
        STATUS current
        DESCRIPTION "One single mode fiber, 2 x 25.78125 GBd continuous transmission / 2 x 25.78125 GBd burst mode reception, high power class, as specified in Clause 141"
        ::= { dot3MauType 187 }

    dot3MauType50GbasePQGU2 OBJECT-IDENTITY
        STATUS current
        DESCRIPTION "One single mode fiber, 2 x 25.78125 GBd continuous reception / 2 x 25.78125 GBd burst mode transmission, medium power class, as specified in Clause 141"
        ::= { dot3MauType 188 }

    dot3MauType50GbasePQGU3 OBJECT-IDENTITY
        STATUS current
        DESCRIPTION "One single mode fiber, 2 x 25.78125 GBd continuous reception / 2 x 25.78125 GBd burst mode transmission, high power class, as specified in Clause 141"
        ::= { dot3MauType 189 }

    dot3MauType50GbasePQXD2 OBJECT-IDENTITY
        STATUS current
        DESCRIPTION "One single mode fiber, 2 x 25.78125 GBd continuous transmission / 2 x 25.78125 GBd burst mode reception, medium power class, as specified in Clause 141"
        ::= { dot3MauType 190 }

    dot3MauType50GbasePQXD3 OBJECT-IDENTITY
        STATUS current
        DESCRIPTION "One single mode fiber, 2 x 25.78125 GBd continuous transmission / 2 x 25.78125 GBd burst mode reception, high power class, as specified in Clause 141"
        ::= { dot3MauType 191 }

    dot3MauType50GbasePQXU2 OBJECT-IDENTITY
        STATUS current
        DESCRIPTION "One single mode fiber, 2 x 25.78125 GBd continuous reception / 2 x 25.78125 GBd burst mode transmission, medium power class, as specified in Clause 141"
        ::= { dot3MauType 192 }

    dot3MauType50GbasePQXU3 OBJECT-IDENTITY
        STATUS current
        DESCRIPTION "One single mode fiber, 2 x 25.78125 GBd continuous reception / 2 x 25.78125 GBd burst mode transmission, high power class, as specified in Clause 141"
        ::= { dot3MauType 193 }

    dot3MauType100GbaseZR OBJECT-IDENTITY
        STATUS current
        DESCRIPTION "100GBASE-R PCS/100GBASE-ZR PMA over a PMD with reach up to at least 80 km as specified in Clause 154"
        ::= { dot3MauType 194 }

    dot3MauType10GbaseBR10D OBJECT-IDENTITY
        STATUS current
        DESCRIPTION "One single-mode fiber OLT PHY supporting a distance of at least 10 km as specified in Clause 158"
        ::= { dot3MauType 195 }

    dot3MauType10GbaseBR10U OBJECT-IDENTITY
        STATUS current
        DESCRIPTION "One single-mode fiber ONU PHY supporting a distance of at least 10 km as specified in Clause 158"
        ::= { dot3MauType 196 }

    dot3MauType10GbaseBR20D OBJECT-IDENTITY
        STATUS current
        DESCRIPTION "One single-mode fiber OLT PHY supporting a distance of at least 20 km as specified in Clause 158"
        ::= { dot3MauType 197 }

    dot3MauType10GbaseBR20U OBJECT-IDENTITY
        STATUS current
        DESCRIPTION "One single-mode fiber ONU PHY supporting a distance of at least 20 km as specified in Clause 158"
        ::= { dot3MauType 198 }

    dot3MauType10GbaseBR40D OBJECT-IDENTITY
        STATUS current
        DESCRIPTION "One single-mode fiber OLT PHY supporting a distance of at least 40 km as specified in Clause 158"
        ::= { dot3MauType 199 }

    dot3MauType10GbaseBR40U OBJECT-IDENTITY
        STATUS current
        DESCRIPTION "One single-mode fiber ONU PHY supporting a distance of at least 40 km as specified in Clause 158"
        ::= { dot3MauType 200 }

    dot3MauType25GbaseBR10D OBJECT-IDENTITY
        STATUS current
        DESCRIPTION "One single-mode fiber OLT PHY supporting a distance of at least 10 km as specified in Clause 159"
        ::= { dot3MauType 201 }

    dot3MauType25GbaseBR10U OBJECT-IDENTITY
        STATUS current
        DESCRIPTION "One single-mode fiber ONU PHY supporting a distance of at least 10 km as specified in Clause 159"
        ::= { dot3MauType 202 }

    dot3MauType25GbaseBR20D OBJECT-IDENTITY
        STATUS current
        DESCRIPTION "One single-mode fiber OLT PHY supporting a distance of at least 20 km as specified in Clause 159"
        ::= { dot3MauType 203 }

    dot3MauType25GbaseBR20U OBJECT-IDENTITY
        STATUS current
        DESCRIPTION "One single-mode fiber ONU PHY supporting a distance of at least 20 km as specified in Clause 159"
        ::= { dot3MauType 204 }

    dot3MauType25GbaseBR40D OBJECT-IDENTITY
        STATUS current
        DESCRIPTION "One single-mode fiber OLT PHY supporting a distance of at least 40 km as specified in Clause 159"
        ::= { dot3MauType 205 }

    dot3MauType25GbaseBR40U OBJECT-IDENTITY
        STATUS current
        DESCRIPTION "One single-mode fiber ONU PHY supporting a distance of at least 40 km as specified in Clause 159"
        ::= { dot3MauType 206 }

    dot3MauType50GbaseBR10D OBJECT-IDENTITY
        STATUS current
        DESCRIPTION "One single-mode fiber OLT PHY supporting a distance of at least 10 km as specified in Clause 160"
        ::= { dot3MauType 207 }

    dot3MauType50GbaseBR10U OBJECT-IDENTITY
        STATUS current
        DESCRIPTION "One single-mode fiber ONU PHY supporting a distance of at least 10 km as specified in Clause 160"
        ::= { dot3MauType 208 }

    dot3MauType50GbaseBR20D OBJECT-IDENTITY
        STATUS current
        DESCRIPTION "One single-mode fiber OLT PHY supporting a distance of at least 20 km as specified in Clause 160"
        ::= { dot3MauType 209 }

    dot3MauType50GbaseBR20U OBJECT-IDENTITY
        STATUS current
        DESCRIPTION "One single-mode fiber ONU PHY supporting a distance of at least 20 km as specified in Clause 160"
        ::= { dot3MauType 210 }

    dot3MauType50GbaseBR40D OBJECT-IDENTITY
        STATUS current
        DESCRIPTION "One single-mode fiber OLT PHY supporting a distance of at least 40 km as specified in Clause 160"
        ::= { dot3MauType 211 }

    dot3MauType50GbaseBR40U OBJECT-IDENTITY
        STATUS current
        DESCRIPTION "One single-mode fiber ONU PHY supporting a distance of at least 40 km as specified in Clause 160"
        ::= { dot3MauType 212 }

    dot3MauType2p5GbaseAU OBJECT-IDENTITY
        STATUS current
        DESCRIPTION "Glass optical fiber PHY as specified in Clause 166"
        ::= { dot3MauType 213 }

    dot3MauType5GbaseAU OBJECT-IDENTITY
        STATUS current
        DESCRIPTION "Glass optical fiber PHY as specified in Clause 166"
        ::= { dot3MauType 214 }

    dot3MauType10GbaseAU OBJECT-IDENTITY
        STATUS current
        DESCRIPTION "Glass optical fiber PHY as specified in Clause 166"
        ::= { dot3MauType 215 }

    dot3MauType25GbaseAU OBJECT-IDENTITY
        STATUS current
        DESCRIPTION "Glass optical fiber PHY as specified in Clause 166"
        ::= { dot3MauType 216 }

    dot3MauType50GbaseAU OBJECT-IDENTITY
        STATUS current
        DESCRIPTION "Glass optical fiber PHY as specified in Clause 166"
        ::= { dot3MauType 217 }

    dot3MauType25GbaseT1 OBJECT-IDENTITY
        STATUS current
        DESCRIPTION "Single balanced pair of conductors PHY as specified in Clause 165"
        ::= { dot3MauType 218 }

    dot3MauType400GbaseDR42 OBJECT-IDENTITY
        STATUS current
        DESCRIPTION "400GBASE-R PCS/PMA over 4 single-mode fibers in each direction
                    PMD with reach up to at least 2 km as specified in Clause 124"
        ::= { dot3MauType 219 }

    dot3MauType800GbaseCR8 OBJECT-IDENTITY
        STATUS current
        DESCRIPTION "800GBASE-R PCS/PMA over 8-lane shielded balanced copper cable
                    PMD as specified in Clause 162"
        ::= { dot3MauType 220 }

    dot3MauType800GbaseDR8 OBJECT-IDENTITY
        STATUS current
        DESCRIPTION "800GBASE-R PCS/PMA over 8 single-mode fibers in each direction
                    PMD with reach up to at least 500 m as specified in Clause 124"
        ::= { dot3MauType 221 }

    dot3MauType800GbaseDR82 OBJECT-IDENTITY
        STATUS current
        DESCRIPTION "800GBASE-R PCS/PMA over 8 single-mode fibers in each direction
                    PMD with reach up to at least 2 km as specified in Clause 124"
        ::= { dot3MauType 222 }

    dot3MauType800GbaseKR8 OBJECT-IDENTITY
        STATUS current
        DESCRIPTION "800GBASE-R PCS/PMA over an electrical backplane PMD as specified
                    in Clause 163"
        ::= { dot3MauType 223 }

    dot3MauType800GbaseR OBJECT-IDENTITY
        STATUS current
        DESCRIPTION "Multi-lane PCS as specified in Clause 172 over undefined PMA/PMD"
        ::= { dot3MauType 224 }

    dot3MauType800GbaseSR8 OBJECT-IDENTITY
        STATUS current
        DESCRIPTION "800GBASE-R PCS/PMA over 8 multimode fibers in each direction
                    PMD with reach up to at least 100 m as specified in Clause 167"
        ::= { dot3MauType 225 }

    dot3MauType800GbaseVR8 OBJECT-IDENTITY
        STATUS current
        DESCRIPTION "800GBASE-R PCS/PMA over 8 multimode fibers in each direction
                    PMD with reach up to at least 50 m as specified in Clause 167"
        ::= { dot3MauType 226 }

END
